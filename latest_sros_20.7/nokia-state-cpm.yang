submodule nokia-state-cpm {

    yang-version "1.1";

    belongs-to nokia-state { prefix "state"; }

    import ietf-yang-types                { prefix "yang"; }
    import nokia-sros-yang-extensions     { prefix "sros-ext"; }
    import nokia-types-card               { prefix "types-card"; }
    import nokia-types-sros               { prefix "types-sros"; }
    import nokia-types-system             { prefix "types-system"; }


    sros-ext:sros-major-release "rel20";

    organization "Nokia";

    contact
        "Nokia SR OS Support
         Web: <http://www.nokia.com>";

    description
        "Nokia YANG Data model with operational state for control plane module on SR OS based routers.

         Copyright 2016 Nokia. All rights reserved. Reproduction of this document
         is authorized on the condition that the foregoing copyright notice is included.

         This nokia-state-cpm YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";

    revision "2019-10-09";

    grouping state-cpm {
        list cpm {
            key "cpm-slot";
            description "Enter the cpm list instance";

            leaf cpm-slot {
                type types-card:cpm-card-slot;
                description "The unique value which identifies this CPM slot.";
            }

            leaf equipped-type {
                type types-card:sros-cpm-type-state;
                description
                    "Indicates the CPM type that is physically inserted into
                     the slot.";
            }

            leaf redundancy-status {
                type enumeration {
                    enum "singleton"                    { value 1; }
                    enum "redundant-active"             { value 2; }
                    enum "redundant-standby"            { value 3; }
                    enum "redundant-split"              { value 4; }
                    enum "redundant-disabled"           { value 5; }
                    enum "redundant-syncing"            { value 6; }
                    enum "redundant-ext-active"         { value 7; }
                    enum "redundant-ext-standby"        { value 8; }
                }
                description "Indicates the role of the CPM card for the redundant pair.";
            }

            leaf number-of-cpus {
                type uint32;
                description "Indicates the number of CPU chips populated on this CPM module.";
            }

            leaf cpu-type {
                type enumeration {
                    enum "unknown"                      { value 1; }
                    enum "mips"                         { value 2; }
                    enum "pentium-pc"                   { value 3; }
                    enum "arm"                          { value 4; }
                }
                description "Indicates the type of CPU chips populated on this CPM module.";
            }

            leaf memory-capacity {
                type uint32;
                units "megabytes";
                description "Indicates the amount of memory populated on this CPM module.";
            }

            leaf system-timing-oscillator-type {
                type enumeration {
                    enum "none"                         { value 1; }
                    enum "tcxo"                         { value 2; }
                    enum "ocxo"                         { value 3; }
                }
                description "Indicates the type of oscillator present on the CPM.";
            }

            leaf universally-unique-identifier {
                type types-sros:uuid;
                description
                    "Indicates the Universally Unique Identifier (UUID) of the
                     CPM card.";
            }

            container boot-options-file {
                description "Enter the boot-options-file context";

                leaf last-modified-time {
                    type yang:date-and-time;
                    description
                        "The date and time the boot options file (BOF) for this CPM was last
                         modified.";
                }

                leaf last-saved-time {
                    type yang:date-and-time;
                    description "The date and time the boot options file (BOF) was last saved.";
                }

                leaf version {
                    type types-sros:description-or-empty;
                    description
                        "The version of the boot options file (BOF) read when this CPM card was
                         last rebooted.";
                }

            } // container boot-options-file

            container config-file {
                description "Enter the config-file context";

                leaf last-booted-file {
                    type string;
                    description
                        "Indicates the location and name of the configuration file from
                         which the system last rebooted.";
                }

                leaf last-modified-time {
                    type yang:date-and-time;
                    description "The date and time the running configuration was last modified.";
                }

                leaf last-saved-time {
                    type yang:date-and-time;
                    description "The date and time the running configuration was last saved.";
                }

                leaf last-saved-file {
                    type string;
                    description
                        "Indicates the location and name of the file to which the
                         configuration was last saved.";
                }

                leaf version {
                    type types-sros:description-or-empty;
                    description
                        "The version of the configuration file read when this CPM card was
                         last rebooted.";
                }

            } // container config-file

            list flash {
                key "flash-id";
                description "Enter the flash list instance";

                leaf flash-id {
                    type uint32 {
                        range "1..32";
                    }
                    description "The unique identifier index for a flash device on a CPM.";
                }

                leaf oper-state {
                    type types-system:device-state;
                    description "Current status of this flash unit on this CPM card.";
                }

                leaf serial-number {
                    type types-sros:description-or-empty;
                    description "The serial number for this flash unit on this CPM card.";
                }

                leaf firmware-revision {
                    type types-sros:description-or-empty;
                    description "The firmware revision number for this flash unit on this CPM card.";
                }

                leaf model-number {
                    type types-sros:description-or-empty;
                    description "The model number for this flash unit on this CPM card.";
                }

                leaf capacity {
                    type uint32;
                    units "kilobytes";
                    description "Indicates the maximum size of this flash unit.";
                }

                leaf free-space {
                    type uint32;
                    units "kilobytes";
                    description "Indicates the amount of free space remaining on this flash unit.";
                }

                leaf percent-used {
                    type uint32;
                    units "percent";
                    description
                        "Indicates the amount used for this flash unit as a percentage
                         of total capacity.";
                }

            } // list flash

            container hardware-data {
                description "Enter the hardware-data context";

                leaf part-number {
                    type string {
                        length "0..32";
                    }
                    description "Indicates the part number information.";
                }

                leaf serial-number {
                    type string {
                        length "0..32";
                    }
                    description "Indicates the serial number of the hardware component.";
                }

                leaf manufacturing-date {
                    type string {
                        length "0..8";
                    }
                    description "Indicates the manufacturing date of the hardware component.";
                }

                leaf common-language-equipment-identifier {
                    type string {
                        length "0..10";
                    }
                    description
                        "Indicates the CLEI, a unique 10-character identifier fixed
                         by the manufacturer.";
                }

                leaf field-replaceable-unit {
                    type boolean;
                    description
                        "Indicates whether the hardware component is a field
                         replaceable unit or not.";
                }

                leaf oper-state {
                    type enumeration {
                        enum "unknown"                      { value 1; }
                        enum "in-service"                   { value 2; }
                        enum "out-of-service"               { value 3; }
                        enum "diagnosing"                   { value 4; }
                        enum "failed"                       { value 5; }
                        enum "booting"                      { value 6; }
                        enum "empty"                        { value 7; }
                        enum "provisioned"                  { value 8; }
                        enum "unprovisioned"                { value 9; }
                        enum "upgrade"                      { value 10; }
                        enum "downgrade"                    { value 11; }
                        enum "in-service-upgrade"           { value 12; }
                        enum "in-service-downgrade"         { value 13; }
                        enum "reset-pending"                { value 14; }
                        enum "soft-reset"                   { value 15; }
                        enum "pre-extension"                { value 16; }
                        enum "downloading"                  { value 17; }
                    }
                    description "Indicates the operational status of the hardware component.";
                }

                leaf failure-reason {
                    type string {
                        length "0..255";
                    }
                    description
                        "Indicates the reason why a hardware component 'failed' as
                         indicated in oper-state.";
                }

                leaf contains-temperature-sensor {
                    type boolean;
                    description
                        "Indicates whether or not this hardware component contains
                         a temperature sensor.";
                }

                leaf temperature {
                    type int32;
                    description
                        "Indicates the current temperature in degrees celsius from
                         the temperature sensor.";
                }

                leaf temperature-threshold {
                    type int32;
                    description
                        "Indicates the temperature threshold for this hardware
                         component in degrees celsius.";
                }

                leaf alarm-state {
                    type enumeration {
                        enum "unknown"                      { value 0; }
                        enum "alarm-active"                 { value 1; }
                        enum "alarm-cleared"                { value 2; }
                    }
                    description
                        "Indicates the current alarm state for this hardware
                         component.";
                }

                leaf manufacturing-deviations {
                    type string {
                        length "0..255";
                    }
                    description
                        "Indicates the record of changes done by the manfacturing
                         to the hardware or software which is outside the normal
                         revision control process.";
                }

                leaf equipped-platform-type {
                    type enumeration {
                        enum "platform-unknown"             { value 0; }
                        enum "platform-7750"                { value 1; }
                        enum "platform-7450"                { value 2; }
                        enum "platform-7710"                { value 3; }
                        enum "platform-7950"                { value 4; }
                        enum "platform-7705"                { value 5; }
                        enum "platform-7250"                { value 6; }
                    }
                    description
                        "Indicates the platform type of the installed hardware
                         component, as read from the EEPROM.";
                }

                leaf manufacturing-assembly-number {
                    type string {
                        length "0..32";
                    }
                    description
                        "Indicates an assembly number indicating manufacturing
                         differences for a given part number.";
                }

                leaf base-mac-address {
                    type yang:mac-address;
                    description "Indicates the base MAC address of the hardware component.";
                }

                leaf boot-code-version {
                    type string {
                        length "0..255";
                    }
                    description "Indicates the version number of boot eprom.";
                }

                leaf software-code-version {
                    type string {
                        length "0..255";
                    }
                    description
                        "Indicates the software product release version number for the
                         software image currently running.";
                }

                leaf software-last-boot-time {
                    type yang:date-and-time;
                    description
                        "This indicates the date and time the software running on this
                         hardware component was last rebooted.";
                }

                leaf software-image-source {
                    type enumeration {
                        enum "unknown"                      { value 0; }
                        enum "primary"                      { value 1; }
                        enum "secondary"                    { value 2; }
                        enum "tertiary"                     { value 3; }
                    }
                    description
                        "Indicates the location in the Boot Options File (BOF)
                         where the software image file was found when the system last
                         rebooted.";
                }

                leaf firmware-code-version {
                    type string {
                        length "0..255";
                    }
                    description
                        "Indicates the software product release version number
                         associated with the firmware version currently programmed.";
                }

                leaf firmware-revision-status {
                    type enumeration {
                        enum "not-applicable"               { value 0; }
                        enum "acceptable"                   { value 1; }
                        enum "not-acceptable"               { value 2; }
                        enum "upgrade-pending"              { value 3; }
                        enum "upgrading"                    { value 4; }
                        enum "upgrade-next-hard-reset"      { value 5; }
                    }
                    description
                        "Indicates the firmware/FPGA revision status for the
                         hardware component.";
                }

            } // container hardware-data

            container statistics {
                description "Enter the statistics context";

                leaf buffer-memory-error {
                    type yang:counter32;
                    description
                        "Indicates the number of times the complex experienced a buffer
                         memory error since startup, last clear, or card reboot.";
                }

                leaf buffer-memory-error-time {
                    type yang:date-and-time;
                    description "Indicates the last time buffer-memory-error incremented.";
                }

                leaf cam-error {
                    type yang:counter32;
                    description
                        "Indicates the number of times the complex experienced a CAM
                         error since startup, last clear, or card reboot.";
                }

                leaf cam-error-time {
                    type yang:date-and-time;
                    description "Indicates the last time cam-error incremented.";
                }

                leaf egress-fcs-error {
                    type yang:counter32;
                    description
                        "Indicates the number of times the complex experienced a FCS
                         error in the egress direction since startup, last clear, or
                         card reboot.";
                }

                leaf egress-fcs-error-time {
                    type yang:date-and-time;
                    description "Indicates the last time egress-fcs-error incremented.";
                }

                leaf ingress-fcs-error {
                    type yang:counter32;
                    description
                        "Indicates the number of times the complex experienced a FCS
                         error in the ingress direction since startup, last clear,
                         or card reboot.";
                }

                leaf ingress-fcs-error-time {
                    type yang:date-and-time;
                    description "Indicates the last time ingress-fcs-error incremented.";
                }

                leaf internal-datapath-error {
                    type yang:counter32;
                    description
                        "Indicates the number of times the complex experienced an
                         internal datapath error since startup, last clear, or card
                         reboot.";
                }

                leaf internal-datapath-error-time {
                    type yang:date-and-time;
                    description "Indicates the last time internal-datapath-error incremented.";
                }

                leaf internal-datapath-cell-error {
                    type yang:counter32;
                    description
                        "Indicates the number of times the complex experienced an
                         internal datapath cell error since startup, last clear, or
                         card reboot.";
                }

                leaf internal-datapath-cell-error-time {
                    type yang:date-and-time;
                    description
                        "Indicates the last time internal-datapath-cell-error
                         incremented.";
                }

                leaf internal-memory-error {
                    type yang:counter32;
                    description
                        "Indicates the number of times the complex experienced an
                         internal memory error since startup, last clear, or card
                         reboot.";
                }

                leaf internal-memory-error-time {
                    type yang:date-and-time;
                    description "Indicates the last time internal-memory-error incremented.";
                }

                leaf memory-error {
                    type yang:counter32;
                    description
                        "Indicates the number of times the complex experienced a
                         memory error since startup, last clear, or card reboot.";
                }

                leaf memory-error-time {
                    type yang:date-and-time;
                    description "Indicates the last time memory-error incremented.";
                }

                leaf source-slots-egress-fcs-error {
                    type types-card:card-slot-bitmap;
                    description
                        "Indicates the source slots reported from the last time
                         egress-fcs-error incremented.";
                }

                leaf statistics-memory-error {
                    type yang:counter32;
                    description
                        "Indicates the number of times the complex experienced a
                         statistics memory error since startup, last clear, or card
                         reboot.";
                }

                leaf statistics-memory-error-time {
                    type yang:date-and-time;
                    description "Indicates the last time statistics-memory-error incremented.";
                }

            } // container statistics

            container virtual-machine {
                description "Enter the virtual-machine context";

                leaf hypervisor {
                    type types-sros:description-or-empty;
                    description "Indicates the name of the hypervisor.";
                }

                leaf cpu-description {
                    type types-sros:description-or-empty;
                    description "Indicates the description of the CPU.";
                }

                leaf number-of-cores {
                    type uint32;
                    description "Indicates the number of processor cores available.";
                }

            } // container virtual-machine

        } // list cpm

    } // grouping state-cpm

}
