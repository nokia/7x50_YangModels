submodule nokia-conf-port-eth-dot1x {

    yang-version "1.1";

    belongs-to nokia-conf { prefix "conf"; }

    import ietf-yang-types                { prefix "yang"; }
    import nokia-sros-yang-extensions     { prefix "sros-ext"; }
    import nokia-types-port               { prefix "types-port"; }
    import nokia-types-sros               { prefix "types-sros"; }

    include nokia-conf-aaa;
    include nokia-conf-groups;
    include nokia-conf-macsec;
    include nokia-conf-system;
    include nokia-conf-system-security;

    sros-ext:sros-major-release "rel20";

    organization "Nokia";

    contact
        "Nokia SR OS Support
         Web: <http://www.nokia.com>";

    description
        "Nokia YANG Data model to configure ethernet ports 802.1x authentication capabilities on SR OS based routers.

         Copyright 2016 Nokia. All rights reserved. Reproduction of this document
         is authorized on the condition that the foregoing copyright notice is included.

         This nokia-conf-port-eth-dot1x YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";

    revision "2020-08-21";

    grouping conf-port-eth-dot1x {
        container dot1x {
            description "Enter the dot1x context";

            leaf max-authentication-requests {
                type uint32 {
                    range "1..10";
                }
                default "2";
                description "Maximum number of times the router sends access request RADIUS message to RADIUS server";
            }

            leaf port-control {
                type types-port:pae-controlled-port-control;
                default "force-authorized";
                description "802.1x authentication mode";
            }

            leaf quiet-period {
                type uint32 {
                    range "1..3600";
                }
                units "seconds";
                default "60";
                description "Time between two authentication sessions during which no EAPOL frames are sent by router";
            }

            leaf radius-policy {
                type leafref {
                    path "../../../../system/security/dot1x/radius-policy/policy-name";
                }
                description "Authentication server policy";
            }

            leaf radius-server-policy {
                type leafref {
                    path "../../../../aaa/radius/server-policy/name";
                }
                description "Referenced RADIUS server policy";
            }

            leaf server-timeout {
                type uint32 {
                    range "1..300";
                }
                units "seconds";
                default "30";
                description "Time during which router waits for RADIUS server to respond to its access request message";
            }

            leaf supplicant-timeout {
                type uint32 {
                    range "1..300";
                }
                units "seconds";
                default "30";
                description "Time during which router waits for a client to respond to its EAPOL messages";
            }

            leaf transmit-period {
                type uint32 {
                    range "1..3600";
                }
                units "seconds";
                default "30";
                description "Time after which router sends a new EAPOL request message";
            }

            leaf tunneling {
                type boolean;
                default "false";
                description "Allow tunneling of untagged 802.1x frames received on a port";
            }

            leaf-list apply-groups {
                type leafref {
                    path "../../../../groups/group/name";
                }
                max-elements 8;
                ordered-by user;
                description "Apply a configuration group at this level";
            }

            container macsec {
                description "Enter the macsec context";

                leaf rx-must-be-encrypted {
                    type boolean;
                    default "false";
                    description "Drop all port traffic that is not MACsec-secured";
                }

                leaf exclude-mac-policy {
                    type leafref {
                        path "../../../../../macsec/mac-policy/mac-policy-id";
                    }
                    description "Configure the policy of mac addresses to be excluded.";
                }

                leaf-list apply-groups {
                    type leafref {
                        path "../../../../../groups/group/name";
                    }
                    max-elements 8;
                    ordered-by user;
                    description "Apply a configuration group at this level";
                }

                container exclude-protocol {
                    description "Enter the exclude-protocol context";

                    leaf cdp {
                        type boolean;
                        default "false";
                        description "Disable MACsec for all packets that are sent and received on the link for CDP (protocol)";
                    }

                    leaf eapol-start {
                        type boolean;
                        default "false";
                        description "Disable MACsec for all packets that are sent and received on the link for EAPOL (protocol)";
                    }

                    leaf lacp {
                        type boolean;
                        default "false";
                        description "Disable MACsec for all packets that are sent and received on the link for LACP (protocol)";
                    }

                    leaf lldp {
                        type boolean;
                        default "false";
                        description "Disable MACsec for all packets that are sent and received on the link for LLDP (protocol)";
                    }

                    leaf efm-oam {
                        type boolean;
                        default "false";
                        description "Disable MACsec for all packets that are sent and received on the link for EFM OAM (protocol)";
                    }

                    leaf eth-cfm {
                        type boolean;
                        default "false";
                        description "Disable MACsec for all packets that are sent and received on the link for ETH CFM (protocol)";
                    }

                    leaf ptp {
                        type boolean;
                        default "false";
                        description "Enable/disable PTP protocol.";
                    }

                    leaf ubfd {
                        type boolean;
                        default "false";
                        description "Enable/disable UBFD protocol.";
                    }

                } // container exclude-protocol

                list sub-port {
                    key "sub-port-id";
                    description "Enter the sub-port list instance";

                    leaf sub-port-id {
                        type uint32 {
                            range "1..1023";
                        }
                        description "Specifies the sub-port ID on the port.";
                    }

                    leaf admin-state {
                        type types-sros:admin-state;
                        default "disable";
                        description "Administrative state of MACsec on this port";
                    }

                    leaf ca-name {
                        type leafref {
                            path "../../../../../../macsec/connectivity-association/ca-name";
                        }
                        description "Configure the connectivity association to be used for this port.";
                    }

                    leaf eapol-destination-address {
                        type yang:mac-address;
                        description "Configure the eapol destination address.";
                    }

                    leaf max-peers {
                        type uint32 {
                            range "1..32";
                        }
                        sros-ext:auto-restart-to-modify;
                        description "Configure the max number of peers supported on this port.";
                    }

                    leaf-list apply-groups {
                        type leafref {
                            path "../../../../../../groups/group/name";
                        }
                        max-elements 8;
                        ordered-by user;
                        description "Apply a configuration group at this level";
                    }

                    container encap-match {
                        description "Enter the encap-match context";

                        choice encap {
                            default "all-match";
                            case all-match {

                                leaf all-match {
                                    type boolean;
                                    default "true";
                                    description "Configure encap match to all.";
                                }

                            }
                            case untagged {

                                leaf untagged {
                                    type boolean;
                                    description "Configure encap match to untagged.";
                                }

                            }
                            case single-tag {

                                leaf single-tag {
                                    type types-sros:single-vlan-encap;
                                    description "Configure encap match to single tag.";
                                }

                            }
                            case double-tag {

                                leaf double-tag {
                                    type types-sros:double-vlan-encap;
                                    description "Configure encap match to double-tag.";
                                }

                            }
                        }
                    } // container encap-match

                } // list sub-port

            } // container macsec

            container re-authentication {
                presence "Enter the 're-authentication' context";
                description "Enable the re-authentication context";

                leaf period {
                    type uint32 {
                        range "1..9000";
                    }
                    units "seconds";
                    default "3600";
                    description "Re-authentication period";
                }

            } // container re-authentication

            container per-host-authentication {
                presence "Enter the 'per-host-authentication' context";
                description "Enable the per-host-authentication context";

                container allowed-source-macs {
                    description "Enter the allowed-source-macs context";

                    list mac-address {
                        key "mac";
                        description "Add a list entry for mac-address";

                        leaf mac {
                            type yang:mac-address;
                            description "Source MAC address of a host selected for authentication";
                        }

                    } // list mac-address

                } // container allowed-source-macs

            } // container per-host-authentication

        } // container dot1x

    } // grouping conf-port-eth-dot1x

}
