module alu-conf-gmpls-tunnel-r13 {
  yang-version "1";

  namespace "urn:alcatel-lucent.com:sros:ns:yang:conf-gmpls-tunnel-r13";

  prefix "conf-gmpls-tunnel-r13";

  import alu-types {
    prefix "alu";
  }

  alu:alu-major-release "rel20";

  organization "Alcatel-Lucent";

  contact
      "Alcatel-Lucent SR OS Support 
       Web: <http://www.alcatel-lucent.com>";

  description
      "Alcatel-Lucent YANG Data model to configure GMPLS Tunnel Groups on SR OS based 
       routers. 
       
       Copyright 2014-2015 Alcatel-Lucent, 2016 Nokia. All rights reserved. 
       Reproduction of this document is authorized on the condition that the 
       foregoing copyright notice is included. 
       
       This alu-conf-gmpls-tunnel-r13 YANG module embodies Alcatel-Lucent's 
       proprietary intellectual property. Alcatel-Lucent retains all title and 
       ownership in the Specification, including any revisions. 
       
       Alcatel-Lucent grants all interested parties a non-exclusive license to use 
       and distribute an unmodified copy of this Specification in connection with 
       management of Alcatel-Lucent products, and without fee, provided this 
       copyright notice and license appear on all copies. 
       
       This Specification is supplied `as is', and Alcatel-Lucent makes no warranty, 
       either express or implied, as to the use, operation, condition, or performance 
       of the Specification.";

  revision  "2019-08-08";

  grouping alu-conf-gmpls-tunnel-r13 {
    list gmpls-tun-grp {
      key "gmpls-tunnel-group-id";
      description
          "Configure GMPLS Tunnel Groups";
      leaf gmpls-tunnel-group-id {
        type uint32 {
          range "1..1024";
        }
        description
            "Attribute gmpls-tunnel-group-id for gmpls-tun-grp";
      } //gmpls-tunnel-group-id

      container description {
        description
            "Configure the description of the GMPLS tunnel group";
        leaf long-description-string {
          type string {
            length "1..160";
          }
        } //long-description-string

      } //container description

      container far-end {
        description
            "Configure the far-end address of the GMPLS tunnel group";
        leaf ip-address {
          type string;
          description
              "Attribute ip-address for far-end";
        } //ip-address

      } //container far-end

      container member-threshold {
        description
            "Configure the minimum number of in-service members needed to declare the GMPLS 
             tunnel group in-service";
        leaf threshold {
          type uint32 {
            range "0..15";
          }
        } //threshold

      } //container member-threshold

      container mode {
        description
            "Configure the mode of the GMPLS tunnel group";
        leaf mode {
          type enumeration {
            enum active-standby;
            enum load-sharing;
          }
          description
              "Attribute mode for mode";
        } //mode

      } //container mode

      leaf shutdown {
        type boolean;
        description
            "Administratively enable/disable the GMPLS tunnel group";
      }

      container type {
        description
            "Configure the GMPLS tunnel group type";
        leaf head-end-tail-end {
          type enumeration {
            enum head-end;
            enum tail-end;
          }
          default "head-end";
          description
              "keywords - Default: head-end";
        } //head-end-tail-end

      } //container type

      list member {
        key "member-id";
        description
            "Configure member parameters";
        leaf member-id {
          type uint32 {
            range "1..16";
          }
        } //member-id

        container glsp {
          description
              "Configure the GMPLS LSP session name of the working path";
          leaf session-name {
            type string {
              length "1..80";
            }
          } //session-name

        } //container glsp

        leaf shutdown {
          type boolean;
          description
              "Administratively enable/disable the member";
        }

      } //list member

    } //list gmpls-tun-grp

  } //grouping alu-conf-gmpls-tunnel-r13

} //module  alu-conf-gmpls-tunnel-r13
