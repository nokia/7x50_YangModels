module alu-conf-router-if-r13 {
  yang-version "1";

  namespace "urn:alcatel-lucent.com:sros:ns:yang:conf-router-if-r13";

  prefix "conf-router-if-r13";

  import alu-conf-l3-nge-r13 {
    prefix "conf-l3-nge-r13";
  }
  import alu-types {
    prefix "alu";
  }
  import ietf-inet-types {
    prefix "inet";
  }
  import ietf-yang-types {
    prefix "yang";
  }

  alu:alu-major-release "rel20";

  organization "Alcatel-Lucent";

  contact
      "Alcatel-Lucent SR OS Support 
       Web: <http://www.alcatel-lucent.com>";

  description
      "Alcatel-Lucent YANG Data model to configure logical IP interfaces in the base 
       routing instance on SR OS based routers. 
       
       Copyright 2014-2015 Alcatel-Lucent, 2016 Nokia. All rights reserved. 
       Reproduction of this document is authorized on the condition that the 
       foregoing copyright notice is included. 
       
       This alu-conf-router-if-r13 YANG module embodies Alcatel-Lucent's proprietary 
       intellectual property. Alcatel-Lucent retains all title and ownership in the 
       Specification, including any revisions. 
       
       Alcatel-Lucent grants all interested parties a non-exclusive license to use 
       and distribute an unmodified copy of this Specification in connection with 
       management of Alcatel-Lucent products, and without fee, provided this 
       copyright notice and license appear on all copies. 
       
       This Specification is supplied `as is', and Alcatel-Lucent makes no warranty, 
       either express or implied, as to the use, operation, condition, or performance 
       of the Specification.";

  revision  "2020-06-10";

  grouping alu-conf-router-if-r13 {
    list interface {
      key "interface-name";
      description
          "Configure logical IP interfaces in the base routing instance";
      leaf interface-name {
        type string {
          length "1..32";
        }
        description
            "[32 chars max] (must start with a letter)";
      } //interface-name

      leaf unnumbered-mpls-tp {
        type boolean;
      } //unnumbered-mpls-tp

      leaf gmpls-loopback {
        type boolean;
      } //gmpls-loopback

      leaf control-tunnel {
        type boolean;
      } //control-tunnel

      leaf pdn {
        type boolean;
      } //pdn

      container accounting-policy {
        description
            "Configure the accounting policy which applies to the router interface";
        leaf policer-id {
          type uint32 {
            range "1..99";
          }
        } //policer-id

      } //container accounting-policy

      container address {
        description
            "Assigns an IP address/IP subnet/broadcast address format to the interface";
        leaf ip-address-mask {
          type string;
          description
              "ip-address a.b.c.d (no multicast/broadcast address) 
               mask [1..32]";
        } //ip-address-mask

        leaf netmask {
          type string;
          description
              "a.b.c.d (network bits all 1 and host bits all 0)";
        } //netmask

        leaf broadcast {
          type enumeration {
            enum all-ones;
            enum host-ones;
          }
          description
              "keywords";
        } //broadcast

        leaf track-srrp {
          type uint32 {
            range "1..4294967295";
          }
        } //track-srrp

        leaf gre-termination {
          type boolean;
        } //gre-termination

      } //container address

      leaf allow-directed-broadcasts {
        type boolean;
        description
            "Enable/disable forwarding of directed broadcasts on the interface";
      }

      leaf arp-learn-unsolicited {
        type boolean;
        description
            "Configure Arp unsolicited learning on the interface";
      }

      container arp-limit {
        description
            "Configures the maximum amount of IPv4 ARP entries";
        leaf limit {
          type int32 {
            range "0..524288";
          }
          description
              "[0..524288] entries - default = disabled";
        } //limit

        leaf log-only {
          type boolean;
        } //log-only

        leaf threshold {
          type uint32 {
            range "1..100";
          }
        } //threshold

      } //container arp-limit

      leaf arp-proactive-refresh {
        type boolean;
        description
            "Configure Arp Proactive Refresh";
      }

      container arp-retry-timer {
        description
            "Configures ARP retry interval on the interface";
        leaf t100s-of-milliseconds {
          type uint32 {
            range "1..300";
          }
          default 50;
          description
              "[1..300] Default: 50";
        } //t100s-of-milliseconds

      } //container arp-retry-timer

      container arp-timeout {
        description
            "Configures timeout for an ARP entry learned on the interface";
        leaf seconds {
          type uint32 {
            range "0..65535";
          }
          default 14400;
        } //seconds

      } //container arp-timeout

      container bfd {
        description
            "Configure BFD parameters";
        leaf transmit-interval {
          type uint32 {
            range "10..100000";
          }
          description
              "[10..100000] in milliseconds";
        } //transmit-interval

        leaf receive {
          type uint32 {
            range "10..100000";
          }
          description
              "[10..100000] in milliseconds";
        } //receive

        leaf multiplier {
          type string;
          description
              "Attribute multiplier for bfd";
        } //multiplier

        leaf echo-receive {
          type uint32 {
            range "100..100000";
          }
          description
              "[100..100000] in milliseconds";
        } //echo-receive

        leaf type {
          type enumeration {
            enum cpm-np;
            enum fp;
          }
          description
              "Attribute type for bfd";
        } //type

      } //container bfd

      leaf collect-stats {
        type boolean;
        description
            "Enable/disable the collection of statistical data";
      }

      container cpu-protection {
        description
            "Assign a CPU protection policy for the interface";
        leaf policy-id {
          type uint32 {
            range "1..255";
          }
          default 255;
          description
              "[1..255] - Default: 255";
        } //policy-id

      } //container cpu-protection

      container delayed-enable {
        status "obsolete";
        description
            "Delays making interface operational by the specified number of seconds";
        leaf seconds {
          type uint32 {
            range "1..65535";
          }
        } //seconds

        leaf init-only {
          type boolean;
        } //init-only

      } //container delayed-enable

      container description {
        description
            "Description for the interface";
        leaf long-description-string {
          type string {
            length "1..255";
          }
        } //long-description-string

      } //container description

      container dist-cpu-protection {
        description
            "Assign Distributed CPU protection policy for the interface";
        leaf policy-name {
          type string;
        } //policy-name

      } //container dist-cpu-protection

      leaf enable-ingress-stats {
        type boolean;
        description
            "Enable/disable the gathering of ingress interface statistics";
      }

      leaf enable-mac-accounting {
        type boolean;
        description
            "Configure MAC Accounting functionality for the interface.";
      }

      leaf gre-termination {
        type boolean;
        description
            "Enables GRE termination on this interface";
      }

      container ip-helper-address {
        description
            "Configure the gateway address to forward UDP traffic sent to the local 
             broadcast address on the interface";
        leaf gateway-address {
          type inet:ip-address;
          description
              "expressed in dotted decimal format (a.b.c.d)";
        } //gateway-address

      } //container ip-helper-address

      container ip-mtu {
        description
            "Configure the interface IP MTU";
        leaf octets {
          type string;
          description
              "Attribute octets for ip-mtu";
        } //octets

      } //container ip-mtu

      container lag-link-map-profile {
        description
            "Configure lag link profile";
        leaf link-map-profile-id {
          type string;
          description
              "Attribute link-map-profile-id for lag-link-map-profile";
        } //link-map-profile-id

      } //container lag-link-map-profile

      container lag-per-link-hash {
        description
            "Configure per-link-hash information";
        leaf class {
          type enumeration {
            enum 1;
            enum 2;
            enum 3;
          }
        } //class

        leaf weight {
          type uint32 {
            range "1..1024";
          }
        } //weight

      } //container lag-per-link-hash

      container ldp-sync-timer {
        description
            "Configure IGP-LDP synchronization timer";
        leaf seconds {
          type uint32 {
            range "1..1800";
          }
        } //seconds

        leaf end-of-lib {
          type boolean;
        } //end-of-lib

      } //container ldp-sync-timer

      container local-dhcp-server {
        description
            "Assign a DHCP server to the interface";
        leaf local-server-name {
          type string {
            length "1..32";
          }
        } //local-server-name

      } //container local-dhcp-server

      leaf local-proxy-arp {
        type boolean;
        description
            "Enable/disable local proxy ARP on the interface";
      }

      leaf loopback {
        type boolean;
        description
            "Configure the interface as a loopback interface";
      }

      container mac {
        description
            "Assign a MAC address to the interface";
        leaf ieee-address {
          type string;
          description
              "Attribute ieee-address for mac";
        } //ieee-address

      } //container mac

      list network-domain {
        key "network-domain-name";
        description
            "Add to a network-domain";
        leaf network-domain-name {
          type inet:domain-name;
        } //network-domain-name

      } //list network-domain

      leaf ntp-broadcast {
        type boolean;
        status "obsolete";
        description
            "Enable/disable receiving of NTP/SNTP broadcasts on the interface";
      }

      container port {
        description
            "Bind the interface to a physical port";
        leaf port-name {
          type string {
            length "1..64";
          }
          description
              "<port-id>[:encap-val] 
               encap-val - 0 for null 
               - [0..4094] for dot1q 
               - [0..4094].* or 
               [1..4094].[0..4094] for qinq 
               ";
        } //port-name

        leaf port-id {
          type string {
            length "1..64";
          }
          description
              "Attribute port-id for port";
        } //port-id

      } //container port

      container proxy-arp-policy {
        description
            "Configure a proxy ARP policy for the interface";
        leaf-list policy-name {
          type string {
            length "1..32";
          }
          max-elements 5;
          description
              "[32 chars max]";
        } //policy-name

      } //container proxy-arp-policy

      leaf ptp-hw-assist {
        type boolean;
        description
            "Enable/Disable time stamping Precision Timing Protocol (PTP) packets at the 
             physical interface.";
      }

      container qos {
        description
            "Associate a network Quality of Service (QoS) policy with the interface";
        leaf network-policy-id {
          type uint32 {
            range "1..65535";
          }
        } //network-policy-id

        leaf queue-redirect-group {
          type string {
            length "1..32";
          }
          status "obsolete";
        } //queue-redirect-group

        leaf egress-port-redirect-group {
          type string {
            length "1..32";
          }
        } //egress-port-redirect-group

        leaf egress-instance {
          type uint16 {
            range "1..65535";
          }
        } //egress-instance

        leaf ingress-fp-redirect-group {
          type string {
            length "1..32";
          }
          description
              "queue-group-name";
        } //ingress-fp-redirect-group

        leaf ingress-instance {
          type uint16 {
            range "1..65535";
          }
          description
              "instance-id";
        } //ingress-instance

      } //container qos

      container qos-route-lookup {
        description
            "Configure Qos route lookup for the interface";
        leaf source-destination {
          type enumeration {
            enum source;
            enum destination;
          }
        } //source-destination

      } //container qos-route-lookup

      leaf remote-proxy-arp {
        type boolean;
        description
            "Enable/disable remote proxy ARP on the interface";
      }

      list secondary {
        key "ip-address-mask netmask";
        description
            "Assigns a secondary IP address/IP subnet/broadcast address format to the 
             interface";
        leaf ip-address-mask {
          type string;
          description
              "ip-address a.b.c.d 
               mask [0..32]";
        } //ip-address-mask

        leaf netmask {
          type string;
          description
              "a.b.c.d (network bits all 1 and host bits all 0)";
        } //netmask

        leaf broadcast {
          type enumeration {
            enum all-ones;
            enum host-ones;
          }
          description
              "keywords";
        } //broadcast

        leaf igp-inhibit {
          type boolean;
          description
              "secondary ip-address should not be recognized as a local interface by the 
               running IGP";
        } //igp-inhibit

        leaf track-srrp {
          type uint32 {
            range "1..4294967295";
          }
        } //track-srrp

      } //list secondary

      leaf shutdown {
        type boolean;
        description
            "Administratively enable/disable the interface";
      }

      container static-arp {
        description
            "Configure a static ARP entry for the interface";
        leaf ip-address {
          type inet:ip-address;
        } //ip-address

        leaf ieee-address {
          type string;
          description
              "xx:xx:xx:xx:xx:xx or xx-xx-xx-xx-xx-xx";
        } //ieee-address

        leaf unnumbered {
          type boolean;
        } //unnumbered

      } //container static-arp

      leaf strip-label {
        type boolean;
        description
            "Enable/disable strip-label on the interface";
      }

      container tcp-mss {
        description
            "Configure TCP maximum segment size for the interface";
        leaf mss-value {
          type string;
          description
              "Attribute mss-value for tcp-mss";
        } //mss-value

      } //container tcp-mss

      container tos-marking-state {
        description
            "Specify TOS marking state";
        leaf trusted-untrusted {
          type enumeration {
            enum trusted;
            enum untrusted;
          }
          description
              "keywords";
        } //trusted-untrusted

      } //container tos-marking-state

      container unnumbered {
        description
            "Configure the interface as an unnumbered interface";
        leaf ip-int-name-ip-address {
          type string;
          description
              "Attribute ip-int-name|ip-address for unnumbered";
        } //ip-int-name-ip-address

      } //container unnumbered

      container untrusted {
        description
            "Configure the interface as an untrusted interface";
        leaf default-forwarding {
          type enumeration {
            enum forward;
            enum drop;
          }
        } //default-forwarding

      } //container untrusted

      leaf urpf-selected-vprns {
        type boolean;
        description
            "Enable/disable per-VPRN selective URPF treatment. This applies to packets 
             associated with a VPRN";
      }

      container vas-if-type {
        description
            "Specifies VAS interface type";
        leaf vas-if-type-id {
          type enumeration {
            enum to-from-access;
            enum to-from-network;
            enum to-from-both;
          }
        } //vas-if-type-id

      } //container vas-if-type

      container autoconfigure {
        description
            "Configure autoconfiguration";
        container dhcp-client {
          presence
              "Configure DHCP client parameters";
          container class-id {
            description
                "Configure the vendor class identifier";
            leaf hex {
              type string {
              }
              description
                  "[0x0..0xFFFFFFFF...(max 254 hex nibbles)]";
            } //hex

            leaf string {
              type string {
                length "1..127";
              }
            } //string

          } //container class-id

          container client-id {
            description
                "Configure the client-identifier";
            leaf use-mac {
              type boolean;
              description
                  "keyword - use the MAC as client-identifier";
            } //use-mac

            leaf interface {
              type boolean;
              description
                  "keyword - use the interface name as client-identifier";
            } //interface

            leaf string {
              type string {
                length "1..127";
              }
            } //string

            leaf hex {
              type string {
              }
              description
                  "[0x0..0xFFFFFFFF...(max 254 hex nibbles)]";
            } //hex

          } //container client-id

          container lease-time {
            description
                "Configure the lease time";
            leaf days {
              type int32 {
                range "0..3650";
              }
            } //days

            leaf hrs {
              type int32 {
                range "0..23";
              }
            } //hrs

            leaf min {
              type int32 {
                range "0..59";
              }
            } //min

            leaf sec {
              type int32 {
                range "0..59";
              }
            } //sec

            leaf infinite {
              type boolean;
              description
                  "keyword - lease never expires";
            } //infinite

          } //container lease-time

          leaf shutdown {
            type boolean;
            description
                "Administratively disable or enable the DHCP client";
          }

          container request-options {
            description
                "Configure the DHCP options for the request messages sent to the server";
            leaf dns-server {
              type boolean;
              description
                  "Request the dns server option";
            }

            leaf router {
              type boolean;
              description
                  "Request the router option";
            }

            leaf static-route {
              type boolean;
              description
                  "Request the static route option";
            }

          } //container request-options

        } //container dhcp-client

      } //container autoconfigure

      container cflowd-parameters {
        description
            "Configure Cflowd parameters on the interface";
        list sampling {
          key "sampling-id";
          description
              "Configure the Cflowd sampling parameters";
          leaf sampling-id {
            type enumeration {
              enum unicast;
              enum multicast;
              enum both;
            }
          } //sampling-id

          leaf type {
            type enumeration {
              enum acl;
              enum interface;
            }
          } //type

          leaf direction {
            type enumeration {
              enum ingress-only;
              enum egress-only;
              enum both;
            }
            default "ingress-only";
            description
                "keywords - Default: ingress-only";
          } //direction

          leaf sample-profile {
            type uint32 {
              range "1..5";
            }
            default 1;
          } //sample-profile

        } //list sampling

      } //container cflowd-parameters

      container dhcp {
        description
            "Configure DHCP parameters";
        container description {
          description
              "Add/remove a text description for DHCP";
          leaf description-string {
            type string {
              length "1..80";
            }
          } //description-string

        } //container description

        container gi-address {
          description
              "Configure the gateway interface address for the DHCP relay";
          leaf ip-address {
            type inet:ip-address;
          } //ip-address

          leaf src-ip-addr {
            type boolean;
            description
                "keyword - use the gi-address as src-ip";
          } //src-ip-addr

        } //container gi-address

        container python-policy {
          description
              "Configure the Python policy";
          leaf python-policy-string {
            type string {
            }
          } //python-policy-string

        } //container python-policy

        leaf relay-plain-bootp {
          type boolean;
          description
              "Enable/disable relaying of plain BOOTP packets";
        }

        container server {
          description
              "Configure the DHCP server IP address";
          leaf-list server-ip-address {
            type inet:ip-address;
            max-elements 8;
            description
                "DHCP server IP address";
          } //server-ip-address

        } //container server

        leaf shutdown {
          type boolean;
          description
              "Administratively enable/disable DHCP on this interface";
        }

        leaf trusted {
          type boolean;
          description
              "Enable/disable relaying of untrusted packets";
        }

        container option {
          presence
              "Configure the DHCP Relay information options";
          container action {
            description
                "Configure the DHCP Relay reforwarding policy action";
            leaf replace-drop-keep {
              type enumeration {
                enum replace;
                enum drop;
                enum keep;
              }
              description
                  "keywords";
            } //replace-drop-keep

          } //container action

          container circuit-id {
            description
                "Configure the circuit-id suboption of the DHCP Relay packet";
            leaf circuit-id-id {
              type enumeration {
                enum ascii-tuple;
                enum ifindex;
                enum if-name;
                enum port-id;
                enum vlan-ascii-tuple;
                enum none;
              }
            } //circuit-id-id

          } //container circuit-id

          container remote-id {
            description
                "Configure the remote-id suboption of the DHCP Relay packet";
            leaf mac {
              type boolean;
            } //mac

            leaf string {
              type string {
                length "1..32";
              }
              description
                  "Max 32 chars";
            } //string

          } //container remote-id

          container vendor-specific-option {
            presence
                "Configure the Nokia vendor specific suboption of the DHCP Relay packet";
            leaf client-mac-address {
              type boolean;
              description
                  "Enable/disable sending of the MAC address in the Nokia vendor specific 
                   suboption of the DHCP Relay packet";
            }

            leaf pool-name {
              type boolean;
              description
                  "Enable/disable sending of the pool name in the Nokia vendor specific suboption 
                   of the DHCP Relay packet";
            }

            leaf port-id {
              type boolean;
              description
                  "Enable/disable sending of the PORT-id in the Nokia vendor specific suboption 
                   of the DHCP Relay packet";
            }

            leaf service-id {
              type boolean;
              description
                  "Enable/disable sending of the service-id in the Nokia vendor specific 
                   suboption of the DHCP Relay packet";
            }

            container string {
              description
                  "Specifies the string in the Nokia vendor specific suboption of the DHCP Relay 
                   packet";
              leaf string-string {
                type string {
                  length "1..32";
                }
              } //string-string

            } //container string

            leaf system-id {
              type boolean;
              description
                  "Enable/disable sending of the system-id in the Nokia vendor specific suboption 
                   of the DHCP Relay packet";
            }

          } //container vendor-specific-option

        } //container option

      } //container dhcp

      container egress {
        description
            "Configure egress network filter policies for the interface.";
        container egress-remark-policy {
          description
              "Specify an egress-remark-policy";
          leaf egress-remark-policy-name {
            type string {
              length "1..64";
            }
          } //egress-remark-policy-name

        } //container egress-remark-policy

        container filter {
          description
              "IP filter policy associated with the interface";
          leaf ip {
            type string;
            description
                "[1..65535]|<name:64 char max>";
          } //ip

          leaf ipv6 {
            type string;
            description
                "[1..65535]|<name:64 char max>";
          } //ipv6

        } //container filter

        container vlan-qos-policy {
          description
              "Specify a vlan-qos-policy";
          leaf name {
            type string;
          } //name

        } //container vlan-qos-policy

        container agg-rate {
          description
              "Configure aggregate rate limit";
          container rate {
            description
                "Specify rate limit for agg-rate";
            leaf pir-kilobits-per-second {
              type string;
              description
                  "[1..100000000|max] Kbps";
            } //pir-kilobits-per-second

            leaf cir {
              type string;
              description
                  "[0..100000000|max] Kbps";
            } //cir

          } //container rate

        } //container agg-rate

      } //container egress

      container eth-cfm {
        description
            "Configure CFM parameters";
        list mep {
          key "mep-id domain association";
          description
              "Configure a CFM Facility Maintenance Endpoint";
          leaf mep-id {
            type int16 {
              range "1..8191";
            }
          } //mep-id

          leaf domain {
            type uint32 {
              range "1..4294967295";
            }
          } //domain

          leaf association {
            type uint32 {
              range "1..4294967295";
            }
          } //association

          leaf ccm-enable {
            type boolean;
            description
                "Enable/Disable Generation of CCM messages";
          }

          container ccm-ltm-priority {
            description
                "Configure the priority of CCM and LTM messages";
            leaf priority {
              type uint16 {
                range "0..7";
              }
              description
                  "[0..7] - Default highest priority for CCMs and LTMs transmitted by the MEP";
            } //priority

          } //container ccm-ltm-priority

          container ccm-padding-size {
            description
                "Insert additional padding in the CCM packets";
            leaf ccm-padding {
              type uint32 {
                range "3..1500";
              }
              description
                  "3..1500 octets";
            } //ccm-padding

          } //container ccm-padding-size

          container ccm-tlv-ignore {
            description
                "Enable/Disable processing of received CCM TLVs";
            leaf port-status {
              type boolean;
            } //port-status

            leaf interface-status {
              type boolean;
            } //interface-status

          } //container ccm-tlv-ignore

          leaf collect-lmm-stats {
            type boolean;
            description
                "Enable/Disable the collection of statistics for OAM-PM Loss Measurement 
                 Message (LMM) tests";
          }

          container description {
            description
                "Add/remove a text description for the MEP";
            leaf description-string {
              type string {
              }
              description
                  "[80 chars max]";
            } //description-string

          } //container description

          leaf facility-fault {
            type boolean;
            description
                "Enable/disable reaction to fault conditions on a facility MEP";
          }

          leaf lbm-svc-act-responder {
            type boolean;
            description
                "Enable/Disable processing of service activation streams that may be 
                 encapsulated in the ETH-CFM request Loopback Message (LBM) on the MEP";
          }

          container low-priority-defect {
            description
                "Configure the Lowest Priority Defect for the MEP";
            leaf allDef-macRemErrXcon-remErrXcon-errXcon-xcon-noXcon {
              type enumeration {
                enum allDef;
                enum macRemErrXcon;
                enum remErrXcon;
                enum errXcon;
                enum xcon;
                enum noXcon;
              }
              description
                  "keywords";
            } //allDef-macRemErrXcon-remErrXcon-errXcon-xcon-noXcon

          } //container low-priority-defect

          container mac-address {
            description
                "Configure the MAC Address for the MEP";
            leaf mac-address {
              type yang:mac-address;
            } //mac-address

          } //container mac-address

          container one-way-delay-threshold {
            description
                "Configure the one-way-delay test threshold";
            leaf seconds {
              type uint32 {
                range "0..600";
              }
              default 3;
              description
                  "[0..600] Default: 3";
            } //seconds

          } //container one-way-delay-threshold

          leaf shutdown {
            type boolean;
            description
                "Administratively enable/disable the MEP";
          }

          container alarm-notification {
            description
                "Configure the MEP alarm notification parameters";
            container fng-alarm-time {
              description
                  "Configure the Fault Notification Generation (FNG) alarm time";
              leaf time {
                type enumeration {
                  enum 0;
                  enum 250;
                  enum 500;
                  enum 1000;
                }
                default 0;
                description
                    "[0,250,500,1000] centi-seconds - Default: 0";
              } //time

            } //container fng-alarm-time

            container fng-reset-time {
              description
                  "Configure the Fault Notification Generation (FNG) reset time";
              leaf time {
                type enumeration {
                  enum 0;
                  enum 250;
                  enum 500;
                  enum 1000;
                }
                default 0;
                description
                    "[0,250,500,1000] centi-seconds - Default: 0";
              } //time

            } //container fng-reset-time

          } //container alarm-notification

          container collect-lmm-fc-stats {
            description
                "Configure the collection of Forwarding Class (FC) aware statistics for OAM-PM 
                 Loss Measurement Message (LMM) tests";
            container fc {
              description
                  "Configure Forwarding Class (FC) counters without regard for profile";
              leaf-list fc-name {
                type enumeration {
                  enum be;
                  enum l2;
                  enum af;
                  enum l1;
                  enum h2;
                  enum ef;
                  enum h1;
                  enum nc;
                }
                max-elements 8;
              } //fc-name

            } //container fc

            container fc-in-profile {
              description
                  "Configure only in profile Forwarding Class (FC) counters";
              leaf-list fc-name {
                type enumeration {
                  enum be;
                  enum l2;
                  enum af;
                  enum l1;
                  enum h2;
                  enum ef;
                  enum h1;
                  enum nc;
                }
                max-elements 8;
              } //fc-name

            } //container fc-in-profile

          } //container collect-lmm-fc-stats

          container eth-test-enable {
            presence
                "Enable/Disable eth-test functionality on MEP";
            container bit-error-threshold {
              description
                  "Configure the bit error trap threshold";
              leaf bit-errors {
                type uint32 {
                  range "0..11840";
                }
                default 1;
                description
                    "[0..11840] Default: 1";
              } //bit-errors

            } //container bit-error-threshold

            container test-pattern {
              description
                  "Configure the test pattern for eth-test frames";
              leaf all-zeros-all-ones {
                type enumeration {
                  enum all-zeros;
                  enum all-ones;
                }
                default "all-zeros";
                description
                    "keywords - Test pattern - default: all-zeros";
              } //all-zeros-all-ones

              leaf crc-enable {
                type boolean;
                description
                    "keyword - Generate CRC checksum";
              } //crc-enable

            } //container test-pattern

          } //container eth-test-enable

          container grace {
            description
                "Configure the generation and reception of grace period parameters";
            container eth-ed {
              description
                  "Configure the generation and reception of eth-ed grace period parameters";
              container max-rx-defect-window {
                description
                    "Configure/Disable an upper maximum defect window length; when disabled the 
                     advertised value from the peer will be used; when enabled the lower of the 
                     configured value or the advertised value from the peer will be used";
                leaf seconds {
                  type uint32 {
                    range "1..86400";
                  }
                  description
                      "[1..86400] - Default: no max-rx-defect-window";
                } //seconds

              } //container max-rx-defect-window

              container priority {
                description
                    "Configure/Disable the transmission priority value for ETH-ED PDUs; when 
                     disabled the priority value of ccm-ltm-priority associated with this MEP will 
                     be used";
                leaf priority {
                  type int32 {
                    range "0..7";
                  }
                  default 0;
                  description
                      "[0..7] - Default: no priority";
                } //priority

              } //container priority

              leaf rx-eth-ed {
                type boolean;
                description
                    "Enable/Disable the receiving and processing of ETH-ED PDUs";
              }

              leaf tx-eth-ed {
                type boolean;
                description
                    "Enable/Disable the transmission of ETH-ED PDUs";
              }

            } //container eth-ed

            container eth-vsm-grace {
              description
                  "Configure the generation and reception of sros vendor specific message (vsm) 
                   grace period parameters";
              leaf rx-eth-vsm-grace {
                type boolean;
                description
                    "Enable/Disable the receiving and processing of vendor specific message (vsm) 
                     grace period notifications";
              }

              leaf tx-eth-vsm-grace {
                type boolean;
                description
                    "Enable/Disable the transmission of vsm grace period notifications";
              }

            } //container eth-vsm-grace

          } //container grace

        } //list mep

      } //container eth-cfm

      uses "conf-l3-nge-r13:alu-conf-l3-nge-r13";
      container hold-time {
        description
            "Configure the hold times (up/down) for the interface";
        container down {
          description
              "Configure the hold time when the interface is coming up";
          leaf ip {
            type boolean;
          } //ip

          leaf ipv6 {
            type boolean;
          } //ipv6

          leaf seconds {
            type uint32 {
              range "1..1200";
            }
          } //seconds

          leaf init-only {
            type boolean;
          } //init-only

        } //container down

        container up {
          description
              "Configure the hold time when the interface is going down";
          leaf ip {
            type boolean;
          } //ip

          leaf ipv6 {
            type boolean;
          } //ipv6

          leaf seconds {
            type uint32 {
              range "1..1200";
            }
          } //seconds

        } //container up

      } //container hold-time

      container icmp {
        description
            "Configure ICMP parameters for the interface";
        leaf mask-reply {
          type boolean;
          description
              "Enable/disable responses to ICMP mask requests";
        }

        container param-problem {
          description
              "Configures rate for ICMP param-problem messages";
          leaf-list number-seconds {
            type uint16 {
              range "1..1000";
            }
            max-elements 2;
            description
                "number [10..1000] 
                 seconds [1..60]";
          } //number-seconds

        } //container param-problem

        container redirects {
          description
              "Configures rate for ICMP redirect messages";
          leaf-list number-seconds {
            type uint16 {
              range "1..1000";
            }
            max-elements 2;
            description
                "number [10..1000] 
                 seconds [1..60]";
          } //number-seconds

        } //container redirects

        container ttl-expired {
          description
              "Configures rate for ICMP TTL expired messages";
          leaf-list number-seconds {
            type uint16 {
              range "1..2000";
            }
            max-elements 2;
            description
                "number [10..2000] 
                 seconds [1..60]";
          } //number-seconds

        } //container ttl-expired

        container unreachables {
          description
              "Configures rate for ICMP unreachable messages";
          leaf-list number-seconds {
            type uint16 {
              range "1..2000";
            }
            max-elements 2;
            description
                "number [10..2000] 
                 seconds [1..60]";
          } //number-seconds

        } //container unreachables

      } //container icmp

      container if-attribute {
        description
            "Add/Remove interface attributes";
        container admin-group {
          description
              "Configure interface Admin Group memberships for this interface";
          leaf-list group-name {
            type string {
              length "1..32";
            }
            max-elements 5;
          } //group-name

        } //container admin-group

        container srlg-group {
          description
              "Configure interface SRLG Group memberships for this interface";
          leaf-list group-name {
            type string {
              length "1..32";
            }
            max-elements 5;
          } //group-name

        } //container srlg-group

        container delay {
          description
              "Configure uni-directional link-delay";
          container static {
            description
                "Configure static uni-directional link-delay";
            leaf microseconds {
              type int32 {
                range "1..16777214";
              }
            } //microseconds

          } //container static

        } //container delay

      } //container if-attribute

      container ingress {
        description
            "Configure ingress network filter policies for the interface.";
        leaf destination-class-lookup {
          type boolean;
          description
              "Enable/disable destination class lookup for egress filtering";
        }

        container filter {
          description
              "IP filter policy associated with the interface";
          leaf ip {
            type string;
            description
                "[1..65535]|<name:64 char max>";
          } //ip

          leaf ipv6 {
            type string;
            description
                "[1..65535]|<name:64 char max>";
          } //ipv6

        } //container filter

        leaf flowspec {
          type boolean;
          status "obsolete";
          description
              "Enable/disable IPv4 Flowspec on the interface";
        }

        leaf flowspec-ipv6 {
          type boolean;
          status "obsolete";
          description
              "Enable/disable IPv6 Flowspec on the interface";
        }

        container policy-accounting {
          description
              "Enable/Disable policy accounting template";
          leaf template-name {
            type string {
              length "1..32";
            }
          } //template-name

        } //container policy-accounting

        container qos {
          description
              "Specify a network ingress policy";
          leaf network-ingress-qos-policy-name {
            type string {
              length "1..64";
            }
          } //network-ingress-qos-policy-name

        } //container qos

      } //container ingress

      container ip-tunnel {
        description
            "Configure the IP tunnel";
        container remote-ip {
          description
              "Configure the IP address of the remote end of the IP tunnel";
          leaf ip-address {
            type inet:ip-address;
            description
                "a.b.c.d";
          } //ip-address

        } //container remote-ip

      } //container ip-tunnel

      container ipsec {
        description
            "Configure IPsec information";
        leaf tunnel-group {
          type uint32 {
            range "1..16";
          }
        } //tunnel-group

        leaf public-sap {
          type uint32 {
            range "0..4094";
          }
        } //public-sap

        container ip-exception {
          description
              "IP filter policy which will be used to bypass encryption";
          leaf filter-id {
            type string;
            description
                "[1..65535]|<name:64 char max>";
          } //filter-id

        } //container ip-exception

        container ipv6-exception {
          description
              "IPv6 filter policy which will be used to bypass encryption";
          leaf exception {
            type string;
            description
                "Attribute exception for ipv6-exception";
          } //exception

        } //container ipv6-exception

        leaf shutdown {
          type boolean;
          description
              "Administratively enable/disable the IPsec";
        }

        list ipsec-tunnel {
          key "name";
          description
              "Configure IPsec tunnel";
          leaf name {
            type string;
          } //name

          leaf private-sap {
            type uint32 {
              range "0..4094";
            }
          } //private-sap

          leaf private-service-name {
            type string;
          } //private-service-name

          leaf bfd-designate {
            type boolean;
            description
                "Configure BFD designation for the tunnel";
          }

          container bfd-enable {
            description
                "Configure BFD parameter";
            leaf service-name {
              type string;
            } //service-name

            leaf interface-name {
              type string {
                length "1..32";
              }
            } //interface-name

            leaf dst-ip {
              type inet:ip-address;
            } //dst-ip

          } //container bfd-enable

          leaf clear-df-bit {
            type boolean;
            description
                "Enable/disable clearing of Do-not-Fragment bit";
          }

          container description {
            description
                "Configure IPsec tunnel description";
            leaf description-string {
              type string {
                length "1..80";
              }
            } //description-string

          } //container description

          container encapsulated-ip-mtu {
            description
                "Configure the interface encapsulated IP MTU";
            leaf bytes {
              type uint32 {
                range "512..9000";
              }
            } //bytes

          } //container encapsulated-ip-mtu

          container ip-mtu {
            description
                "Configure the interface IP MTU";
            leaf bytes {
              type uint32 {
                range "512..9000";
              }
            } //bytes

          } //container ip-mtu

          container local-gateway-address {
            description
                "Configure local gateway address";
            leaf ip-address-ipv6-address {
              type string;
            } //ip-address-ipv6-address

          } //container local-gateway-address

          container max-history-esp-key-records {
            description
                "Configure the maximum number of historical ESP keys which can be recorded by 
                 the system";
            leaf max-history-esp-key-records-id {
              type uint32 {
                range "1..48";
              }
            } //max-history-esp-key-records-id

          } //container max-history-esp-key-records

          container max-history-ike-key-records {
            description
                "Configure the maximum number of historical IKE keys which can be recorded by 
                 the system";
            leaf max-history-ike-key-records-id {
              type uint32 {
                range "1..3";
              }
            } //max-history-ike-key-records-id

          } //container max-history-ike-key-records

          container private-tcp-mss-adjust {
            description
                "Configure the TCP MSS on private network";
            leaf bytes {
              type uint32 {
                range "512..9000";
              }
            } //bytes

          } //container private-tcp-mss-adjust

          container public-tcp-mss-adjust {
            description
                "Configure the TCP MSS on public network";
            leaf public-tcp-mss-adjust-id {
              type uint32 {
                range "512..9000";
              }
            } //public-tcp-mss-adjust-id

            leaf auto {
              type boolean;
            } //auto

          } //container public-tcp-mss-adjust

          container remote-gateway-address {
            description
                "Configure remote gateway address";
            leaf ip-address-ipv6-address {
              type string;
            } //ip-address-ipv6-address

          } //container remote-gateway-address

          container replay-window {
            description
                "Configure Anti replay window for the tunnel";
            leaf replay-window-size {
              type enumeration {
                enum 32;
                enum 64;
                enum 128;
                enum 256;
                enum 512;
              }
            } //replay-window-size

          } //container replay-window

          container security-policy {
            description
                "Configure security policy id for the tunnel";
            leaf security-policy-id {
              type uint32 {
                range "1..32768";
              }
            } //security-policy-id

            leaf strict-match {
              type boolean;
            } //strict-match

          } //container security-policy

          leaf shutdown {
            type boolean;
            description
                "Administratively enable/disable the IPsec tunnel";
          }

          container dynamic-keying {
            presence
                "Configure dynamic keying for the IPsec tunnel";
            leaf auto-establish {
              type boolean;
              description
                  "Enable/Disable auto-establish";
            }

            container ike-policy {
              description
                  "Configure IKE policy for the dynamic keying";
              leaf ike-policy-id {
                type uint32 {
                  range "1..2048";
                }
              } //ike-policy-id

            } //container ike-policy

            container local-id {
              description
                  "Configure local ID type for dynamic keying";
              leaf type {
                type enumeration {
                  enum ;
                  enum ipv4;
                  enum fqdn;
                  enum ipv6;
                }
              } //type

              leaf value {
                type string {
                  length "1..255";
                }
              } //value

            } //container local-id

            container pre-shared-key {
              description
                  "Configure key for dynamic keying";
              leaf key {
                type string {
                  length "1..500";
                }
                description
                    "64 chars max";
              } //key

              leaf hash-hash2-custom {
                type enumeration {
                  enum hash;
                  enum hash2;
                  enum custom;
                }
              } //hash-hash2-custom

            } //container pre-shared-key

            container transform {
              description
                  "Configure IPsec transforms for dynamic keying";
              leaf-list transform-id {
                type uint32 {
                  range "1..2048";
                }
                max-elements 4;
              } //transform-id

            } //container transform

            container cert {
              description
                  "Configure certificate parameters";
              container cert-profile {
                description
                    "Configure certificate profile name";
                leaf name {
                  type string;
                } //name

              } //container cert-profile

              container trust-anchor-profile {
                description
                    "Configure Trust Anchor profile";
                leaf name {
                  type string;
                } //name

              } //container trust-anchor-profile

              container status-verify {
                description
                    "Configure certificate status verification parameters";
                container default-result {
                  description
                      "Configure default result of certificate status verification";
                  leaf revoked-good {
                    type enumeration {
                      enum revoked;
                      enum good;
                    }
                  } //revoked-good

                } //container default-result

                container primary {
                  description
                      "Configure primary and secondary certificate status verification methods";
                  leaf primary {
                    type enumeration {
                      enum ocsp;
                      enum crl;
                    }
                    default "crl";
                    description
                        "ocsp|crl - default: crl";
                  } //primary

                  leaf secondary {
                    type enumeration {
                      enum ocsp;
                      enum crl;
                      enum none;
                    }
                    default "none";
                    description
                        "ocsp|crl|none - default: none";
                  } //secondary

                } //container primary

              } //container status-verify

            } //container cert

          } //container dynamic-keying

          container icmp6-generation {
            description
                "Configure ICMPv6 generation information";
            container pkt-too-big {
              presence
                  "Enable/disable the generation of the ICMPv6 packet too big messages";
              container interval {
                description
                    "Configure the maximum interval that the ICMPv6 messages can be sent";
                leaf seconds {
                  type uint32 {
                    range "1..60";
                  }
                  default 10;
                  description
                      "[1..60] - Default: 10";
                } //seconds

              } //container interval

              container message-count {
                description
                    "Configure the maximum number of ICMPv6 messages that can be sent during the 
                     period specified by 'interval'";
                leaf count {
                  type uint32 {
                    range "10..1000";
                  }
                  default 100;
                  description
                      "[10..1000] - Default: 100";
                } //count

              } //container message-count

            } //container pkt-too-big

          } //container icmp6-generation

          container manual-keying {
            presence
                "Configure manual keying for the IPsec tunnel";
            list security-association {
              key "security-association-id direction";
              description
                  "Configure Security Association for manual keying";
              leaf security-association-id {
                type uint32 {
                  range "1..16";
                }
              } //security-association-id

              leaf authentication-key {
                type string;
                description
                    "none or [0x0..0xFFFFFFFF...(max 128 hex nibbles)]";
              } //authentication-key

              leaf encryption-key {
                type string;
                description
                    "none or [0x0..0xFFFFFFFF...(max 64 hex nibbles)]";
              } //encryption-key

              leaf spi {
                type uint32 {
                  range "256..16383";
                }
              } //spi

              leaf transform-id {
                type uint32 {
                  range "1..2048";
                }
              } //transform-id

              leaf direction {
                type enumeration {
                  enum inbound;
                  enum outbound;
                }
              } //direction

            } //list security-association

          } //container manual-keying

        } //list ipsec-tunnel

      } //container ipsec

      container ipv6 {
        presence
            "Enables/Configures IPv6 for an interface";
        list address {
          key "ipv6-address-prefix-length";
          description
              "Assigns an IPv6 address to the interface.";
          leaf ipv6-address-prefix-length {
            type string;
            description
                "ipv6-address x:x:x:x:x:x:x:x (eight 16-bit pieces) 
                 x:x:x:x:x:x:d.d.d.d 
                 x [0..FFFF]H 
                 d [0..255]D 
                 (no multicast address) 
                 prefix-length [1..128]";
          } //ipv6-address-prefix-length

          leaf eui-64 {
            type boolean;
          } //eui-64

          leaf preferred {
            type boolean;
            status "obsolete";
          } //preferred

          leaf track-srrp {
            type uint32 {
              range "1..4294967295";
            }
          } //track-srrp

          leaf modifier {
            type string {
              length "1..43";
            }
            description
                "[0x0..0xFFFFFFFF...(32 hex nibbles)]";
          } //modifier

          leaf dad-disable {
            type boolean;
          } //dad-disable

          leaf primary-preference {
            type uint32 {
              range "1..4294967295";
            }
          } //primary-preference

        } //list address

        container bfd {
          description
              "Configure BFD parameters for IPv6";
          leaf transmit-interval {
            type uint32 {
              range "10..100000";
            }
            description
                "[10..100000] in milliseconds";
          } //transmit-interval

          leaf receive {
            type uint32 {
              range "10..100000";
            }
            description
                "[10..100000] in milliseconds";
          } //receive

          leaf multiplier {
            type string;
            description
                "Attribute multiplier for bfd";
          } //multiplier

          leaf echo-receive {
            type uint32 {
              range "100..100000";
            }
            description
                "[100..100000] in milliseconds";
          } //echo-receive

          leaf type {
            type enumeration {
              enum cpm-np;
              enum fp;
            }
            description
                "Attribute type for bfd";
          } //type

        } //container bfd

        leaf dad-disable {
          type boolean;
          description
              "Disable Duplicate Address Detection";
        }

        leaf forward-ipv4-packets {
          type boolean;
          description
              "Enable/disable forwarding unencapsulated IPv4 packets";
        }

        container link-local-address {
          description
              "Configure link-local address";
          leaf ipv6-address {
            type string;
            description
                "Attribute ipv6-address for link-local-address";
          } //ipv6-address

          leaf preferred {
            type boolean;
            status "obsolete";
          } //preferred

          leaf dad-disable {
            type boolean;
          } //dad-disable

        } //container link-local-address

        container local-dhcp-server {
          description
              "Assign a DHCP server to the interface";
          leaf local-server-name {
            type string {
              length "1..32";
            }
          } //local-server-name

        } //container local-dhcp-server

        leaf local-proxy-nd {
          type boolean;
          description
              "Enable/disable local proxy Neighbor Discovery on the interface";
        }

        container nd-learn-unsolicited {
          description
              "Configure neighbor discovery unsolicited learning on the interface";
          leaf nd-learn-unsolicited-id {
            type enumeration {
              enum global;
              enum link-local;
              enum both;
            }
          } //nd-learn-unsolicited-id

        } //container nd-learn-unsolicited

        container nd-proactive-refresh {
          description
              "Configure neighbor discovery proactive refresh";
          leaf nd-proactive-refresh-id {
            type enumeration {
              enum global;
              enum link-local;
              enum both;
            }
          } //nd-proactive-refresh-id

        } //container nd-proactive-refresh

        list neighbor {
          key "ipv6-address";
          description
              "Configure IPv6-to-MAC address mapping on the interface";
          leaf ipv6-address {
            type inet:ipv6-address;
            description
                "x:x:x:x:x:x:x:x (eight 16-bit pieces) 
                 x:x:x:x:x:x:d.d.d.d 
                 x [0..FFFF]H 
                 d [0..255]D";
          } //ipv6-address

          leaf mac-address {
            type alu:ieee-address;
            description
                "xx:xx:xx:xx:xx:xx or xx-xx-xx-xx-xx-xx";
          } //mac-address

        } //list neighbor

        container neighbor-limit {
          description
              "Configures the maximum amount of IPv6 neighbor entries";
          leaf limit {
            type int32 {
              range "0..102400";
            }
            description
                "[0..102400] entries - default = disabled";
          } //limit

          leaf log-only {
            type boolean;
          } //log-only

          leaf threshold {
            type uint32 {
              range "1..100";
            }
          } //threshold

        } //container neighbor-limit

        container proxy-nd-policy {
          description
              "Configure a proxy Neighbor Discovery policy for the interface";
          leaf-list policy-name {
            type string {
              length "1..32";
            }
            max-elements 5;
            description
                "[32 chars max]";
          } //policy-name

        } //container proxy-nd-policy

        container qos-route-lookup {
          description
              "Enable/Disable Qos route lookup for the interface";
          leaf source-destination {
            type enumeration {
              enum source;
              enum destination;
            }
          } //source-destination

        } //container qos-route-lookup

        container reachable-time {
          description
              "Configure neighbor reachability detection timer";
          leaf seconds {
            type uint32 {
              range "30..3600";
            }
          } //seconds

        } //container reachable-time

        container stale-time {
          description
              "Configure the time a neighbor discovery cache entry can remain stale before 
               being removed";
          leaf seconds {
            type uint32 {
              range "60..65535";
            }
          } //seconds

        } //container stale-time

        container tcp-mss {
          description
              "Configure TCP maximum segment size for the interface";
          leaf mss-value {
            type string;
            description
                "Attribute mss-value for tcp-mss";
          } //mss-value

        } //container tcp-mss

        container icmp6 {
          description
              "Configure ICMPv6 parameters for the interface";
          container packet-too-big {
            description
                "Configures rate for ICMPv6 packet-too-big messages";
            leaf-list number-seconds {
              type uint16 {
                range "1..1000";
              }
              max-elements 2;
              description
                  "number [10..1000] 
                   seconds [1..60]";
            } //number-seconds

          } //container packet-too-big

          container param-problem {
            description
                "Configures rate for ICMPv6 param-problem messages";
            leaf-list number-seconds {
              type uint16 {
                range "1..1000";
              }
              max-elements 2;
              description
                  "number [10..1000] 
                   seconds [1..60]";
            } //number-seconds

          } //container param-problem

          container redirects {
            description
                "Configures rate for ICMPv6 redirect messages";
            leaf-list number-seconds {
              type uint16 {
                range "1..1000";
              }
              max-elements 2;
              description
                  "number [10..1000] 
                   seconds [1..60]";
            } //number-seconds

          } //container redirects

          container time-exceeded {
            description
                "Configures rate for ICMPv6 time-exceeded messages";
            leaf-list number-seconds {
              type uint16 {
                range "1..2000";
              }
              max-elements 2;
              description
                  "number [10..2000] 
                   seconds [1..60]";
            } //number-seconds

          } //container time-exceeded

          container unreachables {
            description
                "Configures rate for ICMPv6 unreachable messages";
            leaf-list number-seconds {
              type uint16 {
                range "1..2000";
              }
              max-elements 2;
              description
                  "number [10..2000] 
                   seconds [1..60]";
            } //number-seconds

          } //container unreachables

        } //container icmp6

        container secure-nd {
          presence
              "Configure Secure Neighbor Discovery (SEND) parameters for the interface";
          leaf allow-unsecured-msgs {
            type boolean;
            description
                "Specify whether unsecured messages are accepted";
          }

          container link-local-modifier {
            description
                "Configure the CGA modifier for link-local addresses";
            leaf link-local-modifier-string {
              type string {
                length "1..34";
              }
              description
                  "[0x0..0xFFFFFFFF...(32 hex nibbles)]";
            } //link-local-modifier-string

          } //container link-local-modifier

          container public-key-min-bits {
            description
                "Configure the minimum acceptable key length for public keys used in the 
                 generation of a CGA";
            leaf bits {
              type uint32 {
                range "512..1024";
              }
            } //bits

          } //container public-key-min-bits

          container security-parameter {
            description
                "Configure the security parameter used in the generation of a CGA";
            leaf sec {
              type uint32 {
                range "0..1";
              }
            } //sec

          } //container security-parameter

          leaf shutdown {
            type boolean;
            description
                "Administratively enable/disable SEND on this interface";
          }

        } //container secure-nd

        container urpf-check {
          presence
              "Enables/Configures unicast RPF check for Ipv6 on this interface";
          leaf ignore-default {
            type boolean;
            description
                "Enable/Disable default route when performing a uRPF check.";
          }

          container mode {
            description
                "Configure unicast RPF check mode";
            leaf strict-loose-strict-no-ecmp {
              type enumeration {
                enum strict;
                enum loose;
                enum strict-no-ecmp;
              }
              description
                  "keywords";
            } //strict-loose-strict-no-ecmp

          } //container mode

        } //container urpf-check

        list vrrp {
          key "virtual-router-id";
          description
              "Context to create and configure VRRP virtual router instance on the interface";
          leaf virtual-router-id {
            type uint16 {
              range "1..255";
            }
          } //virtual-router-id

          leaf owner {
            type boolean;
          } //owner

          leaf passive {
            type boolean;
          } //passive

          list backup {
            key "ipv6-address";
            description
                "Configure virtual router IP addresses for the interface";
            leaf ipv6-address {
              type inet:ipv6-address;
              description
                  "x:x:x:x:x:x:x:x (eight 16-bit pieces) 
                   ";
            } //ipv6-address

          } //list backup

          list bfd-enable {
            key "interface dst-ip";
            description
                "Configure a BFD interface";
            leaf svc-id {
              type uint32 {
                range "1..2147483647";
              }
            } //svc-id

            leaf interface {
              type string {
                length "1..32";
              }
              description
                  "[32 chars max] (must start with a letter)";
            } //interface

            leaf dst-ip {
              type string;
              description
                  "Attribute ip-address for bfd-enable";
            } //dst-ip

            leaf name {
              type string;
              description
                  "64-char max (ies/vprn service-name)";
            } //name

          } //list bfd-enable

          container init-delay {
            description
                "Configure VRRP initialization delay timer";
            leaf seconds {
              type uint32 {
                range "1..65535";
              }
            } //seconds

          } //container init-delay

          container mac {
            description
                "Configure a Virtual MAC address to use in Neighbor Discovery";
            leaf mac-address {
              type string;
              description
                  "xx:xx:xx:xx:xx:xx or xx-xx-xx-xx-xx-xx";
            } //mac-address

          } //container mac

          leaf master-int-inherit {
            type boolean;
            description
                "Allow/disallow the master instance to dictate the master down timer (non-owner 
                 context only)";
          }

          container message-interval {
            description
                "Configure the interval for sending VRRP Advertisement messages";
            leaf seconds {
              type uint32 {
                range "1..40";
              }
            } //seconds

            leaf milliseconds {
              type uint32 {
                range "10..990";
              }
            } //milliseconds

          } //container message-interval

          leaf ntp-reply {
            type boolean;
            description
                "Allow/disallow non-owner master to reply to NTP requests (non-owner context 
                 only)";
          }

          container oper-group {
            description
                "Associate group-name to VRRP";
            leaf group-name {
              type string {
                length "1..32";
              }
            } //group-name

          } //container oper-group

          leaf ping-reply {
            type boolean;
            description
                "Allow/disallow non-owner master to reply to ICMP Echo requests (non-owner 
                 context only)";
          }

          container policy {
            description
                "Associate a VRRP Priority Control Policy with the virtual router instance 
                 (non-owner context only)";
            leaf vrrp-policy-id {
              type uint32 {
                range "1..9999";
              }
            } //vrrp-policy-id

          } //container policy

          leaf preempt {
            type boolean;
            description
                "Allow/disallow the virtual router instance to override an existing non-owner 
                 master (non-owner context only)";
          }

          container priority {
            description
                "Configure the base priority for the virtual router instance (non-owner context 
                 only)";
            leaf priority {
              type uint16 {
                range "1..254";
              }
            } //priority

          } //container priority

          leaf shutdown {
            type boolean;
            description
                "Administratively enable/disable the virtual router instance (non-owner context 
                 only)";
          }

          leaf standby-forwarding {
            type boolean;
            description
                "Allow/disallow the forwarding of packets by a standby router";
          }

          leaf telnet-reply {
            type boolean;
            description
                "Allow/disallow non-owner master to reply to Telnet requests (non-owner context 
                 only)";
          }

          leaf traceroute-reply {
            type boolean;
            description
                "Allow/disallow non-owner master to reply to traceroute requests (non-owner 
                 context only)";
          }

        } //list vrrp

      } //container ipv6

      container load-balancing {
        description
            "Context to configure hashing commands";
        container egr-ip-load-balancing {
          description
              "Configure egr-ip-load-balancing for the interface";
          leaf algorithm {
            type enumeration {
              enum source;
              enum destination;
              enum inner-ip;
            }
          } //algorithm

        } //container egr-ip-load-balancing

        container lsr-load-balancing {
          description
              "Configure the LSR Load Balancing algorithm for the interface";
          leaf hashing-algorithm {
            type enumeration {
              enum lbl-ip;
              enum lbl-only;
              enum ip-only;
              enum eth-encap-ip;
              enum lbl-ip-l4-teid;
            }
            description
                "lbl-only | lbl-ip | ip-only | eth-encap-ip | lbl-ip-l4-teid 
                 Default: use system configuration";
          } //hashing-algorithm

        } //container lsr-load-balancing

        leaf spi-load-balancing {
          type boolean;
          description
              "Enable/disable SPI use in hashing for the interface";
        }

        leaf teid-load-balancing {
          type boolean;
          description
              "Enable/disable TEID load balancing for the interface";
        }

      } //container load-balancing

      container urpf-check {
        presence
            "Enables/Configures unicast RPF check for an interface";
        leaf ignore-default {
          type boolean;
          description
              "Enable/Disable default route when performing a uRPF check.";
        }

        container mode {
          description
              "Configure unicast RPF check mode";
          leaf strict-loose-strict-no-ecmp {
            type enumeration {
              enum strict;
              enum loose;
              enum strict-no-ecmp;
            }
            description
                "keywords";
          } //strict-loose-strict-no-ecmp

        } //container mode

      } //container urpf-check

      list vrrp {
        key "virtual-router-id";
        description
            "Context to create and configure VRRP virtual router instance on the interface";
        leaf virtual-router-id {
          type uint16 {
            range "1..255";
          }
        } //virtual-router-id

        leaf owner {
          type boolean;
        } //owner

        leaf passive {
          type boolean;
        } //passive

        container authentication-key {
          description
              "Configure password for simple text password authentication";
          leaf authentication-key-hash-key {
            type string {
              length "1..500";
            }
            description
                "authentication-key - [8 chars max] 
                 hash-key 
                 hash2-key 
                 custom-key";
          } //authentication-key-hash-key

          leaf hash-hash2-custom {
            type enumeration {
              enum hash;
              enum hash2;
              enum custom;
            }
            description
                "keywords - specify hashing scheme";
          } //hash-hash2-custom

        } //container authentication-key

        list backup {
          key "ip-address";
          description
              "Configure virtual router IP addresses for the interface";
          leaf ip-address {
            type inet:ip-address;
          } //ip-address

        } //list backup

        list bfd-enable {
          key "interface dst-ip";
          description
              "Configure a BFD interface";
          leaf svc-id {
            type uint32 {
              range "1..2147483647";
            }
          } //svc-id

          leaf interface {
            type string {
              length "1..32";
            }
            description
                "[32 chars max] (must start with a letter)";
          } //interface

          leaf dst-ip {
            type inet:ip-address;
            description
                "ip-address";
          } //dst-ip

          leaf name {
            type string;
            description
                "64-char max (ies/vprn service-name)";
          } //name

        } //list bfd-enable

        container init-delay {
          description
              "Configure VRRP initialization delay timer";
          leaf seconds {
            type uint32 {
              range "1..65535";
            }
          } //seconds

        } //container init-delay

        container mac {
          description
              "Configure a Virtual MAC address to use in ARP responses";
          leaf mac-address {
            type string;
            description
                "xx:xx:xx:xx:xx:xx or xx-xx-xx-xx-xx-xx";
          } //mac-address

        } //container mac

        leaf master-int-inherit {
          type boolean;
          description
              "Allow/disallow the master instance to dictate the master down timer (non-owner 
               context only)";
        }

        container message-interval {
          description
              "Configure the interval for sending VRRP Advertisement messages";
          leaf seconds {
            type uint32 {
              range "1..255";
            }
          } //seconds

          leaf milliseconds {
            type uint32 {
              range "100..900";
            }
          } //milliseconds

        } //container message-interval

        leaf ntp-reply {
          type boolean;
          description
              "Allow/disallow non-owner master to reply to NTP requests (non-owner context 
               only)";
        }

        container oper-group {
          description
              "Associate group-name to VRRP";
          leaf group-name {
            type string {
              length "1..32";
            }
          } //group-name

        } //container oper-group

        leaf ping-reply {
          type boolean;
          description
              "Allow/disallow non-owner master to reply to ICMP Echo requests (non-owner 
               context only)";
        }

        container policy {
          description
              "Associate a VRRP Priority Control Policy with the virtual router instance 
               (non-owner context only)";
          leaf vrrp-policy-id {
            type uint32 {
              range "1..9999";
            }
          } //vrrp-policy-id

        } //container policy

        leaf preempt {
          type boolean;
          description
              "Allow/disallow the virtual router instance to override an existing non-owner 
               master (non-owner context only)";
        }

        container priority {
          description
              "Configure the base priority for the virtual router instance (non-owner context 
               only)";
          leaf priority {
            type uint16 {
              range "1..254";
            }
          } //priority

        } //container priority

        leaf shutdown {
          type boolean;
          description
              "Administratively enable/disable the virtual router instance (non-owner context 
               only)";
        }

        leaf ssh-reply {
          type boolean;
          description
              "Allow/disallow non-owner master to reply to SSH requests (non-owner context 
               only)";
        }

        leaf standby-forwarding {
          type boolean;
          description
              "Allow/disallow the forwarding of packets by a standby router";
        }

        leaf telnet-reply {
          type boolean;
          description
              "Allow/disallow non-owner master to reply to Telnet requests (non-owner context 
               only)";
        }

        leaf traceroute-reply {
          type boolean;
          description
              "Allow/disallow non-owner master to reply to traceroute requests (non-owner 
               context only)";
        }

      } //list vrrp

    } //list interface

  } //grouping alu-conf-router-if-r13

} //module  alu-conf-router-if-r13
