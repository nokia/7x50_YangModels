module alu-conf-router-treesid-r13 {
  yang-version "1";

  namespace "urn:alcatel-lucent.com:sros:ns:yang:conf-router-treesid-r13";

  prefix "conf-router-treesid-r13";

  import alu-types {
    prefix "alu";
  }
  import ietf-inet-types {
    prefix "inet";
  }

  alu:alu-major-release "rel20";

  organization "Alcatel-Lucent";

  contact
      "Alcatel-Lucent SR OS Support 
       Web: <http://www.alcatel-lucent.com>";

  description
      "Alcatel-Lucent YANG Data model to create/deletes p2mp-sr-tree entries on SR OS 
       based routers. 
       
       Copyright 2014-2015 Alcatel-Lucent, 2016 Nokia. All rights reserved. 
       Reproduction of this document is authorized on the condition that the 
       foregoing copyright notice is included. 
       
       This alu-conf-router-treesid-r13 YANG module embodies Alcatel-Lucent's 
       proprietary intellectual property. Alcatel-Lucent retains all title and 
       ownership in the Specification, including any revisions. 
       
       Alcatel-Lucent grants all interested parties a non-exclusive license to use 
       and distribute an unmodified copy of this Specification in connection with 
       management of Alcatel-Lucent products, and without fee, provided this 
       copyright notice and license appear on all copies. 
       
       This Specification is supplied `as is', and Alcatel-Lucent makes no warranty, 
       either express or implied, as to the use, operation, condition, or performance 
       of the Specification.";

  revision  "2020-07-15";

  grouping alu-conf-router-treesid-r13 {
    container p2mp-sr-tree {
      presence
          "Creates/Deletes p2mp-sr-tree entries";
      container bfd-enable {
        description
            "Enable/Disable BFD tracking of p2mp-sr-tree";
        leaf ipv4 {
          type boolean;
        } //ipv4

        leaf ipv6 {
          type boolean;
        } //ipv6

      } //container bfd-enable

      container reserved-lbl-block {
        description
            "Set reserved-lbl-block name for this p2mp-sr-tree instance";
        leaf reserved-lbl-block {
          type string {
            length "1..64";
          }
        } //reserved-lbl-block

      } //container reserved-lbl-block

      leaf shutdown {
        type boolean;
        description
            "Administratively disable or enable this p2mp-sr-tree instance";
      }

      list p2mp-policy {
        key "policy-name";
        description
            "Creates/Deletes treesid p2mp-policy entries";
        leaf policy-name {
          type string {
            length "1..32";
          }
        } //policy-name

        container root-address {
          description
              "root-address for p2mp-policy entries";
          leaf ip-address {
            type inet:ip-address;
          } //ip-address

        } //container root-address

        container root-tree-id {
          description
              "root-tree-id for p2mp-policy entries";
          leaf tree-id {
            type uint32 {
              range "8193..16286";
            }
          } //tree-id

        } //container root-tree-id

        leaf shutdown {
          type boolean;
          description
              "Administratively enable or disable this p2mp-sr-tree p2mp-policy instance";
        }

        list p2mp-candidate-path {
          key "candidate-path-name";
          description
              "p2mp-candidate-path for p2mp-policy entries";
          leaf candidate-path-name {
            type string {
              length "1..32";
            }
          } //candidate-path-name

          container active-instance {
            description
                "active-instance for the p2mp-policy candidate-path entries";
            leaf instance-id {
              type uint32 {
                range "1..2";
              }
            } //instance-id

          } //container active-instance

          container preference {
            description
                "preference for p2mp-sr-policy candidate path entries";
            leaf preference {
              type uint32 {
                range "0..1024";
              }
            } //preference

          } //container preference

          leaf shutdown {
            type boolean;
            description
                "Administratively disable or enable this p2mp-sr-tree p2mp-policy 
                 candidate-path instance";
          }

          container instances {
            description
                "instances for p2mp-sr-tree candidate path instances entries";
            list instance {
              key "instance-id";
              description
                  "instance for the p2mp-policy candidate-path entries";
              leaf instance-id {
                type uint32 {
                  range "1..2";
                }
              } //instance-id

              leaf instance-value {
                type uint32 {
                  range "1..4294967295";
                }
              } //instance-value

            } //list instance

          } //container instances

        } //list p2mp-candidate-path

      } //list p2mp-policy

      list replication-segment {
        key "policy-name";
        description
            "Creates/Deletes treesid replication-segment entries";
        leaf policy-name {
          type string {
            length "1..32";
          }
        } //policy-name

        container incoming-sid {
          description
              "incoming-sid for replication-segment entries";
          leaf static-label {
            type uint32;
          } //static-label

        } //container incoming-sid

        container instance-id {
          description
              "instance-id for replication-segment entries";
          leaf instance-id {
            type uint32 {
              range "1..4294967295";
            }
          } //instance-id

        } //container instance-id

        container root-address {
          description
              "root-address for replication-segment entries";
          leaf ip-address {
            type inet:ip-address;
          } //ip-address

        } //container root-address

        container root-tree-id {
          description
              "root-tree-id for replication-segment entries";
          leaf tree-id {
            type uint32 {
              range "8193..16286";
            }
          } //tree-id

        } //container root-tree-id

        leaf shutdown {
          type boolean;
          description
              "Administratively disable or enable this treesid replication-segment instance";
        }

        container sid-action {
          description
              "sid-action for replication-segment entries";
          leaf action {
            type enumeration {
              enum push;
              enum pop;
              enum swap;
            }
          } //action

        } //container sid-action

        list next-hop-id {
          key "next-hop-index";
          description
              "next-hop-id for replication-segment entries";
          leaf next-hop-index {
            type uint32 {
              range "1..4096";
            }
          } //next-hop-index

          container next-hop-address {
            description
                "next-hop-address for the replication-policy next-hop entries";
            leaf ip-address-ipv6-address {
              type string;
              description
                  "Attribute ip-address|ipv6-address for next-hop-address";
            } //ip-address-ipv6-address

          } //container next-hop-address

          container next-hop-interface-name {
            description
                "next-hop-interface-name for the replication-policy next-hop entries";
            leaf interface-name {
              type string {
                length "1..32";
              }
            } //interface-name

          } //container next-hop-interface-name

          container protecting-nexthop-id {
            description
                "next-hop-interface-id for the replication-policy next-hop entries";
            leaf next-hop-index {
              type uint32 {
                range "1..4096";
              }
            } //next-hop-index

          } //container protecting-nexthop-id

          container replication-sid {
            description
                "replication-sid for the replication-policy next-hop entries";
            leaf label {
              type string;
              description
                  "3 | 16..1048576 | 4294967295";
            } //label

          } //container replication-sid

          leaf shutdown {
            type boolean;
            description
                "Administratively enable or disable this p2mp-sr-tree replication-segment 
                 next-hop-id";
          }

        } //list next-hop-id

      } //list replication-segment

    } //container p2mp-sr-tree

  } //grouping alu-conf-router-treesid-r13

} //module  alu-conf-router-treesid-r13
