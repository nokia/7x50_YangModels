module alu-conf-svc-vprn-spoke-r13 {
  yang-version "1";

  namespace "urn:alcatel-lucent.com:sros:ns:yang:conf-svc-vprn-spoke-r13";

  prefix "conf-svc-vprn-spoke-r13";

  import alu-types {
    prefix "alu";
  }

  alu:alu-major-release "rel20";

  organization "Alcatel-Lucent";

  contact
      "Alcatel-Lucent SR OS Support 
       Web: <http://www.alcatel-lucent.com>";

  description
      "Alcatel-Lucent YANG Data model to configure spoke SDP bindings for VPRN 
       services on SR OS based routers. 
       
       Copyright 2014-2015 Alcatel-Lucent, 2016 Nokia. All rights reserved. 
       Reproduction of this document is authorized on the condition that the 
       foregoing copyright notice is included. 
       
       This alu-conf-svc-vprn-spoke-r13 YANG module embodies Alcatel-Lucent's 
       proprietary intellectual property. Alcatel-Lucent retains all title and 
       ownership in the Specification, including any revisions. 
       
       Alcatel-Lucent grants all interested parties a non-exclusive license to use 
       and distribute an unmodified copy of this Specification in connection with 
       management of Alcatel-Lucent products, and without fee, provided this 
       copyright notice and license appear on all copies. 
       
       This Specification is supplied `as is', and Alcatel-Lucent makes no warranty, 
       either express or implied, as to the use, operation, condition, or performance 
       of the Specification.";

  revision  "2019-11-12";

  grouping alu-conf-svc-vprn-spoke-r13 {
    list spoke-sdp {
      key "sdp-id-vc-id";
      description
          "Configure spoke SDP bindings for VPRN services";
      leaf sdp-id-vc-id {
        type string;
        description
            "sdp-id - [1..32767] 
             vc-id - [1..4294967295]";
      } //sdp-id-vc-id

      container description {
        description
            "Set description for spoke-sdp";
        leaf description-string {
          type string {
            length "1..80";
          }
          description
              "80 char max";
        } //description-string

      } //container description

    } //list spoke-sdp

  } //grouping alu-conf-svc-vprn-spoke-r13

} //module  alu-conf-svc-vprn-spoke-r13
