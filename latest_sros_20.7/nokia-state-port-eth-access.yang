submodule nokia-state-port-eth-access {

    yang-version "1.1";

    belongs-to nokia-state { prefix "state"; }

    import ietf-yang-types                { prefix "yang"; }
    import nokia-sros-yang-extensions     { prefix "sros-ext"; }
    import nokia-types-qos                { prefix "types-qos"; }
    import nokia-types-sros               { prefix "types-sros"; }

    include nokia-state-qos;

    sros-ext:sros-major-release "rel20";

    organization "Nokia";

    contact
        "Nokia SR OS Support
         Web: <http://www.nokia.com>";

    description
        "Nokia YANG Data model with operational state for access capabilities for ethernet ports on SR OS based routers.

         Copyright 2016 Nokia. All rights reserved. Reproduction of this document
         is authorized on the condition that the foregoing copyright notice is included.

         This nokia-state-port-eth-access YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";

    revision "2020-06-29";

    grouping state-port-eth-access {
        container access {
            description "Enter the access context";

            leaf available-bandwidth {
                type yang:counter64;
                units "kilobps";
                description "Indicates the bandwidth that is still free for booking on the Ethernet port.";
            }

            leaf booked-bandwidth {
                type yang:counter64;
                units "kilobps";
                description "Indicates the bandwidth that has been booked on the Ethernet port.";
            }

            container egress {
                description "Enter the egress context";

                list queue-group {
                    key "queue-group-name instance-id";
                    description "Enter the queue-group list instance";

                    leaf queue-group-name {
                        type leafref {
                            path "../../../../../../qos/queue-group-templates/egress/queue-group/egress-queue-group-name";
                        }
                        description "Queue group name";
                    }

                    leaf instance-id {
                        type uint16 {
                            range "1..65535";
                        }
                        description "Instance ID";
                    }

                    container scheduler-policy {
                        description "Enter the scheduler-policy context";

                        list scheduler {
                            key "scheduler-name";
                            description "Enter the scheduler list instance";

                            leaf scheduler-name {
                                type types-sros:named-item;
                                description "Scheduler name";
                            }

                            container statistics {
                                description "Enter the statistics context";

                                leaf forwarded-packets {
                                    type yang:counter64;
                                    description "The number of forwarded packets.";
                                }

                                leaf forwarded-octets {
                                    type yang:counter64;
                                    description "The number of forwarded octets.";
                                }

                            } // container statistics

                        } // list scheduler

                    } // container scheduler-policy

                    list queue {
                        key "queue-id";
                        description "Enter the queue list instance";

                        leaf queue-id {
                            type leafref {
                                path "../../../../../../../qos/queue-group-templates/egress/queue-group[egress-queue-group-name=current()/../../queue-group-name]/queue/queue-id";
                            }
                            description "Specifies the queue overrides queue identifier.";
                        }

                        container statistics {
                            description "Enter the statistics context";

                            choice stat-mode {
                                case profile {

                                    container profile {
                                        description "Enter the profile context";

                                        leaf in-inplus-profile-forwarded-packets {
                                            type yang:counter64;
                                            description
                                                "The number of in-profile/in-plus-profile packets
                                                 (rate below CIR) forwarded.";
                                        }

                                        leaf in-inplus-profile-forwarded-octets {
                                            type yang:counter64;
                                            description
                                                "The number of in-profile/in-plus-profile octets
                                                 (rate below CIR) forwarded.";
                                        }

                                        leaf in-inplus-profile-dropped-packets {
                                            type yang:counter64;
                                            description
                                                "The number of in-profile/in-plus-profile packets
                                                 discarded.";
                                        }

                                        leaf in-inplus-profile-dropped-octets {
                                            type yang:counter64;
                                            description
                                                "The number of in-profile/in-plus-profile octets
                                                 discarded.";
                                        }

                                        leaf out-exceed-profile-forwarded-packets {
                                            type yang:counter64;
                                            description
                                                "The number of out-profile/exceed-profile packets
                                                 (rate above CIR) forwarded.";
                                        }

                                        leaf out-exceed-profile-forwarded-octets {
                                            type yang:counter64;
                                            description
                                                "The number of out-profile/exceed-profile octets
                                                 (rate above CIR) forwarded.";
                                        }

                                        leaf out-exceed-profile-dropped-packets {
                                            type yang:counter64;
                                            description
                                                "The number of out-profile/exceed-profile packets
                                                 discarded.";
                                        }

                                        leaf out-exceed-profile-dropped-octets {
                                            type yang:counter64;
                                            description
                                                "The number of out-profile/exceed-profile octets
                                                 discarded.";
                                        }

                                    } // container profile

                                }
                            }
                        } // container statistics

                    } // list queue

                } // list queue-group

                list virtual-port {
                    key "vport-name";
                    description "Enter the virtual-port list instance";

                    leaf vport-name {
                        type types-sros:named-item;
                        description "Specifies the name of the virtual port on the port.";
                    }

                    leaf multicast-hqos-adjustment-delta {
                        type uint32;
                        units "kilobps";
                        description "Indicates the actual bandwidth correction.";
                    }

                    list scheduler {
                        key "scheduler-name";
                        description "Enter the scheduler list instance";

                        leaf scheduler-name {
                            type types-sros:named-item;
                            description "Scheduler name";
                        }

                        container statistics {
                            description "Enter the statistics context";

                            leaf forwarded-packets {
                                type yang:counter64;
                                description "The number of forwarded packets.";
                            }

                            leaf forwarded-octets {
                                type yang:counter64;
                                description "The number of forwarded octets.";
                            }

                        } // container statistics

                    } // list scheduler

                } // list virtual-port

            } // container egress

            container ingress {
                description "Enter the ingress context";

                list queue-group {
                    key "queue-group-name";
                    description "Enter the queue-group list instance";

                    leaf queue-group-name {
                        type leafref {
                            path "../../../../../../qos/queue-group-templates/ingress/queue-group/ingress-queue-group-name";
                        }
                        description "Queue group name";
                    }

                    container scheduler-policy {
                        description "Enter the scheduler-policy context";

                        list scheduler {
                            key "scheduler-name";
                            description "Enter the scheduler list instance";

                            leaf scheduler-name {
                                type types-sros:named-item;
                                description "Scheduler name";
                            }

                            container statistics {
                                description "Enter the statistics context";

                                leaf forwarded-packets {
                                    type yang:counter64;
                                    description "The number of forwarded packets.";
                                }

                                leaf forwarded-octets {
                                    type yang:counter64;
                                    description "The number of forwarded octets.";
                                }

                            } // container statistics

                        } // list scheduler

                    } // container scheduler-policy

                    list queue {
                        key "queue-id";
                        description "Enter the queue list instance";

                        leaf queue-id {
                            type types-qos:ingress-queue-id;
                            description "Specifies the queue group queue identifier.";
                        }

                        container statistics {
                            description "Enter the statistics context";

                            choice stat-mode {
                                case unicast-priority {

                                    container unicast-priority {
                                        description "Enter the unicast-priority context";

                                        leaf high-priority-offered-packets {
                                            type yang:counter64;
                                            description "The number of high-priority packets offered by packet processor to traffic manager.";
                                        }

                                        leaf high-priority-offered-octets {
                                            type yang:counter64;
                                            description "The number of high-priority octets offered by packet processor to traffic manager.";
                                        }

                                        leaf low-priority-offered-packets {
                                            type yang:counter64;
                                            description "The number of low-priority packets offered by packet processor to traffic manager.";
                                        }

                                        leaf low-priority-offered-octets {
                                            type yang:counter64;
                                            description "The number of low-priority octets offered by packet processor to traffic manager.";
                                        }

                                        leaf high-priority-dropped-packets {
                                            type yang:counter64;
                                            description "The number of high-priority packets dropped by packet processor to traffic manager.";
                                        }

                                        leaf high-priority-dropped-octets {
                                            type yang:counter64;
                                            description "The number of high-priority octets dropped by packet processor to traffic manager.";
                                        }

                                        leaf low-priority-dropped-packets {
                                            type yang:counter64;
                                            description "The number of low-priority packets dropped by packet processor to traffic manager.";
                                        }

                                        leaf low-priority-dropped-octets {
                                            type yang:counter64;
                                            description "The number of low-priority octets dropped by packet processor to traffic manager.";
                                        }

                                        leaf in-profile-forwarded-packets {
                                            type yang:counter64;
                                            description "The number of in-profile packets (rate below CIR) forwarded.";
                                        }

                                        leaf in-profile-forwarded-octets {
                                            type yang:counter64;
                                            description "The number of in-profile octets (rate below CIR) forwarded.";
                                        }

                                        leaf out-profile-forwarded-packets {
                                            type yang:counter64;
                                            description "The number of out-of-profile packets (rate below CIR) forwarded.";
                                        }

                                        leaf out-profile-forwarded-octets {
                                            type yang:counter64;
                                            description "The number of out-of-profile octets (rate below CIR) forwarded.";
                                        }

                                    } // container unicast-priority

                                }
                                case unicast-profile {

                                    container unicast-profile {
                                        description "Enter the unicast-profile context";

                                        leaf color-in-offered-packets {
                                            type yang:counter64;
                                            description "The number of color-in packets offered to traffic manager.";
                                        }

                                        leaf color-in-offered-octets {
                                            type yang:counter64;
                                            description "The number of color-in octets offered to traffic manager.";
                                        }

                                        leaf color-out-offered-packets {
                                            type yang:counter64;
                                            description "The number of color-out packets offered to traffic manager.";
                                        }

                                        leaf color-out-offered-octets {
                                            type yang:counter64;
                                            description "The number of color-out octets offered to traffic manager.";
                                        }

                                        leaf color-offered-packets {
                                            type yang:counter64;
                                            description "The number of color packets offered to traffic manager.";
                                        }

                                        leaf color-offered-octets {
                                            type yang:counter64;
                                            description "The number of color octets offered to traffic manager.";
                                        }

                                        leaf uncolor-offered-packets {
                                            type yang:counter64;
                                            description "The number of uncolor packets offered to traffic manager.";
                                        }

                                        leaf uncolor-offered-octets {
                                            type yang:counter64;
                                            description "The number of uncolor octets offered to traffic manager.";
                                        }

                                        leaf color-out-dropped-packets {
                                            type yang:counter64;
                                            description "The number of color-out packets dropped.";
                                        }

                                        leaf color-out-dropped-octets {
                                            type yang:counter64;
                                            description "The number of color-out octets dropped.";
                                        }

                                        leaf color-in-uncolor-dropped-packets {
                                            type yang:counter64;
                                            description "The number of color-in/uncolor packets dropped.";
                                        }

                                        leaf color-in-uncolor-dropped-octets {
                                            type yang:counter64;
                                            description "The number of color-in/uncolor octets dropped.";
                                        }

                                        leaf in-profile-forwarded-packets {
                                            type yang:counter64;
                                            description "The number of in-profile packets (rate below CIR) forwarded.";
                                        }

                                        leaf in-profile-forwarded-octets {
                                            type yang:counter64;
                                            description "The number of in-profile octets (rate below CIR) forwarded.";
                                        }

                                        leaf out-profile-forwarded-packets {
                                            type yang:counter64;
                                            description "The number of out-of-profile packets (rate below CIR) forwarded.";
                                        }

                                        leaf out-profile-forwarded-octets {
                                            type yang:counter64;
                                            description "The number of out-of-profile octets (rate below CIR) forwarded.";
                                        }

                                    } // container unicast-profile

                                }
                                case multipoint-priority {

                                    container multipoint-priority {
                                        description "Enter the multipoint-priority context";

                                        leaf high-priority-offered-packets {
                                            type yang:counter64;
                                            description "The number of high-priority packets offered by packet processor to traffic manager.";
                                        }

                                        leaf high-priority-offered-octets {
                                            type yang:counter64;
                                            description "The number of high-priority octets offered by packet processor to traffic manager.";
                                        }

                                        leaf low-priority-offered-packets {
                                            type yang:counter64;
                                            description "The number of low-priority packets offered by packet processor to traffic manager.";
                                        }

                                        leaf low-priority-offered-octets {
                                            type yang:counter64;
                                            description "The number of low-priority octets offered by packet processor to traffic manager.";
                                        }

                                        leaf combined-offered-packets {
                                            type yang:counter64;
                                            description "The number of combined high and low priority packets offered by packet processor to traffic manager.";
                                        }

                                        leaf combined-offered-octets {
                                            type yang:counter64;
                                            description "The number of combined high and low priority octets offered by packet processor to traffic manager.";
                                        }

                                        leaf managed-offered-packets {
                                            type yang:counter64;
                                            description "The number of managed packets offered by packet processor to traffic manager.";
                                        }

                                        leaf managed-offered-octets {
                                            type yang:counter64;
                                            description "The number of managed octets offered by packet processor to traffic manager.";
                                        }

                                        leaf high-priority-dropped-packets {
                                            type yang:counter64;
                                            description "The number of high-priority packets dropped by packet processor to traffic manager.";
                                        }

                                        leaf high-priority-dropped-octets {
                                            type yang:counter64;
                                            description "The number of high-priority octets dropped by packet processor to traffic manager.";
                                        }

                                        leaf low-priority-dropped-packets {
                                            type yang:counter64;
                                            description "The number of low-priority packets dropped by packet processor to traffic manager.";
                                        }

                                        leaf low-priority-dropped-octets {
                                            type yang:counter64;
                                            description "The number of low-priority octets dropped by packet processor to traffic manager.";
                                        }

                                        leaf in-profile-forwarded-packets {
                                            type yang:counter64;
                                            description "The number of in-profile packets (rate below CIR) forwarded.";
                                        }

                                        leaf in-profile-forwarded-octets {
                                            type yang:counter64;
                                            description "The number of in-profile octets (rate below CIR) forwarded.";
                                        }

                                        leaf out-profile-forwarded-packets {
                                            type yang:counter64;
                                            description "The number of out-of-profile packets (rate below CIR) forwarded.";
                                        }

                                        leaf out-profile-forwarded-octets {
                                            type yang:counter64;
                                            description "The number of out-of-profile octets (rate below CIR) forwarded.";
                                        }

                                    } // container multipoint-priority

                                }
                                case multipoint-profile {

                                    container multipoint-profile {
                                        description "Enter the multipoint-profile context";

                                        leaf color-in-offered-packets {
                                            type yang:counter64;
                                            description "The number of color-in packets offered to traffic manager.";
                                        }

                                        leaf color-in-offered-octets {
                                            type yang:counter64;
                                            description "The number of color-in octets offered to traffic manager.";
                                        }

                                        leaf color-out-offered-packets {
                                            type yang:counter64;
                                            description "The number of color-out packets offered to traffic manager.";
                                        }

                                        leaf color-out-offered-octets {
                                            type yang:counter64;
                                            description "The number of color-out octets offered to traffic manager.";
                                        }

                                        leaf uncolor-offered-packets {
                                            type yang:counter64;
                                            description "The number of uncolor packets offered to traffic manager.";
                                        }

                                        leaf uncolor-offered-octets {
                                            type yang:counter64;
                                            description "The number of uncolor octets offered to traffic manager.";
                                        }

                                        leaf combined-offered-packets {
                                            type yang:counter64;
                                            description "The number of combined colored in, out and uncolored packets offered to traffic manager.";
                                        }

                                        leaf combined-offered-octets {
                                            type yang:counter64;
                                            description "The number of combined colored in, out and uncolored octets offered to traffic manager.";
                                        }

                                        leaf managed-offered-packets {
                                            type yang:counter64;
                                            description "The number of managed packets offered by packet processor to traffic manager.";
                                        }

                                        leaf managed-offered-octets {
                                            type yang:counter64;
                                            description "The number of managed octets offered by packet processor to traffic manager.";
                                        }

                                        leaf color-out-dropped-packets {
                                            type yang:counter64;
                                            description "The number of color-out packets dropped.";
                                        }

                                        leaf color-out-dropped-octets {
                                            type yang:counter64;
                                            description "The number of color-out octets dropped.";
                                        }

                                        leaf color-in-uncolor-dropped-packets {
                                            type yang:counter64;
                                            description "The number of color-in/uncolor packets dropped.";
                                        }

                                        leaf color-in-uncolor-dropped-octets {
                                            type yang:counter64;
                                            description "The number of color-in/uncolor octets dropped.";
                                        }

                                        leaf in-profile-forwarded-packets {
                                            type yang:counter64;
                                            description "The number of in-profile packets (rate below CIR) forwarded.";
                                        }

                                        leaf in-profile-forwarded-octets {
                                            type yang:counter64;
                                            description "The number of in-profile octets (rate below CIR) forwarded.";
                                        }

                                        leaf out-profile-forwarded-packets {
                                            type yang:counter64;
                                            description "The number of out-of-profile packets (rate below CIR) forwarded.";
                                        }

                                        leaf out-profile-forwarded-octets {
                                            type yang:counter64;
                                            description "The number of out-of-profile octets (rate below CIR) forwarded.";
                                        }

                                    } // container multipoint-profile

                                }
                            }
                        } // container statistics

                    } // list queue

                } // list queue-group

            } // container ingress

        } // container access

    } // grouping state-port-eth-access

}
