submodule nokia-conf-system {

    yang-version "1.1";

    belongs-to nokia-conf { prefix "conf"; }

    import ietf-yang-types                { prefix "yang"; }
    import nokia-sros-yang-extensions     { prefix "sros-ext"; }
    import nokia-types-cellular           { prefix "types-cellular"; }
    import nokia-types-eth-cfm            { prefix "types-eth-cfm"; }
    import nokia-types-l2tp               { prefix "types-l2tp"; }
    import nokia-types-sros               { prefix "types-sros"; }
    import nokia-types-system             { prefix "types-system"; }

    include nokia-conf-groups;
    include nokia-conf-system-bluetooth;
    include nokia-conf-system-central-frequency-clock;
    include nokia-conf-system-cron;
    include nokia-conf-system-login-control;
    include nokia-conf-system-ned;
    include nokia-conf-system-persistence;
    include nokia-conf-system-script-control;
    include nokia-conf-system-security;
    include nokia-conf-system-security-tls;
    include nokia-conf-system-telemetry;
    include nokia-conf-system-time;

    sros-ext:sros-major-release "rel20";

    organization "Nokia";

    contact
        "Nokia SR OS Support
         Web: <http://www.nokia.com>";

    description
        "Nokia YANG Data model to configure system parameters on SR OS based routers.

         Copyright 2016 Nokia. All rights reserved. Reproduction of this document
         is authorized on the condition that the foregoing copyright notice is included.

         This nokia-conf-system YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";

    revision "2020-08-28";

    grouping conf-system {
        container system {
            description "Enter the system context";

            leaf contact {
                type types-sros:description;
                description "Contact information for this managed node";
            }

            leaf name {
                type types-sros:named-item-64;
                description "Administrative name assigned to the system";
            }

            leaf location {
                type types-sros:description;
                description "Site location of this system";
            }

            leaf alarm-contact-in-power {
                type boolean;
                default "false";
                description "Supply +24V output power on the +24DC pin of the Alarm Interface Port";
            }

            leaf icmp-vse {
                type boolean;
                default "false";
                description "Vendor-specific extensions to ICMP";
            }

            leaf selective-fib {
                type boolean;
                default "false";
                description "FIB assigned to the system";
            }

            leaf coordinates {
                type types-sros:description;
                description "GPS coordinates for the system location";
            }

            leaf clli-code {
                type types-sros:clli-description;
                description "CLLI code value for the system";
            }

            leaf congestion-management {
                type boolean;
                default "false";
                description "Virtual Service Router congestion management";
            }

            leaf ospf-dynamic-hostnames {
                type boolean;
                default "false";
                description "Process received OSPF dynamic hostname information";
            }

            leaf boot-good-exec {
                type types-sros:url;
                description "Location and name of CLI script file executed after successful boot-up configuration file execution";
            }

            leaf boot-bad-exec {
                type types-sros:url;
                description "CLI script file to execute following a failed boot-up";
            }

            leaf allow-boot-license-violations {
                type boolean;
                default "true";
                description "Allow boot license violations in a boot-up configuration";
            }

            leaf-list apply-groups {
                type leafref {
                    path "../../groups/group/name";
                }
                max-elements 8;
                ordered-by user;
                description "Apply a configuration group at this level";
            }

            container alarms {
                description "Enter the alarms context";

                leaf admin-state {
                    type types-sros:admin-state;
                    default "enable";
                    description "Administrative state of the system alarm";
                }

                leaf max-cleared {
                    type uint32 {
                        range "0..500";
                    }
                    default "500";
                    description "Maximum number of cleared alarms";
                }

                leaf-list apply-groups {
                    type leafref {
                        path "../../../groups/group/name";
                    }
                    max-elements 8;
                    ordered-by user;
                    description "Apply a configuration group at this level";
                }

            } // container alarms

            container cpm-http-redirect {
                description "Enter the cpm-http-redirect context";

                leaf optimized-mode {
                    type boolean;
                    default "true";
                    description "Enable optimized mode for CPM HTTP redirect messages";
                }

                leaf-list apply-groups {
                    type leafref {
                        path "../../../groups/group/name";
                    }
                    max-elements 8;
                    ordered-by user;
                    description "Apply a configuration group at this level";
                }

            } // container cpm-http-redirect

            container load-balancing {
                description "Enter the load-balancing context";

                leaf l2tp-load-balancing {
                    type boolean;
                    default "false";
                    description "L2TP header load balancing.";
                }

                leaf l4-load-balancing {
                    type boolean;
                    description "Use load balancing based on Layer 4 fields";
                }

                leaf lsr-load-balancing {
                    type enumeration {
                        enum "lbl-only"                     { value 1; }
                        enum "lbl-ip"                       { value 2; }
                        enum "ip-only"                      { value 3; }
                        enum "eth-encap-ip"                 { value 4; }
                        enum "lbl-ip-l4-teid"               { value 5; }
                    }
                    default "lbl-only";
                    description "Hashing algorithm for system-wide LSR load balancing";
                }

                leaf mc-enh-load-balancing {
                    type boolean;
                    default "false";
                    description "Enable enhanced egress multicast load balancing behavior for Layer 3 multicast";
                }

                leaf service-id-lag-hashing {
                    type boolean;
                    default "false";
                    description "Enable enhanced VLL LAG service ID hashing";
                }

                leaf system-ip-load-balancing {
                    type boolean;
                    description "Use the system IP address in the ECMP and LAG load balancing calculation";
                }

                leaf-list apply-groups {
                    type leafref {
                        path "../../../groups/group/name";
                    }
                    max-elements 8;
                    ordered-by user;
                    description "Apply a configuration group at this level";
                }

                container hash-polynomial {
                    description "Enter the hash-polynomial context";

                    leaf ecmp {
                        type types-system:hash-polynomial-type;
                        default "poly1";
                        description "CRC polynomial used in the ECMP hashing.";
                    }

                    leaf lag {
                        type types-system:hash-polynomial-type;
                        default "poly2";
                        description "CRC polynomial used in the LAG hashing.";
                    }

                } // container hash-polynomial

            } // container load-balancing

            list alarm-contact-input {
                key "input-pin-number";
                description "Enter the alarm-contact-input list instance";

                leaf input-pin-number {
                    type int32 {
                        range "1..4";
                    }
                    description "PIN of the alarm contact input";
                }

                leaf admin-state {
                    type types-sros:admin-state;
                    default "disable";
                    description "Administrative state of the alarm contact input";
                }

                leaf description {
                    type types-sros:long-description;
                    description "Text description";
                }

                leaf normal-state {
                    type enumeration {
                        enum "open"                         { value 1; }
                        enum "closed"                       { value 2; }
                    }
                    default "open";
                    description "Alarm normal state";
                }

                leaf trigger-message {
                    type types-sros:description;
                    default "Alarm Input Triggered";
                    description "Text message sent in the log event when input changes";
                }

                leaf clear-message {
                    type types-sros:description;
                    default "Alarm Input Cleared";
                    description "Text message sent in the log event when an alarm clears";
                }

                leaf-list apply-groups {
                    type leafref {
                        path "../../../groups/group/name";
                    }
                    max-elements 8;
                    ordered-by user;
                    description "Apply a configuration group at this level";
                }

            } // list alarm-contact-input

            container dns {
                description "Enter the dns context";

                leaf address-pref {
                    type enumeration {
                        enum "ipv4-only"                    { value 1; }
                        enum "ipv6-first"                   { value 2; }
                    }
                    description "Preference in DNS address resolving order";
                }

                leaf-list apply-groups {
                    type leafref {
                        path "../../../groups/group/name";
                    }
                    max-elements 8;
                    ordered-by user;
                    description "Apply a configuration group at this level";
                }

                container dnssec {
                    description "Enter the dnssec context";

                    leaf ad-validation {
                        type enumeration {
                            enum "fall-through"                 { value 1; description "Allow non-DNSSEC responses to fall-through to permit resolution in case of
                            validation failure."; }
                            enum "drop"                         { value 2; description "Drop non-DNSSEC responses in case of validation failure."; }
                        }
                        description "Response to DNSSEC validation of presence of AD-bit in responses from DNS servers";
                    }

                } // container dnssec

            } // container dns

            container efm-oam {
                description "Enter the efm-oam context";

                leaf dying-gasp-tx-on-reset {
                    type boolean;
                    default "false";
                    description "Generate Information OAM PDU when EFM receives soft reset";
                }

                leaf grace-tx {
                    type boolean;
                    default "false";
                    description "Allow sending of EFM OAM grace period messages";
                }

                leaf-list apply-groups {
                    type leafref {
                        path "../../../groups/group/name";
                    }
                    max-elements 8;
                    ordered-by user;
                    description "Apply a configuration group at this level";
                }

            } // container efm-oam

            container eth-cfm {
                description "Enter the eth-cfm context";

                leaf grace {
                    type boolean;
                    default "true";
                    description "Allow overall system level capability of grace messaging for ETH-CFM MEPs";
                }

                leaf-list apply-groups {
                    type leafref {
                        path "../../../groups/group/name";
                    }
                    max-elements 8;
                    ordered-by user;
                    description "Apply a configuration group at this level";
                }

                container sender-id {
                    description "Enter the sender-id context";

                    leaf type {
                        type types-eth-cfm:chassis-id-subtype;
                        description "ETH-CFM sender ID to be used in CFM PDUs";
                    }

                    leaf local-name {
                        type string {
                            length "1..45";
                        }
                        description "Local name in CFM PDUs";
                    }

                } // container sender-id

                container redundancy {
                    description "Enter the redundancy context";

                    leaf-list apply-groups {
                        type leafref {
                            path "../../../../groups/group/name";
                        }
                        max-elements 8;
                        ordered-by user;
                        description "Apply a configuration group at this level";
                    }

                    container mc-lag {
                        description "Enter the mc-lag context";

                        leaf propagate-hold-time {
                            type union {
                                type int32 {
                                    range "1..60";
                                }
                                type enumeration {
                                    enum "none"                         { value 0; }
                                }
                            }
                            units "seconds";
                            default "1";
                            description "Delay timer value for the fault propagation caused by port, or MC-LAG state changes";
                        }

                        leaf standby-mep {
                            type boolean;
                            default "false";
                            description "Allow MEPs on the standby MC-LAG to act administratively down";
                        }

                    } // container mc-lag

                } // container redundancy

                container slm {
                    description "Enter the slm context";

                    leaf inactivity-timer {
                        type uint32 {
                            range "10..100";
                        }
                        units "seconds";
                        default "100";
                        description "SLR inactivity timer to maintain the stale test data";
                    }

                    leaf-list apply-groups {
                        type leafref {
                            path "../../../../groups/group/name";
                        }
                        max-elements 8;
                        ordered-by user;
                        description "Apply a configuration group at this level";
                    }

                } // container slm

                container md-auto-id {
                    description "Enter the md-auto-id context";

                    container md-index-range {
                        presence "Enter the 'md-index-range' context";
                        description "Enable the md-index-range context";

                        leaf start {
                            type uint32 {
                                range "1..max";
                            }
                            sros-ext:immutable;
                            mandatory true;
                            description "Start of the range";
                        }

                        leaf end {
                            type uint32 {
                                range "1..max";
                            }
                            sros-ext:immutable;
                            mandatory true;
                            description "End of the range";
                        }

                        leaf-list apply-groups {
                            type leafref {
                                path "../../../../../groups/group/name";
                            }
                            max-elements 8;
                            ordered-by user;
                            description "Apply a configuration group at this level";
                        }

                    } // container md-index-range

                    container ma-index-range {
                        presence "Enter the 'ma-index-range' context";
                        description "Enable the ma-index-range context";

                        leaf start {
                            type uint32 {
                                range "1..max";
                            }
                            sros-ext:immutable;
                            mandatory true;
                            description "Start of the range";
                        }

                        leaf end {
                            type uint32 {
                                range "1..max";
                            }
                            sros-ext:immutable;
                            mandatory true;
                            description "End of the range";
                        }

                        leaf-list apply-groups {
                            type leafref {
                                path "../../../../../groups/group/name";
                            }
                            max-elements 8;
                            ordered-by user;
                            description "Apply a configuration group at this level";
                        }

                    } // container ma-index-range

                } // container md-auto-id

            } // container eth-cfm

            container fp {
                description "Enter the fp context";

                leaf-list apply-groups {
                    type leafref {
                        path "../../../groups/group/name";
                    }
                    max-elements 8;
                    ordered-by user;
                    description "Apply a configuration group at this level";
                }

                container options {
                    description "Enter the options context";

                    leaf-list apply-groups {
                        type leafref {
                            path "../../../../groups/group/name";
                        }
                        max-elements 8;
                        ordered-by user;
                        description "Apply a configuration group at this level";
                    }

                    container qos {
                        description "Enter the qos context";

                        container dscp-transparency {
                            description "Enter the dscp-transparency context";

                            leaf admin-state {
                                type types-sros:admin-state;
                                default "enable";
                                description "Administratively enable/disable the DSCP transparency option.";
                            }

                        } // container dscp-transparency

                        container fc-4-profile {
                            description "Enter the fc-4-profile context";

                            leaf admin-state {
                                type types-sros:admin-state;
                                default "disable";
                                description "Administratively enable/disable the fc-4-profile option.";
                            }

                        } // container fc-4-profile

                        container mac-classification-criteria {
                            description "Enter the mac-classification-criteria context";

                            leaf admin-state {
                                type types-sros:admin-state;
                                default "disable";
                                description "Administratively enable/disable the QOS mac classification criteria.";
                            }

                        } // container mac-classification-criteria

                        container ipv6-classification-criteria {
                            description "Enter the ipv6-classification-criteria context";

                            leaf admin-state {
                                type types-sros:admin-state;
                                default "disable";
                                description "Administratively enable/disable the QOS ipv6 classification criteria.";
                            }

                        } // container ipv6-classification-criteria

                        container bum-policers {
                            description "Enter the bum-policers context";

                            leaf admin-state {
                                type types-sros:admin-state;
                                default "disable";
                                description "Administratively enable/disable the QOS bum policers.";
                            }

                        } // container bum-policers

                    } // container qos

                    container mpls {
                        description "Enter the mpls context";

                        container entropy-label {
                            description "Enter the entropy-label context";

                            leaf admin-state {
                                type types-sros:admin-state;
                                default "disable";
                                description "Administratively enable/disable the entropy label option.";
                            }

                        } // container entropy-label

                        container fast-switchover {
                            description "Enter the fast-switchover context";

                            leaf admin-state {
                                type types-sros:admin-state;
                                default "enable";
                                description "Administratively enable/disable the MPLS fast switchover option.";
                            }

                        } // container fast-switchover

                    } // container mpls

                    container service {
                        description "Enter the service context";

                        container vpls-evpn-mpls {
                            description "Enter the vpls-evpn-mpls context";

                            leaf admin-state {
                                type types-sros:admin-state;
                                default "enable";
                                description "Administratively enable/disable the VPLS-EVPN-MPLS option.";
                            }

                        } // container vpls-evpn-mpls

                    } // container service

                    container mac-filter {
                        description "Enter the mac-filter context";

                        container outer-vlan-priority {
                            description "Enter the outer-vlan-priority context";

                            leaf admin-state {
                                type types-sros:admin-state;
                                default "disable";
                                description "Administratively enable/disable the MAC filter outer VLAN priority option.";
                            }

                        } // container outer-vlan-priority

                    } // container mac-filter

                    container router {
                        description "Enter the router context";

                        container ecmp {
                            description "Enter the ecmp context";

                            leaf admin-state {
                                type types-sros:admin-state;
                                default "enable";
                                description "Administratively enable/disable the router ECMP option.";
                            }

                        } // container ecmp

                    } // container router

                } // container options

                container cam-allocation {
                    description "Enter the cam-allocation context";

                    leaf v6-multicast {
                        type uint32 {
                            range "0|512|1024|2048|4096|6144|8192|10240";
                        }
                        default "0";
                        description "Cam bank allocation for v6 multicast configurations.";
                    }

                    leaf-list apply-groups {
                        type leafref {
                            path "../../../../groups/group/name";
                        }
                        max-elements 8;
                        ordered-by user;
                        description "Apply a configuration group at this level";
                    }

                } // container cam-allocation

            } // container fp

            list transmission-profile {
                key "name";
                description "Enter the transmission-profile list instance";

                leaf name {
                    type types-sros:named-item;
                    description "Name of file transmission profile";
                }

                leaf ipv4-source-address {
                    type types-sros:ipv4-unicast-address;
                    description "IPv4 source address of the file transmission connections";
                }

                leaf ipv6-source-address {
                    type types-sros:ipv6-address;
                    description "IPv6 source address of the file transmission connections";
                }

                leaf redirection {
                    type uint32 {
                        range "1..8";
                    }
                    description "Maximum level of redirection";
                }

                leaf retry {
                    type uint32 {
                        range "1..256";
                    }
                    description "Number of attempts to reconnecting to the server";
                }

                leaf router-instance {
                    type types-sros:router-instance-base-management-vprn-loose;
                    default "Base";
                    description "Router instance that hosts the file transmission connection";
                }

                leaf timeout {
                    type uint32 {
                        range "1..3600";
                    }
                    units "seconds";
                    default "60";
                    description "Timeout for a response from the server";
                }

                leaf-list apply-groups {
                    type leafref {
                        path "../../../groups/group/name";
                    }
                    max-elements 8;
                    ordered-by user;
                    description "Apply a configuration group at this level";
                }

            } // list transmission-profile

            container grpc {
                description "Enter the grpc context";

                leaf admin-state {
                    type types-sros:admin-state;
                    default "disable";
                    description "Administrative state of gRPC server";
                }

                leaf max-msg-size {
                    type uint32 {
                        range "1..1024";
                    }
                    units "megabytes";
                    default "512";
                    description "Maximum size of received message";
                }

                leaf-list apply-groups {
                    type leafref {
                        path "../../../groups/group/name";
                    }
                    max-elements 8;
                    ordered-by user;
                    description "Apply a configuration group at this level";
                }

                choice transport {
                    case tls-server-profile {

                        leaf tls-server-profile {
                            type leafref {
                                path "../../security/tls/server-tls-profile/server-profile-name";
                            }
                            description "Preferred TLS server profile";
                        }

                    }
                    case allow-unsecure-connection {

                        leaf allow-unsecure-connection {
                            type empty;
                            description "Run gRPC server without secured transport protocol";
                        }

                    }
                }
                container tcp-keepalive {
                    description "Enter the tcp-keepalive context";

                    leaf admin-state {
                        type types-sros:admin-state;
                        default "disable";
                        description "Administrative state of the TCP keepalive algorithm";
                    }

                    leaf idle-time {
                        type types-sros:time-duration {
                            range "1..100000";
                        }
                        units "seconds";
                        default "600";
                        description "Seconds until the first TCP keepalive probe is sent";
                    }

                    leaf interval {
                        type types-sros:time-duration {
                            range "1..100000";
                        }
                        units "seconds";
                        default "15";
                        description "Seconds between TCP keep-alive probes";
                    }

                    leaf retries {
                        type uint32 {
                            range "3..100";
                        }
                        default "4";
                        description "Missed keepalives before the TCP connection is closed";
                    }

                } // container tcp-keepalive

                container gnmi {
                    description "Enter the gnmi context";

                    leaf admin-state {
                        type types-sros:admin-state;
                        default "enable";
                        description "Administrative state of gNMI service";
                    }

                    leaf auto-config-save {
                        type boolean;
                        default "false";
                        description "Automatically save the configuration";
                    }

                } // container gnmi

                container gnoi {
                    description "Enter the gnoi context";

                    container cert-mgmt {
                        description "Enter the cert-mgmt context";

                        leaf admin-state {
                            type types-sros:admin-state;
                            default "disable";
                            description "Administrative state of gNOI CertificateManagement service.";
                        }

                    } // container cert-mgmt

                    container system {
                        description "Enter the system context";

                        leaf admin-state {
                            type types-sros:admin-state;
                            default "disable";
                            description "Administrative state of gNOI System service.";
                        }

                    } // container system

                } // container gnoi

                container md-cli {
                    description "Enter the md-cli context";

                    leaf admin-state {
                        type types-sros:admin-state;
                        default "disable";
                        description "Administrative state of the MD-CLI service";
                    }

                } // container md-cli

                container rib-api {
                    description "Enter the rib-api context";

                    leaf admin-state {
                        type types-sros:admin-state;
                        default "disable";
                        description "Administrative state of RibAPI service";
                    }

                    leaf purge-timeout {
                        type types-sros:time-duration {
                            range "1..100000";
                        }
                        units "seconds";
                        description "Number of seconds until stale entries are purged";
                    }

                } // container rib-api

            } // container grpc

            container management-interface {
                description "Enter the management-interface context";

                leaf configuration-mode {
                    type enumeration {
                        enum "classic"                      { value 1; }
                        enum "model-driven"                 { value 2; }
                        enum "mixed"                        { value 3; }
                    }
                    default "classic";
                    description "Mode of the management interface configuration in the system";
                }

                leaf schema-path {
                    type types-sros:url;
                    description "Schema path URL";
                }

                leaf-list apply-groups {
                    type leafref {
                        path "../../../groups/group/name";
                    }
                    max-elements 8;
                    ordered-by user;
                    description "Apply a configuration group at this level";
                }

                container cli {
                    description "Enter the cli context";

                    leaf-list cli-engine {
                        type types-system:cli-engine-type;
                        max-elements 2;
                        ordered-by user;
                        description "System wide CLI engine access";
                    }

                    leaf-list apply-groups {
                        type leafref {
                            path "../../../../groups/group/name";
                        }
                        max-elements 8;
                        ordered-by user;
                        description "Apply a configuration group at this level";
                    }

                    container classic-cli {
                        description "Enter the classic-cli context";

                        leaf allow-immediate {
                            type boolean;
                            default "true";
                            description "Allow writable access in the classic CLI configure branch";
                        }

                        container rollback {
                            description "Enter the rollback context";

                            leaf location {
                                type types-sros:url;
                                description "Location and filename of the rollback checkpoint files";
                            }

                            leaf local-checkpoints {
                                type uint32 {
                                    range "1..50";
                                }
                                default "10";
                                description "Maximum number of rollback files on compact flash";
                            }

                            leaf remote-checkpoints {
                                type uint32 {
                                    range "1..200";
                                }
                                default "10";
                                description "Maximum number of rollback files saved at a remote location";
                            }

                            leaf-list apply-groups {
                                type leafref {
                                    path "../../../../../../groups/group/name";
                                }
                                max-elements 8;
                                ordered-by user;
                                description "Apply a configuration group at this level";
                            }

                            container rescue {
                                description "Enter the rescue context";

                                leaf location {
                                    type types-sros:url;
                                    description "Location of the rollback rescue file";
                                }

                            } // container rescue

                        } // container rollback

                    } // container classic-cli

                    container md-cli {
                        description "Enter the md-cli context";

                        leaf auto-config-save {
                            type boolean;
                            default "false";
                            description "Automatically save the configuration";
                        }

                        leaf command-accounting-during-load {
                            type boolean;
                            default "true";
                            description "Perform remote command accounting during a load or rollback operation";
                        }

                        leaf-list apply-groups {
                            type leafref {
                                path "../../../../../groups/group/name";
                            }
                            max-elements 8;
                            ordered-by user;
                            description "Apply a configuration group at this level";
                        }

                        container environment {
                            description "Enter the environment context";

                            leaf more {
                                type boolean;
                                default "true";
                                description "Prompt to continue or stop when output text fills page";
                            }

                            leaf time-display {
                                type enumeration {
                                    enum "local"                        { value 1; }
                                    enum "utc"                          { value 2; }
                                }
                                default "local";
                                description "Time zone displayed before the prompt";
                            }

                            leaf time-format {
                                type enumeration {
                                    enum "iso-8601"                     { value 1; }
                                    enum "rfc-1123"                     { value 2; }
                                    enum "rfc-3339"                     { value 3; }
                                }
                                default "rfc-3339";
                                description "Time format to display date and time";
                            }

                            container command-completion {
                                description "Enter the command-completion context";

                                leaf enter {
                                    type boolean;
                                    default "true";
                                    description "Complete the command when the enter key is pressed";
                                }

                                leaf space {
                                    type boolean;
                                    default "true";
                                    description "Complete the command when the space key is pressed";
                                }

                                leaf tab {
                                    type boolean;
                                    default "true";
                                    description "Complete the command when the tab key is pressed";
                                }

                            } // container command-completion

                            container console {
                                description "Enter the console context";

                                leaf length {
                                    type uint32 {
                                        range "24..512";
                                    }
                                    default "24";
                                    description "Number of lines displayed on the screen";
                                }

                                leaf width {
                                    type uint32 {
                                        range "80..512";
                                    }
                                    default "80";
                                    description "Number of columns displayed on the screen";
                                }

                            } // container console

                            container message-severity-level {
                                description "Enter the message-severity-level context";

                                leaf cli {
                                    type enumeration {
                                        enum "warning"                      { value 6; }
                                        enum "info"                         { value 7; }
                                    }
                                    default "info";
                                    description "Message severity threshold for CLI messages";
                                }

                            } // container message-severity-level

                            container progress-indicator {
                                description "Enter the progress-indicator context";

                                leaf admin-state {
                                    type types-sros:admin-state;
                                    default "enable";
                                    description "Administrative state of the progress indicator";
                                }

                                leaf type {
                                    type enumeration {
                                        enum "dots"                         { value 1; }
                                    }
                                    default "dots";
                                    description "Progress indicator output style";
                                }

                                leaf delay {
                                    type uint32 {
                                        range "0..10000";
                                    }
                                    units "milliseconds";
                                    default "1000";
                                    description "Delay before progress indicator is displayed";
                                }

                            } // container progress-indicator

                            container prompt {
                                description "Enter the prompt context";

                                leaf context {
                                    type boolean;
                                    default "true";
                                    description "Show the current command context in the prompt";
                                }

                                leaf newline {
                                    type boolean;
                                    default "true";
                                    description "Add a new line before every prompt line";
                                }

                                leaf timestamp {
                                    type boolean;
                                    default "false";
                                    description "Show the timestamp before the first prompt line";
                                }

                                leaf uncommitted-changes-indicator {
                                    type boolean;
                                    default "true";
                                    description "Show an asterisk (*) when uncommitted changes exist";
                                }

                            } // container prompt

                        } // container environment

                    } // container md-cli

                } // container cli

                container configuration-save {
                    description "Enter the configuration-save context";

                    leaf configuration-backups {
                        type uint32 {
                            range "1..200";
                        }
                        default "5";
                        description "Maximum number of backup versions maintained";
                    }

                    leaf-list apply-groups {
                        type leafref {
                            path "../../../../groups/group/name";
                        }
                        max-elements 8;
                        ordered-by user;
                        description "Apply a configuration group at this level";
                    }

                } // container configuration-save

                container netconf {
                    description "Enter the netconf context";

                    leaf admin-state {
                        type types-sros:admin-state;
                        default "disable";
                        description "Administrative state of NETCONF";
                    }

                    leaf port {
                        type uint32 {
                            range "22|830";
                        }
                        default "830";
                        description "Choose port on which the NETCONF server will listen for new connections.";
                    }

                    leaf auto-config-save {
                        type boolean;
                        default "false";
                        description "Automatically save the configuration";
                    }

                    leaf-list apply-groups {
                        type leafref {
                            path "../../../../groups/group/name";
                        }
                        max-elements 8;
                        ordered-by user;
                        description "Apply a configuration group at this level";
                    }

                    container capabilities {
                        description "Enter the capabilities context";

                        leaf candidate {
                            type boolean;
                            default "true";
                            description "Allow the NETCONF server to access the candidate datastore";
                        }

                        leaf writable-running {
                            type boolean;
                            default "false";
                            description "Allow the NETCONF server to access the writable running datastore";
                        }

                    } // container capabilities

                } // container netconf

                container remote-management {
                    description "Enter the remote-management context";

                    leaf admin-state {
                        type types-sros:admin-state;
                        default "disable";
                        description "Administrative state of remote management registration";
                    }

                    leaf connection-timeout {
                        type uint32 {
                            range "1..3600";
                        }
                        units "seconds";
                        default "60";
                        description "Max time without response before manager declared down";
                    }

                    leaf hello-interval {
                        type types-sros:time-duration {
                            range "10..3600";
                        }
                        units "minutes";
                        default "10";
                        description "Time between hello messages from SR OS node to manager";
                    }

                    leaf router-instance {
                        type string;
                        default "management";
                        description "Reference to a router or VPRN service name";
                    }

                    leaf device-label {
                        type types-sros:named-item-64;
                        description "Device label supplied to the remote manager";
                    }

                    leaf device-name {
                        type types-sros:named-item-64;
                        description "Device name supplied to the remote manager";
                    }

                    leaf source-address {
                        type types-sros:ip-address;
                        description "Source IP address for connection to the manager";
                    }

                    leaf source-port {
                        type types-system:remote-mgmt-registration-port;
                        default "grpc-default";
                        description "Source TCP port number to connection to the manager";
                    }

                    leaf-list apply-groups {
                        type leafref {
                            path "../../../../groups/group/name";
                        }
                        max-elements 8;
                        ordered-by user;
                        description "Apply a configuration group at this level";
                    }

                    choice transport {
                        case client-tls-profile {

                            leaf client-tls-profile {
                                type leafref {
                                    path "../../../security/tls/client-tls-profile/client-profile-name";
                                }
                                description "TLS client profile name";
                            }

                        }
                        case allow-unsecure-connection {

                            leaf allow-unsecure-connection {
                                type empty;
                                description "Allow remote management without secured gRPC protocol";
                            }

                        }
                    }
                    list manager {
                        key "manager-name";
                        max-elements 2;
                        description "Enter the manager list instance";

                        leaf manager-name {
                            type types-sros:named-item-64;
                            description "Remote management manager name";
                        }

                        leaf admin-state {
                            type types-sros:admin-state;
                            default "disable";
                            description "Administrative state of remote management registration";
                        }

                        leaf connection-timeout {
                            type uint32 {
                                range "1..3600";
                            }
                            units "seconds";
                            description "Max time without response before manager declared down";
                        }

                        leaf description {
                            type types-sros:description;
                            description "Text description";
                        }

                        leaf manager-address {
                            type union {
                                type types-sros:ip-address;
                                type types-sros:fully-qualified-domain-name;
                            }
                            mandatory true;
                            description "Destination IP address of the manager";
                        }

                        leaf manager-port {
                            type types-sros:tcp-udp-port-non-zero;
                            default "57400";
                            description "TCP port for gRPC connections to manager";
                        }

                        leaf router-instance {
                            type string;
                            description "Reference to a router or VPRN service name";
                        }

                        leaf device-label {
                            type types-sros:named-item-64;
                            description "Device label supplied to the remote manager";
                        }

                        leaf device-name {
                            type types-sros:named-item-64;
                            description "Device name supplied to the remote manager";
                        }

                        leaf source-address {
                            type types-sros:ip-address;
                            description "Source IP address for connection to the manager";
                        }

                        leaf source-port {
                            type types-system:remote-mgmt-registration-port;
                            description "Source TCP destination port number";
                        }

                        leaf-list apply-groups {
                            type leafref {
                                path "../../../../../groups/group/name";
                            }
                            max-elements 8;
                            ordered-by user;
                            description "Apply a configuration group at this level";
                        }

                        choice transport {
                            case client-tls-profile {

                                leaf client-tls-profile {
                                    type leafref {
                                        path "../../../../security/tls/client-tls-profile/client-profile-name";
                                    }
                                    description "TLS client profile name";
                                }

                            }
                            case allow-unsecure-connection {

                                leaf allow-unsecure-connection {
                                    type empty;
                                    description "Allow manager connection without secured gRPC protocol";
                                }

                            }
                        }
                    } // list manager

                } // container remote-management

                container yang-modules {
                    description "Enter the yang-modules context";

                    leaf base-r13-modules {
                        type boolean;
                        default "false";
                        description "Support base release 13 YANG models";
                    }

                    leaf nokia-modules {
                        type boolean;
                        description "Support Nokia YANG models";
                    }

                    leaf openconfig-modules {
                        type boolean;
                        default "false";
                        description "Support OpenConfig YANG models";
                    }

                    leaf nokia-combined-modules {
                        type boolean;
                        description "Support access to combined Nokia YANG models";
                    }

                    leaf-list apply-groups {
                        type leafref {
                            path "../../../../groups/group/name";
                        }
                        max-elements 8;
                        ordered-by user;
                        description "Apply a configuration group at this level";
                    }

                } // container yang-modules

                container snmp {
                    description "Enter the snmp context";

                    leaf engine-id {
                        type types-system:engine-id-as-string;
                        description "SNMP engine ID to uniquely identify the SNMPv3 node";
                    }

                    leaf general-port {
                        type types-sros:tcp-udp-port;
                        default "161";
                        description "Port number to be used to send general SNMP messages.";
                    }

                    leaf packet-size {
                        type int32 {
                            range "484..9216";
                        }
                        default "1500";
                        description "Max size SNMP packet generated by this node.";
                    }

                    leaf admin-state {
                        type types-sros:admin-state;
                        default "enable";
                        description "Administrative state of the SNMP daemon";
                    }

                    leaf-list apply-groups {
                        type leafref {
                            path "../../../../groups/group/name";
                        }
                        max-elements 8;
                        ordered-by user;
                        description "Apply a configuration group at this level";
                    }

                    container streaming {
                        description "Enter the streaming context";

                        leaf admin-state {
                            type types-sros:admin-state;
                            default "disable";
                            description "Administrative state of the streaming daemon";
                        }

                        leaf-list apply-groups {
                            type leafref {
                                path "../../../../../groups/group/name";
                            }
                            max-elements 8;
                            ordered-by user;
                            description "Apply a configuration group at this level";
                        }

                    } // container streaming

                } // container snmp

            } // container management-interface

            container thresholds {
                description "Enter the thresholds context";

                list cflash-cap-alarm-percent {
                    key "cflash-id";
                    description "Enter the cflash-cap-alarm-percent list instance";

                    leaf cflash-id {
                        type types-sros:thresholds-cflash-url;
                        description "Capacity that monitors the cflash (compact flash) assigned in this command";
                    }

                    leaf rising-threshold {
                        type int32 {
                            range "0..100";
                        }
                        units "percent";
                        mandatory true;
                        description "Specifies the rising threshold percentage value for sampled statistics of cflash capacity alarm entry.";
                    }

                    leaf falling-threshold {
                        type int32 {
                            range "0..100";
                        }
                        units "percent";
                        description "Specifies the falling threshold percentage value for sampled statistics of cflash capacity alarm entry.";
                    }

                    leaf interval {
                        type int32 {
                            range "1..2147483647";
                        }
                        mandatory true;
                        description "Polling period over which data is sampled and compared";
                    }

                    leaf rmon-event-type {
                        type types-system:threshold-event-type;
                        description "Notification type specifying action when event occurs";
                    }

                    leaf startup-alarm {
                        type types-system:threshold-startup-alarm;
                        description "Alarm type when the alarm is first created";
                    }

                    leaf-list apply-groups {
                        type leafref {
                            path "../../../../groups/group/name";
                        }
                        max-elements 8;
                        ordered-by user;
                        description "Apply a configuration group at this level";
                    }

                } // list cflash-cap-alarm-percent

                list cflash-cap-warn-percent {
                    key "cflash-id";
                    description "Enter the cflash-cap-warn-percent list instance";

                    leaf cflash-id {
                        type types-sros:thresholds-cflash-url;
                        description "Capacity that monitors the cflash (compact flash) assigned in this command";
                    }

                    leaf rising-threshold {
                        type int32 {
                            range "0..100";
                        }
                        units "percent";
                        mandatory true;
                        description "Specifies the rising threshold percentage value for sampled statistics of cflash capacity alarm entry.";
                    }

                    leaf falling-threshold {
                        type int32 {
                            range "0..100";
                        }
                        units "percent";
                        description "Specifies the falling threshold percentage value for sampled statistics of cflash capacity alarm entry.";
                    }

                    leaf interval {
                        type int32 {
                            range "1..2147483647";
                        }
                        mandatory true;
                        description "Polling period over which data is sampled and compared";
                    }

                    leaf rmon-event-type {
                        type types-system:threshold-event-type;
                        description "Notification type specifying action when event occurs";
                    }

                    leaf startup-alarm {
                        type types-system:threshold-startup-alarm;
                        description "Alarm type when the alarm is first created";
                    }

                    leaf-list apply-groups {
                        type leafref {
                            path "../../../../groups/group/name";
                        }
                        max-elements 8;
                        ordered-by user;
                        description "Apply a configuration group at this level";
                    }

                } // list cflash-cap-warn-percent

                container kb-memory-use-alarm {
                    presence "Enter the 'kb-memory-use-alarm' context";
                    description "Enable the kb-memory-use-alarm context";

                    leaf rising-threshold {
                        type int64 {
                            range "-2147483648..2147483647";
                        }
                        mandatory true;
                        description "Specifies the threshold for the sampled statistic for the rising threshold event.";
                    }

                    leaf falling-threshold {
                        type int64 {
                            range "-2147483648..2147483647";
                        }
                        description "Specifies the threshold for the sampled statistic for the falling threshold event.";
                    }

                    leaf interval {
                        type int32 {
                            range "1..2147483647";
                        }
                        mandatory true;
                        description "Polling period over which data is sampled and compared";
                    }

                    leaf rmon-event-type {
                        type types-system:threshold-event-type;
                        description "Notification type specifying action when event occurs";
                    }

                    leaf startup-alarm {
                        type types-system:threshold-startup-alarm;
                        description "Alarm type when the alarm is first created";
                    }

                    leaf-list apply-groups {
                        type leafref {
                            path "../../../../groups/group/name";
                        }
                        max-elements 8;
                        ordered-by user;
                        description "Apply a configuration group at this level";
                    }

                } // container kb-memory-use-alarm

                container kb-memory-use-warn {
                    presence "Enter the 'kb-memory-use-warn' context";
                    description "Enable the kb-memory-use-warn context";

                    leaf rising-threshold {
                        type int64 {
                            range "-2147483648..2147483647";
                        }
                        mandatory true;
                        description "Specifies the threshold for the sampled statistic for the rising threshold event.";
                    }

                    leaf falling-threshold {
                        type int64 {
                            range "-2147483648..2147483647";
                        }
                        description "Specifies the threshold for the sampled statistic for the falling threshold event.";
                    }

                    leaf interval {
                        type int32 {
                            range "1..2147483647";
                        }
                        mandatory true;
                        description "Polling period over which data is sampled and compared";
                    }

                    leaf rmon-event-type {
                        type types-system:threshold-event-type;
                        description "Notification type specifying action when event occurs";
                    }

                    leaf startup-alarm {
                        type types-system:threshold-startup-alarm;
                        description "Alarm type when the alarm is first created";
                    }

                    leaf-list apply-groups {
                        type leafref {
                            path "../../../../groups/group/name";
                        }
                        max-elements 8;
                        ordered-by user;
                        description "Apply a configuration group at this level";
                    }

                } // container kb-memory-use-warn

                container rmon {
                    description "Enter the rmon context";

                    list alarm {
                        key "rmon-alarm-id";
                        max-elements 1200;
                        description "Enter the alarm list instance";

                        leaf rmon-alarm-id {
                            type uint32 {
                                range "0..65400";
                            }
                            description "Index ID for an entry in the alarm table";
                        }

                        leaf variable-oid {
                            type string {
                                length "1..255";
                            }
                            mandatory true;
                            description "Object identifier to sample the specific variable";
                        }

                        leaf interval {
                            type int32 {
                                range "1..2147483647";
                            }
                            mandatory true;
                            description "Polling period over which data is sampled and compared";
                        }

                        leaf sample-type {
                            type types-system:threshold-sample;
                            description "Method to sample the selected variable and calculate the value comparing against the thresholds";
                        }

                        leaf startup-alarm {
                            type types-system:threshold-startup-alarm;
                            description "Alarm to send when this entry is first set to valid";
                        }

                        leaf rising-event {
                            type uint32 {
                                range "0..65400";
                            }
                            description "RMON event ID used when a rising event threshold event occurs";
                        }

                        leaf falling-event {
                            type uint32 {
                                range "0..65400";
                            }
                            description "RMON event ID used when a falling threshold crossing event occurs";
                        }

                        leaf rising-threshold {
                            type int64 {
                                range "-2147483648..2147483647";
                            }
                            description "Specifies the threshold for the sampled statistic for the rising threshold event.";
                        }

                        leaf falling-threshold {
                            type int64 {
                                range "-2147483648..2147483647";
                            }
                            description "Specifies the threshold for the sampled statistic for the falling threshold event.";
                        }

                        leaf owner {
                            type string {
                                length "1..80";
                            }
                            default "TiMOS CLI";
                            description "Owner that created this entry and uses the resources";
                        }

                        leaf-list apply-groups {
                            type leafref {
                                path "../../../../../groups/group/name";
                            }
                            max-elements 8;
                            ordered-by user;
                            description "Apply a configuration group at this level";
                        }

                    } // list alarm

                    list event {
                        key "rmon-event-id";
                        max-elements 1200;
                        description "Enter the event list instance";

                        leaf rmon-event-id {
                            type uint32 {
                                range "1..65400";
                            }
                            description "Index ID for an entry in the event table";
                        }

                        leaf event-type {
                            type types-system:threshold-rmon-event-type;
                            description "Type of notification action to be taken when this event occurs";
                        }

                        leaf description {
                            type types-sros:description;
                            description "Text description";
                        }

                        leaf owner {
                            type string {
                                length "1..80";
                            }
                            default "TiMOS CLI";
                            description "Owner that created this entry and uses the resources";
                        }

                        leaf-list apply-groups {
                            type leafref {
                                path "../../../../../groups/group/name";
                            }
                            max-elements 8;
                            ordered-by user;
                            description "Apply a configuration group at this level";
                        }

                    } // list event

                } // container rmon

            } // container thresholds

            container ip {
                description "Enter the ip context";

                leaf allow-qinq-network-interface {
                    type boolean;
                    default "false";
                    description "Allow QinQ encapsulation for network interfaces";
                }

                leaf enforce-unique-if-index {
                    type boolean;
                    default "false";
                    description "Create IP interface indexes that are globally unique";
                }

                leaf mpls-tunnel-mode {
                    type types-sros:mpls-tunnel-mode;
                    default "uniform";
                    description "Specifies the MPLS tunnel mode.";
                }

                leaf forward-6in4 {
                    type boolean;
                    default "false";
                    description "Allows the 6in4 forwarding of traffic sent to the system IP address.";
                }

                leaf forward-ip-over-gre {
                    type boolean;
                    default "false";
                    description "Allows the forwarding of IP traffic encapsulated in GRE transport sent to the system IP address.";
                }

                leaf ipv6-eh {
                    type enumeration {
                        enum "max"                          { value 1; }
                        enum "limited"                      { value 2; }
                    }
                    default "max";
                    description "Limit the number of IPv6 extension headers processed ingress/egress.";
                }

                leaf-list apply-groups {
                    type leafref {
                        path "../../../groups/group/name";
                    }
                    max-elements 8;
                    ordered-by user;
                    description "Apply a configuration group at this level";
                }

                container mpls {
                    description "Enter the mpls context";

                    leaf label-stack-statistics-count {
                        type uint32 {
                            range "1..2";
                        }
                        default "1";
                        description "Specifies the MPLS label stack statistics count.";
                    }

                } // container mpls

            } // container ip

            container lacp {
                description "Enter the lacp context";

                leaf system-priority {
                    type uint32 {
                        range "1..65535";
                    }
                    default "32768";
                    description "Set the LACP system priority";
                }

                leaf-list apply-groups {
                    type leafref {
                        path "../../../groups/group/name";
                    }
                    max-elements 8;
                    ordered-by user;
                    description "Apply a configuration group at this level";
                }

            } // container lacp

            container lldp {
                description "Enter the lldp context";

                leaf tx-credit-max {
                    type int32 {
                        range "1..100";
                    }
                    default "5";
                    description "Maximum consecutive LLDPDUs to be transmitted";
                }

                leaf message-fast-tx {
                    type int32 {
                        range "1..3600";
                    }
                    units "seconds";
                    default "1";
                    description "Interval at which LLDP frames are transmitted";
                }

                leaf message-fast-tx-init {
                    type int32 {
                        range "1..8";
                    }
                    default "4";
                    description "Number of PDUs to transmit during a fast transmission period";
                }

                leaf admin-state {
                    type types-sros:admin-state;
                    default "enable";
                    description "Administrative state of LLDP";
                }

                leaf tx-interval {
                    type int32 {
                        range "5..32768";
                    }
                    units "seconds";
                    default "30";
                    description "Interval at which LLDP frames are transmitted";
                }

                leaf tx-hold-multiplier {
                    type int32 {
                        range "2..10";
                    }
                    default "4";
                    description "LLDP transmit interval time";
                }

                leaf reinit-delay {
                    type int32 {
                        range "1..10";
                    }
                    units "seconds";
                    default "2";
                    description "Time required before reinitializing LLDP on a port";
                }

                leaf notification-interval {
                    type int32 {
                        range "5..3600";
                    }
                    units "seconds";
                    default "5";
                    description "Transmission interval of LLDP notifications";
                }

                leaf-list apply-groups {
                    type leafref {
                        path "../../../groups/group/name";
                    }
                    max-elements 8;
                    ordered-by user;
                    description "Apply a configuration group at this level";
                }

            } // container lldp

            container l2tp {
                description "Enter the l2tp context";

                leaf-list apply-groups {
                    type leafref {
                        path "../../../groups/group/name";
                    }
                    max-elements 8;
                    ordered-by user;
                    description "Apply a configuration group at this level";
                }

                container non-multi-chassis-tunnel-id-range {
                    description "Enter the non-multi-chassis-tunnel-id-range context";

                    leaf start {
                        type types-l2tp:loc-tunnel-id-or-zero;
                        default "1";
                        description "Start value of range";
                    }

                    leaf end {
                        type types-l2tp:loc-tunnel-id-or-zero;
                        default "16383";
                        description "End value of the range";
                    }

                } // container non-multi-chassis-tunnel-id-range

            } // container l2tp

            list power-management {
                key "power-zone";
                description "Enter the power-management list instance";

                leaf power-zone {
                    type uint32 {
                        range "1..2";
                    }
                    description "Power mode";
                }

                leaf mode {
                    type enumeration {
                        enum "none"                         { value 0; }
                        enum "basic"                        { value 1; }
                        enum "advanced"                     { value 2; }
                    }
                    default "basic";
                    description "Power capacity mode algorithm";
                }

                leaf power-safety-alert {
                    type uint32 {
                        range "0..120000";
                    }
                    units "watts";
                    default "0";
                    description "Power capacity to trigger a safety alert event";
                }

                leaf power-safety-level {
                    type yang:gauge32 {
                        range "0..100";
                    }
                    units "percent";
                    default "100";
                    description "Minimum threshold to power off devices";
                }

                leaf-list apply-groups {
                    type leafref {
                        path "../../../groups/group/name";
                    }
                    max-elements 8;
                    ordered-by user;
                    description "Apply a configuration group at this level";
                }

            } // list power-management

            container dhcp6 {
                description "Enter the dhcp6 context";

                leaf-list adv-noaddrs-global {
                    type enumeration {
                        enum "esm-relay"                    { value 1; }
                        enum "server"                       { value 2; }
                    }
                    max-elements 2;
                    description "Specifies the composition of DHCPv6 Advertise Messages in case a DHCP6 application in this system will not assign any addresses to any Identity Association (IA) in a subsequent Request from the client. DHCP6 applications in this system are Server and ESM Relay, which must be set together.";
                }

                leaf-list apply-groups {
                    type leafref {
                        path "../../../groups/group/name";
                    }
                    max-elements 8;
                    ordered-by user;
                    description "Apply a configuration group at this level";
                }

            } // container dhcp6

            list software-repository {
                key "repository-name";
                description "Enter the software-repository list instance";

                leaf repository-name {
                    type types-sros:named-item;
                    description "Unique name for the system software repository";
                }

                leaf description {
                    type types-sros:description;
                    description "Text description";
                }

                leaf primary-location {
                    type string {
                        length "1..180";
                    }
                    description "Primary location for the files in the software repository";
                }

                leaf secondary-location {
                    type string {
                        length "1..180";
                    }
                    description "Secondary location for the files in the software repository";
                }

                leaf tertiary-location {
                    type string {
                        length "1..180";
                    }
                    description "Tertiary location for the files in the software repository";
                }

                leaf-list apply-groups {
                    type leafref {
                        path "../../../groups/group/name";
                    }
                    max-elements 8;
                    ordered-by user;
                    description "Apply a configuration group at this level";
                }

            } // list software-repository

            container resource {
                description "Enter the resource context";

                list ecmp-profile {
                    key "profile-id";
                    description "Enter the ecmp-profile list instance";

                    leaf profile-id {
                        type uint32 {
                            range "1..2";
                        }
                        description "The ecmp-profile identifier.";
                    }

                    leaf type {
                        type enumeration {
                            enum "mpls"                         { value 1; }
                            enum "ip"                           { value 2; }
                        }
                        sros-ext:immutable;
                        mandatory true;
                        description "Specifies the ECMP bundle type applicable to this profile.";
                    }

                    leaf links {
                        type uint32 {
                            range "1..16";
                        }
                        mandatory true;
                        description "Specifies the maximum number of links per group for the ECMP bundle.";
                    }

                    leaf groups {
                        type uint32 {
                            range "1..2048";
                        }
                        mandatory true;
                        description "Specifies the maximum number of groups allowed for the ECMP bundle. When type is 'mpls', the maximum value for group is 2047. When type is 'ip', the maximum value for group is 2048.";
                    }

                    leaf-list apply-groups {
                        type leafref {
                            path "../../../../groups/group/name";
                        }
                        max-elements 8;
                        ordered-by user;
                        description "Apply a configuration group at this level";
                    }

                } // list ecmp-profile

            } // container resource

            container switch-fabric {
                description "Enter the switch-fabric context";

                leaf sfm-loss-threshold {
                    type uint32 {
                        range "1..7";
                    }
                    description "Number of SFMs that can fail before SFM overload state";
                }

                leaf-list apply-groups {
                    type leafref {
                        path "../../../groups/group/name";
                    }
                    max-elements 8;
                    ordered-by user;
                    description "Apply a configuration group at this level";
                }

            } // container switch-fabric

            uses conf-system-bluetooth;
            uses conf-system-central-frequency-clock;
            uses conf-system-cron;
            uses conf-system-login-control;
            uses conf-system-ned-network-element-discovery;
            uses conf-system-persistence;
            uses conf-system-script-control;
            uses conf-system-security;
            uses conf-system-telemetry;
            uses conf-system-time;
        } // container system

    } // grouping conf-system

}
