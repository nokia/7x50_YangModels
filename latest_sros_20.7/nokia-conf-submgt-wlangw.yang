submodule nokia-conf-submgt-wlangw {

    yang-version "1.1";

    belongs-to nokia-conf { prefix "conf"; }

    import nokia-sros-yang-extensions     { prefix "sros-ext"; }
    import nokia-types-isa                { prefix "types-isa"; }
    import nokia-types-nat                { prefix "types-nat"; }
    import nokia-types-sros               { prefix "types-sros"; }
    import nokia-types-wlangw             { prefix "types-wlangw"; }

    include nokia-conf-groups;

    sros-ext:sros-major-release "rel20";

    organization "Nokia";

    contact
        "Nokia SR OS Support
         Web: <http://www.nokia.com>";

    description
        "Nokia YANG Data model to configure subscriber management WLAN Gateway on SR OS based routers.

         Copyright 2016 Nokia. All rights reserved. Reproduction of this document
         is authorized on the condition that the foregoing copyright notice is included.

         This nokia-conf-submgt-wlangw YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";

    revision "2020-02-03";

    grouping conf-submgt-wlangw-wlan-gw {
        container wlan-gw {
            description "Enter the wlan-gw context";

            leaf virtual-chassis-identifier {
                type types-sros:string-not-all-spaces {
                    length "1..16";
                }
                description "WLAN Gateway virtual chassis ID or dual homing key";
            }

            leaf-list apply-groups {
                type leafref {
                    path "../../../groups/group/name";
                }
                max-elements 8;
                ordered-by user;
                description "Apply a configuration group at this level";
            }

            container queries {
                description "Enter the queries context";

                leaf-list apply-groups {
                    type leafref {
                        path "../../../../groups/group/name";
                    }
                    max-elements 8;
                    ordered-by user;
                    description "Apply a configuration group at this level";
                }

                list ue {
                    key "name";
                    max-elements 1024;
                    description "Enter the ue list instance";

                    leaf name {
                        type types-sros:named-item;
                        description "Textual identification for the UE query";
                    }

                    leaf bridge-domain {
                        type uint32 {
                            range "0..4294967294";
                        }
                        description "When specified, the query will only return UEs in this Bridge Domain";
                    }

                    leaf mac-address {
                        type types-sros:mac-address;
                        description "When specified, the query will only return the UE having this MAC address";
                    }

                    leaf vlan {
                        type types-sros:qtag-full-range;
                        description "When specified, the query will only return UEs for which the VLAN tag is present in the traffic received from the UE";
                    }

                    leaf-list apply-groups {
                        type leafref {
                            path "../../../../../groups/group/name";
                        }
                        max-elements 8;
                        ordered-by user;
                        description "Apply a configuration group at this level";
                    }

                    container address {
                        description "Enter the address context";

                        leaf type {
                            type types-wlangw:ue-address-type;
                            description "When specified, the query will only return UEs with this address type";
                        }

                        leaf ipv4 {
                            type types-sros:ipv4-unicast-address;
                            description "When specified, the query will only return UEs having this IPv4 address";
                        }

                        leaf dhcp6-na {
                            type types-sros:ipv6-unicast-without-local-address;
                            description "When specified, the query will only return UEs having this DHCPv6 address";
                        }

                        leaf slaac {
                            type types-sros:ipv6-unicast-without-local-address;
                            description "When specified, the query will only return UEs having this SLAAC prefix";
                        }

                    } // container address

                    container connection-state {
                        presence "Enter the 'connection-state' context";
                        description "Enable the connection-state context";

                        leaf data-triggered {
                            type boolean;
                            default "true";
                            description "Controls whether the query returns UEs in data-triggered state";
                        }

                        leaf dhcp-triggered {
                            type boolean;
                            default "true";
                            description "Controls whether the query returns UEs in DHCP-triggered state";
                        }

                        leaf ip-assigned {
                            type boolean;
                            default "true";
                            description "Controls whether the query returns UEs in IP-assigned state";
                        }

                        leaf authorized-only {
                            type boolean;
                            default "true";
                            description "Controls whether the query returns UEs in authorized-only state";
                        }

                        leaf ip-assigned-authorized {
                            type boolean;
                            default "true";
                            description "Controls whether the query returns UEs in IP-assigned-authorized state";
                        }

                        leaf already-signed-in {
                            type boolean;
                            default "true";
                            description "Controls whether the query returns UEs in already-signed-in state";
                        }

                        leaf portal {
                            type boolean;
                            default "true";
                            description "Controls whether the query returns UEs in portal state";
                        }

                        leaf dsm {
                            type boolean;
                            default "true";
                            description "Controls whether the query returns UEs in DSM state";
                        }

                        leaf esm {
                            type boolean;
                            default "true";
                            description "Controls whether the query returns UEs in ESM state";
                        }

                        leaf l2 {
                            type boolean;
                            default "true";
                            description "Controls whether the query returns UEs in Layer-2 Wholesale state";
                        }

                        leaf gtp-authorized {
                            type boolean;
                            default "true";
                            description "Controls whether the query returns UEs in GTP-authorized state";
                        }

                        leaf delete-pending {
                            type boolean;
                            default "true";
                            description "Controls whether the query returns UEs in delete-pending state";
                        }

                        leaf cross-connect {
                            type boolean;
                            default "true";
                            description "Controls whether the query returns UEs in cross-connect state";
                        }

                    } // container connection-state

                    container tunnel {
                        description "Enter the tunnel context";

                        leaf router-instance {
                            type string;
                            description "When specified, the query will only return UEs on this tunnel router";
                        }

                        leaf remote-address {
                            type types-sros:ip-address;
                            description "When specified, the query will only return UEs with this IP address as remote tunnel endpoint";
                        }

                        leaf local-address {
                            type types-sros:ip-address;
                            description "When specified, the query will only return UEs with this IP address as local tunnel endpoint";
                        }

                        leaf encapsulation {
                            type types-wlangw:encapsulation;
                            description "When specified, the query will only return UEs for which the received traffic is encapsulated with this type";
                        }

                    } // container tunnel

                    container wlan-gw-group {
                        presence "Enter the 'wlan-gw-group' context";
                        description "Enable the wlan-gw-group context";

                        leaf id {
                            type types-isa:wlan-gw-group-id;
                            mandatory true;
                            description "The identifier of the WLAN-GW ISA group";
                        }

                        leaf member {
                            type types-nat:bb-group-member {
                                range "1..1024";
                            }
                            description "The member of the WLAN-GW ISA group";
                        }

                    } // container wlan-gw-group

                } // list ue

                list tunnel {
                    key "name";
                    max-elements 1024;
                    description "Enter the tunnel list instance";

                    leaf name {
                        type types-sros:named-item;
                        description "Textual identification for the tunnel query";
                    }

                    leaf calculate-counts {
                        type boolean;
                        default "false";
                        description "Whether the system calculates the current number of tunnels matching this query";
                    }

                    leaf access-point-mac-address-learning-status {
                        type enumeration {
                            enum "failed"                       { value 1; }
                            enum "succeeded"                    { value 2; }
                        }
                        description "When specified, the query will only return tunnels where the learning of the Access Point MAC address had the specified result";
                    }

                    leaf-list apply-groups {
                        type leafref {
                            path "../../../../../groups/group/name";
                        }
                        max-elements 8;
                        ordered-by user;
                        description "Apply a configuration group at this level";
                    }

                    container encapsulation {
                        presence "Enter the 'encapsulation' context";
                        description "Enable the encapsulation context";

                        leaf gre {
                            type boolean;
                            default "true";
                            description "Controls whether the query returns Soft GRE tunnels";
                        }

                        leaf l2tp {
                            type boolean;
                            default "true";
                            description "Controls whether the query returns Soft L2TPv3 tunnels";
                        }

                        leaf l2 {
                            type boolean;
                            default "true";
                            description "Controls whether the query returns IEEE 802.1Q and IEEE 802.1ad tunnels";
                        }

                        leaf vxlan {
                            type boolean;
                            default "true";
                            description "Controls whether the query returns VXLAN tunnels";
                        }

                    } // container encapsulation

                    container l2 {
                        description "Enter the l2 context";

                        leaf sap {
                            type types-sros:sap;
                            description "When specified, the query will only return a Layer-2 tunnel if the value matches the tunnel's L2-AP Access Point";
                        }

                        leaf inner-vlan {
                            type types-sros:qtag-full-range;
                            description "When specified, the query will only return a Layer-2 tunnel if the value matches the tunnel's inner tag (customer tag, ethertype 0x8100) in case of qinq encapsulation";
                        }

                        leaf outer-vlan {
                            type types-sros:qtag-full-range;
                            description "When specified, the query will only return a Layer-2 tunnel if the value matches the tunnel's VLAN tag in case of IEEE 802.1Q encapsulation, or the outer tag (service tag, ethertype 0x88a8) in case of IEEE 802.1ad encapsulation";
                        }

                    } // container l2

                    container l3 {
                        description "Enter the l3 context";

                        leaf router-instance {
                            type string;
                            description "When specified, the query will only return tunnels on this router-instance";
                        }

                        leaf remote-address {
                            type types-sros:ip-address;
                            description "When specified, the query will only return tunnels with this IP address as remote endpoint";
                        }

                        leaf local-address {
                            type types-sros:ip-address;
                            description "When specified, the query will only return tunnels with this IP address as local endpoint";
                        }

                        leaf address-type {
                            type enumeration {
                                enum "ipv4"                         { value 1; }
                                enum "ipv6"                         { value 2; }
                            }
                            description "When specified, the query will only return tunnels where the IP layer has this address type";
                        }

                    } // container l3

                    container ues {
                        description "Enter the ues context";

                        leaf maximum {
                            type uint32;
                            description "The query will only return tunnels where the number of UEs is lower than or equal to this value. When a UE state filter is active, the maximum is enforced using the UE count after the state filter.";
                        }

                        leaf minimum {
                            type uint32;
                            default "1";
                            description "The query will only return tunnels where the number of UEs is higher than or equal to this value. When a UE state filter is active the minimum is enforced using the UE count after the state filter.";
                        }

                        container state {
                            presence "Enter the 'state' context";
                            description "Enable the state context";

                            leaf migrant {
                                type boolean;
                                default "true";
                                description "Controls whether the query takes the number of migrant UEs in a tunnel into account";
                            }

                            leaf dsm {
                                type boolean;
                                default "true";
                                description "Controls whether the query takes the number of DSM UEs in a tunnel into account";
                            }

                            leaf esm {
                                type boolean;
                                default "true";
                                description "Controls whether the query takes the number of ESM UEs in a tunnel into account";
                            }

                            leaf l2 {
                                type boolean;
                                default "true";
                                description "Controls whether the query takes the number of Layer-2 Wholesale UEs in a tunnel into account";
                            }

                            leaf cross-connect {
                                type boolean;
                                default "true";
                                description "Controls whether the query takes the number of cross-connect UEs in a tunnel into account";
                            }

                        } // container state

                    } // container ues

                } // list tunnel

            } // container queries

        } // container wlan-gw

    } // grouping conf-submgt-wlangw-wlan-gw

}
