submodule nokia-state-port-gnss {

    yang-version "1.1";

    belongs-to nokia-state { prefix "state"; }

    import ietf-yang-types                { prefix "yang"; }
    import nokia-sros-yang-extensions     { prefix "sros-ext"; }
    import nokia-types-port               { prefix "types-port"; }
    import nokia-types-sros               { prefix "types-sros"; }


    sros-ext:sros-major-release "rel20";

    organization "Nokia";

    contact
        "Nokia SR OS Support
         Web: <http://www.nokia.com>";

    description
        "Nokia YANG Data model with operational state for Global Navigation Satellite System (GNSS) CPM ports on SR OS based routers.

         Copyright 2016 Nokia. All rights reserved. Reproduction of this document
         is authorized on the condition that the foregoing copyright notice is included.

         This nokia-state-port-gnss YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";

    revision "2020-05-22";

    grouping state-port-gnss {
        container gnss {
            description "Enter the gnss context";

            leaf visible-satellite-count {
                type uint32;
                description "The number of satellites currently 'seen' by the GNSS receiver module";
            }

            leaf used-satellite-count {
                type uint32;
                description "The number of satellites currently 'used' in computations by the GNSS receiver module";
            }

            leaf antenna-status {
                type types-port:gnss-antenna-status;
                description "The status of the GNSS receiver module's antenna";
            }

            leaf sync-status {
                type types-port:gnss-sync-status;
                description "The sync status of the GNSS receiver module";
            }

            leaf latitude {
                type decimal64 {
                    range "-90..90";
                    fraction-digits 5;
                }
                units "degrees latitude-longitude";
                description "The latitude of the GNSS receiver module's antenna";
            }

            leaf longitude {
                type decimal64 {
                    range "-180..180";
                    fraction-digits 5;
                }
                units "degrees latitude-longitude";
                description "The longitude of the GNSS receiver module's antenna";
            }

            leaf altitude {
                type int32 {
                    range "-1000..10000";
                }
                units "meters";
                description "The altitude of the GNSS receiver module's antenna";
            }

            leaf date-and-time {
                type yang:date-and-time;
                description "The current date and time as provided by the GNSS receiver module";
            }

            leaf receiver-status {
                type types-sros:display-string-or-empty;
                description "The status of the GNSS receiver module";
            }

            leaf current-utc-offset {
                type int32 {
                    range "-65536..65535";
                }
                units "seconds";
                description
                    "the current offset between GPS time and UTC in seconds, as provided by the
                     GNSS receiver module";
            }

            leaf receiver-firmware-version {
                type types-sros:display-string-or-empty;
                description "The firmware version of the GNSS receiver module";
            }

        } // container gnss

    } // grouping state-port-gnss

}
