submodule nokia-state-router {

    yang-version "1.1";

    belongs-to nokia-state { prefix "state"; }

    import ietf-yang-types                { prefix "yang"; }
    import nokia-sros-yang-extensions     { prefix "sros-ext"; }
    import nokia-types-card               { prefix "types-card"; }
    import nokia-types-ipsec              { prefix "types-ipsec"; }
    import nokia-types-isa                { prefix "types-isa"; }
    import nokia-types-nat                { prefix "types-nat"; }
    import nokia-types-qos                { prefix "types-qos"; }
    import nokia-types-router             { prefix "types-router"; }
    import nokia-types-services           { prefix "types-services"; }
    import nokia-types-sros               { prefix "types-sros"; }
    import nokia-types-subscriber-mgmt    { prefix "types-submgt"; }
    import nokia-types-wlan               { prefix "types-wlan"; }
    import nokia-types-wlangw             { prefix "types-wlangw"; }

    include nokia-state-router-bgp;
    include nokia-state-router-bier;
    include nokia-state-router-dhcp-server;
    include nokia-state-router-fib-telemetry;
    include nokia-state-router-igmp;
    include nokia-state-router-isis;
    include nokia-state-router-l2tp;
    include nokia-state-router-ldp;
    include nokia-state-router-mld;
    include nokia-state-router-mpls;
    include nokia-state-router-msdp;
    include nokia-state-router-nat;
    include nokia-state-router-origin-validation;
    include nokia-state-router-ospf;
    include nokia-state-router-ospf3;
    include nokia-state-router-pcep;
    include nokia-state-router-pim;
    include nokia-state-router-radius;
    include nokia-state-router-rib-api;
    include nokia-state-router-rip;
    include nokia-state-router-ripng;
    include nokia-state-router-rsvp;
    include nokia-state-router-segment-routing;
    include nokia-state-router-static-route;
    include nokia-state-router-twamp-light;
    include nokia-state-router-wpp;

    sros-ext:sros-major-release "rel20";

    organization "Nokia";

    contact
        "Nokia SR OS Support
         Web: <http://www.nokia.com>";

    description
        "Nokia YANG Data model with operational state for routing protocols on SR OS based routers.

         Copyright 2016 Nokia. All rights reserved. Reproduction of this document
         is authorized on the condition that the foregoing copyright notice is included.

         This nokia-state-router YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";

    revision "2020-06-25";

    grouping state-router-mvpn-extranet {
        list mvpn-extranet {
            key "next-hop-address route-distinguisher source-mvpn receiver-mvpn";
            description "Enter the mvpn-extranet list instance";

            leaf next-hop-address {
                type types-sros:ip-address;
                description
                    "Indicates the next hop address in order to reach
                     the MVPN where the source is present.";
            }

            leaf route-distinguisher {
                type types-services:state-vpn-rd;
                description
                    "Indicates the Route Distinguisher used to reach
                     the MVPN where source is present.";
            }

            leaf source-mvpn {
                type types-sros:router-instance;
                description "Indicates the source MVPN id.";
            }

            leaf receiver-mvpn {
                type types-sros:router-instance;
                description "Indicates the receiver MVPN id.";
            }

            leaf receiver-reference-count {
                type uint32;
                description
                    "Indicates the number of receivers in the receiver
                     MVPN which expect to receive Extranet
                     traffic from this source MVPN.";
            }

        } // list mvpn-extranet

    } // grouping state-router-mvpn-extranet

    grouping state-router {
        list router {
            key "router-name";
            description "Enter the router list instance";

            leaf router-name {
                type types-sros:named-item-64;
                description "Router name";
            }

            leaf vrtr-id {
                type int32;
                description "The virtual router index.";
            }

            leaf oper-router-id {
                type types-sros:ipv4-address;
                description "Indicates the operational router-id.";
            }

            container gtp {
                description "Enter the gtp context";

                list control-plane-peer {
                    key "remote-address udp-port";
                    description "Enter the control-plane-peer list instance";

                    leaf remote-address {
                        type types-sros:ip-address;
                        description "IP Address of the GTP-C peer";
                    }

                    leaf udp-port {
                        type types-sros:tcp-udp-port;
                        description "UDP port used by the GTP-C peer";
                    }

                    leaf local-address {
                        type types-sros:ip-address;
                        description "Local IP address";
                    }

                    leaf oper-state {
                        type types-wlangw:mobile-gateway-state;
                        description "Connection state";
                    }

                    leaf profile {
                        type types-sros:named-item;
                        description "Profile";
                    }

                    leaf gtp-c-version {
                        type uint32 {
                            range "1..2";
                        }
                        description "GTP-C protocol version";
                    }

                    leaf interface-type {
                        type types-wlangw:mobile-gateway-connection;
                        description "Interface type";
                    }

                    leaf restart-count {
                        type uint32;
                        description "Number of times this connection is restarted";
                    }

                    leaf up-time {
                        type yang:date-and-time;
                        description "Moment when this connection was created";
                    }

                    container statistics {
                        description "Enter the statistics context";

                        leaf tx-echo-requests {
                            type yang:counter32;
                            description "Echo request transmitted";
                        }

                        leaf tx-echo-responses {
                            type yang:counter32;
                            description "Echo response transmitted";
                        }

                        leaf rx-echo-requests {
                            type yang:counter32;
                            description "Echo request received";
                        }

                        leaf rx-echo-responses {
                            type yang:counter32;
                            description "Echo response received";
                        }

                        leaf rx-version-not-supported {
                            type yang:counter32;
                            description "Version not supported";
                        }

                        leaf rx-malformed-packets {
                            type yang:counter32;
                            description "Malformed packets";
                        }

                        leaf rx-unknown-packets {
                            type yang:counter32;
                            description "Unknown packets";
                        }

                        leaf rx-missing-ie-packets {
                            type yang:counter32;
                            description "Packets with missing IEs";
                        }

                        leaf peer-restarts {
                            type yang:counter32;
                            description "Peer restarts";
                        }

                        leaf peer-restart-counter {
                            type yang:counter32;
                            description "Peer restarts counter";
                        }

                        leaf path-management-failures {
                            type yang:counter32;
                            description "Path management failures";
                        }

                        leaf create-pdp-request {
                            type yang:counter32;
                            description "Create-PDP-context requests";
                        }

                        leaf create-pdp-response {
                            type yang:counter32;
                            description "Create-PDP-context responses";
                        }

                        leaf delete-pdp-request {
                            type yang:counter32;
                            description "Delete-PDP-context requests";
                        }

                        leaf delete-pdp-response {
                            type yang:counter32;
                            description "Delete-PDP-context responses";
                        }

                        leaf modify-pdp-request {
                            type yang:counter32;
                            description "Modify-PDP-context requests";
                        }

                        leaf modify-pdp-response {
                            type yang:counter32;
                            description "Modify-PDP-context responses";
                        }

                        leaf create-session-request {
                            type yang:counter32;
                            description "Create-session requests";
                        }

                        leaf create-session-response {
                            type yang:counter32;
                            description "Create-session responses";
                        }

                        leaf delete-session-request {
                            type yang:counter32;
                            description "Delete-session requests";
                        }

                        leaf delete-session-response {
                            type yang:counter32;
                            description "Delete-session responses";
                        }

                        leaf create-bearer-request {
                            type yang:counter32;
                            description "Create-bearer requests";
                        }

                        leaf create-bearer-response {
                            type yang:counter32;
                            description "Create-bearer responses";
                        }

                        leaf delete-bearer-request {
                            type yang:counter32;
                            description "Delete-bearer requests";
                        }

                        leaf delete-bearer-response {
                            type yang:counter32;
                            description "Delete-bearer responses";
                        }

                        leaf update-bearer-request {
                            type yang:counter32;
                            description "Update-bearer requests";
                        }

                        leaf update-bearer-response {
                            type yang:counter32;
                            description "Update-bearer responses";
                        }

                        leaf modify-bearer-request {
                            type yang:counter32;
                            description "Modify-bearer requests";
                        }

                        leaf modify-bearer-response {
                            type yang:counter32;
                            description "Modify-bearer responses";
                        }

                        leaf release-access-bearers-request {
                            type yang:counter32;
                            description "Release-access-bearers requests";
                        }

                        leaf release-access-bearers-response {
                            type yang:counter32;
                            description "Release-access-bearers responses";
                        }

                        leaf downlink-notification {
                            type yang:counter32;
                            description "Downlink-notification";
                        }

                        leaf downlink-notification-ack {
                            type yang:counter32;
                            description "Downlink-notification ack";
                        }

                        leaf downlink-notification-fail {
                            type yang:counter32;
                            description "Downlink notification fail";
                        }

                        leaf stop-paging {
                            type yang:counter32;
                            description "Stop-paging indication";
                        }

                        leaf change-notification-request {
                            type yang:counter32;
                            description "Change-notification requests";
                        }

                        leaf change-notification-response {
                            type yang:counter32;
                            description "Change-notification responses";
                        }

                        leaf create-indirect-data-forwarding-tunnel-request {
                            type yang:counter32;
                            description "Create-indirect-data-forwarding-tunnel requests";
                        }

                        leaf delete-indirect-data-forwarding-tunnel-request {
                            type yang:counter32;
                            description "Delete-indirect-data-forwarding-tunnel requests";
                        }

                        leaf create-indirect-data-forwarding-tunnel-response {
                            type yang:counter32;
                            description "Create-indirect-data-forwarding-tunnel responses";
                        }

                        leaf delete-indirect-data-forwarding-tunnel-response {
                            type yang:counter32;
                            description "Delete-indirect-data-forwarding-tunnel responses";
                        }

                        leaf bearers {
                            type yang:counter32;
                            description "Number of bearers";
                        }

                    } // container statistics

                } // list control-plane-peer

                list dsm-peer {
                    key "remote-address udp-port local-address";
                    description "Enter the dsm-peer list instance";

                    leaf remote-address {
                        type types-sros:ip-address;
                        description "IP Address of the GTP-C peer";
                    }

                    leaf udp-port {
                        type types-sros:tcp-udp-port;
                        description "UDP port used by the GTP-C peer";
                    }

                    leaf local-address {
                        type types-sros:ip-address;
                        description "Local IP address";
                    }

                    leaf oper-state {
                        type types-wlangw:mobile-gateway-state;
                        description "Connection state";
                    }

                    leaf profile {
                        type types-sros:named-item;
                        description "Profile";
                    }

                    leaf gtp-c-version {
                        type uint32 {
                            range "1..2";
                        }
                        description "GTP-C protocol version";
                    }

                    leaf interface-type {
                        type types-wlangw:mobile-gateway-connection;
                        description "Interface type";
                    }

                    leaf restart-count {
                        type uint32;
                        description "Number of times this connection is restarted";
                    }

                    leaf up-time {
                        type yang:date-and-time;
                        description "Moment when this connection was created";
                    }

                    container statistics {
                        description "Enter the statistics context";

                        leaf parse-error {
                            type yang:counter64;
                            description "Packets dropped because of parse errors";
                        }

                        leaf no-resources {
                            type yang:counter64;
                            description "Number of packets dropped because not enough resources were available";
                        }

                        leaf peer-restart {
                            type yang:counter64;
                            description "Number of times the peer connection was restarted";
                        }

                        leaf session-dropped {
                            type yang:counter64;
                            description "Number of sessions dropped";
                        }

                        container gtp-v1 {
                            description "Enter the gtp-v1 context";

                            leaf invalid {
                                type yang:counter64;
                                description "Invalid";
                            }

                            leaf failed {
                                type yang:counter64;
                                description "Failed";
                            }

                            leaf ignored {
                                type yang:counter64;
                                description "Ignored";
                            }

                            leaf echo-request {
                                type yang:counter64;
                                description "Echo requests";
                            }

                            leaf echo-response {
                                type yang:counter64;
                                description "Echo responses";
                            }

                            leaf create-pdp-context-request {
                                type yang:counter64;
                                description "Create-PDP-context requests";
                            }

                            leaf create-pdp-context-response {
                                type yang:counter64;
                                description "Create-PDP-context responses";
                            }

                            leaf create-pdp-context-timeout {
                                type yang:counter64;
                                description "Timed out create-PDP-context requests";
                            }

                            leaf delete-pdp-context-request {
                                type yang:counter64;
                                description "Delete-PDP-context requests";
                            }

                            leaf delete-pdp-context-response {
                                type yang:counter64;
                                description "Delete-PDP-context responses";
                            }

                            leaf delete-pdp-context-request-invalid {
                                type yang:counter64;
                                description "Invalid delete-PDP-context requests";
                            }

                            leaf delete-pdp-context-timeout {
                                type yang:counter64;
                                description "Timed out delete-pdp-context requests";
                            }

                            leaf version-not-supported {
                                type yang:counter64;
                                description "Version not supported";
                            }

                        } // container gtp-v1

                        container gtp-v2 {
                            description "Enter the gtp-v2 context";

                            leaf invalid {
                                type yang:counter64;
                                description "Invalid";
                            }

                            leaf failed {
                                type yang:counter64;
                                description "Failed";
                            }

                            leaf ignored {
                                type yang:counter64;
                                description "Ignored";
                            }

                            leaf echo-request {
                                type yang:counter64;
                                description "Echo requests";
                            }

                            leaf echo-response {
                                type yang:counter64;
                                description "Echo responses";
                            }

                            leaf create-session-request {
                                type yang:counter64;
                                description "Create-session requests";
                            }

                            leaf create-session-response {
                                type yang:counter64;
                                description "Create-session responses";
                            }

                            leaf create-session-timeout {
                                type yang:counter64;
                                description "Timed oud create-session requests";
                            }

                            leaf delete-session-request {
                                type yang:counter64;
                                description "Delete-session requests";
                            }

                            leaf delete-session-response {
                                type yang:counter64;
                                description "Delete-session responses";
                            }

                            leaf delete-session-timeout {
                                type yang:counter64;
                                description "Timed out delete-session requests";
                            }

                            leaf delete-bearer-request {
                                type yang:counter64;
                                description "Delete-bearer requests";
                            }

                            leaf delete-bearer-response {
                                type yang:counter64;
                                description "Delete-bearer responses";
                            }

                            leaf delete-bearer-request-invalid {
                                type yang:counter64;
                                description "Invalid delete-bearer requests";
                            }

                            leaf version-not-supported {
                                type yang:counter64;
                                description "Version not supported";
                            }

                        } // container gtp-v2

                        container gtp-u {
                            description "Enter the gtp-u context";

                            leaf invalid {
                                type yang:counter64;
                                description "Invalid";
                            }

                            leaf failed {
                                type yang:counter64;
                                description "Failed";
                            }

                            leaf ignored {
                                type yang:counter64;
                                description "Ignored";
                            }

                            leaf error-indication {
                                type yang:counter64;
                                description "Error-indications";
                            }

                            leaf forward-upstream {
                                type yang:counter64;
                                description "Number of packets forwarded upstream";
                            }

                            leaf forward-downstream {
                                type yang:counter64;
                                description "Number of packets forwarded downstream";
                            }

                        } // container gtp-u

                    } // container statistics

                } // list dsm-peer

                container dns-cache {
                    description "Enter the dns-cache context";

                    list a-record {
                        key "name index";
                        description "Enter the a-record list instance";

                        leaf name {
                            type string;
                            description "Record name";
                        }

                        leaf index {
                            type uint32;
                            description "Index to distinguish multiple entries with the same name";
                        }

                        leaf address {
                            type types-sros:ip-address;
                            description "Resolved address";
                        }

                        leaf ttl {
                            type uint32;
                            description "Remaining time this entry is valid";
                        }

                    } // list a-record

                    list snaptr-record {
                        key "name order index";
                        description "Enter the snaptr-record list instance";

                        leaf name {
                            type string;
                            description "Record name";
                        }

                        leaf order {
                            type uint32;
                            description "Ordinal indicating in which order entries with the same name should be processed";
                        }

                        leaf index {
                            type uint32;
                            description "Index to distinguish entries with the same name and order";
                        }

                        leaf preference {
                            type uint32;
                            description "Number indicating preference of this entry, lower numbers mean higher preference";
                        }

                        leaf service {
                            type string;
                            description "Service associated with this entry";
                        }

                        leaf next-lookup {
                            type enumeration {
                                enum "dns-srv"                      { value 1; }
                                enum "dns-a"                        { value 2; }
                                enum "dns-naptr"                    { value 3; }
                            }
                            description "The record type to be used in the next lookup";
                        }

                        leaf next-lookup-name {
                            type string;
                            description "The record name to be used in the next lookup";
                        }

                        leaf ttl {
                            type uint32;
                            description "Remaining time this entry is valid";
                        }

                    } // list snaptr-record

                    list srv-record {
                        key "name priority index";
                        description "Enter the srv-record list instance";

                        leaf name {
                            type string;
                            description "Record name";
                        }

                        leaf priority {
                            type uint32 {
                                range "0..65535";
                            }
                            description "Ordinal indicating in which order entries with the same name should be processed";
                        }

                        leaf index {
                            type uint32;
                            description "Index to distinguish entries with the same name and priority";
                        }

                        leaf weight {
                            type uint32 {
                                range "0..65535";
                            }
                            description "Weight used in determining which entry to use when multiple entries have the same priority. Entries with higher weight should have a higher probability of being used.";
                        }

                        leaf port {
                            type types-sros:tcp-udp-port;
                            description "Port of this service on the target host";
                        }

                        leaf target {
                            type string;
                            description "Domain name of the target host";
                        }

                        leaf ttl {
                            type uint32;
                            description "Remaining time this entry is valid";
                        }

                    } // list srv-record

                } // container dns-cache

            } // container gtp

            container aggregates {
                description "Enter the aggregates context";

                list aggregate {
                    key "ip-prefix";
                    description "Enter the aggregate list instance";

                    leaf ip-prefix {
                        type types-sros:ip-unicast-prefix;
                        description "Destination IP address prefix of the aggregate route";
                    }

                    leaf oper-state {
                        type types-sros:oper-state;
                        description "Operational state.";
                    }

                } // list aggregate

            } // container aggregates

            list wlan-gw-tunnel {
                key "remote-address local-address";
                description "Enter the wlan-gw-tunnel list instance";

                leaf remote-address {
                    type types-sros:ip-address;
                    description "IP address of the remote endpoint (Access Point) of this tunnel";
                }

                leaf local-address {
                    type types-sros:ip-address;
                    description "IP address of the local endpoint of this tunnel";
                }

                leaf established-time {
                    type yang:date-and-time;
                    description "Time when this tunnel was established";
                }

                leaf wlan-gw-group {
                    type types-isa:wlan-gw-group-id;
                    description "WLAN-GW ISA group associated with this tunnel";
                }

                leaf group-member {
                    type types-nat:bb-group-member;
                    description "The member of the WLAN-GW ISA group associated with this tunnel";
                }

                leaf number-of-ues {
                    type uint32;
                    description
                        "Number of User Equipment's connected to this system through
                         this tunnel";
                }

                leaf service {
                    type types-services:service-name;
                    description
                        "Identifier of the service of the WLAN-GW group-interface
                         associated with this tunnel";
                }

                leaf group-interface {
                    type types-sros:interface-name;
                    description "The group-interface associated with this tunnel";
                }

                container access-point {
                    description "Enter the access-point context";

                    leaf mac-address {
                        type types-sros:mac-address;
                        description "MAC address of the Access Point, as learned by this system";
                    }

                    leaf mac-learn-failed {
                        type boolean;
                        description
                            "Learning of the MAC address of the Access Point via ARPoGRE
                             or NDoGRE failed";
                    }

                } // container access-point

                container l2 {
                    description "Enter the l2 context";

                    leaf sap {
                        type types-sros:sap;
                        description "The SAP of the L2 Access Point, as learned by this system";
                    }

                    leaf inner-vlan {
                        type types-sros:qtag-full-range;
                        description "Inner tag in case of qinq encapsulation";
                    }

                    leaf outer-vlan {
                        type types-sros:qtag-full-range;
                        description
                            "VLAN tag in case of IEEE 802.1Q encapsulation, or the outer
                             tag in case of qinq encapsulation";
                    }

                } // container l2

                container qos {
                    description "Enter the qos context";

                    leaf oper-state {
                        type types-wlangw:qos-oper-state;
                        description "Operational state of per tunnel QoS enforcement";
                    }

                    leaf remaining-hold-time {
                        type types-sros:time-duration;
                        description
                            "Remaining time before the tunnel QoS is removed when no UEs are
                             active";
                    }

                    container egress-encapsulation-group {
                        description "Enter the egress-encapsulation-group context";

                        leaf service {
                            type types-services:service-name;
                            description
                                "Name of the internal service where the encap group is
                                 applied";
                        }

                        leaf sap {
                            type types-sros:sap;
                            description "Internal SAP to which the encap-group is applied";
                        }

                        leaf name {
                            type string;
                            description "Name of the encapsulation group";
                        }

                        leaf member {
                            type types-services:isid;
                            description "Encapsulation group member (ISID) used";
                        }

                    } // container egress-encapsulation-group

                    container overrides {
                        description "Enter the overrides context";

                        leaf aggregate-rate-limit {
                            type types-qos:queue-pir-rate-override;
                            units "kilobps";
                            description "Overridden aggregate rate limit";
                        }

                        list scheduler {
                            key "name";
                            description "Enter the scheduler list instance";

                            leaf name {
                                type string;
                                description "Identifier of the overwritten QoS object";
                            }

                            leaf pir {
                                type types-qos:queue-pir-rate-override;
                                units "kilobps";
                                description "Overridden PIR";
                            }

                            leaf cir {
                                type types-qos:queue-cir-rate-override;
                                units "kilobps";
                                description "Overridden CIR";
                            }

                        } // list scheduler

                    } // container overrides

                } // container qos

                list ue {
                    key "bridge-domain mac-address";
                    description "Enter the ue list instance";

                    leaf bridge-domain {
                        type uint32;
                        description
                            "The vRGW Bridge Domain of this UE, 0 denotes no associated
                             bridge or plain WLAN-GW functionality";
                    }

                    leaf mac-address {
                        type types-sros:mac-unicast-address;
                        description "The MAC address of this UE";
                    }

                    leaf vlan {
                        type types-sros:qtag-full-range;
                        description "The VLAN tag present in the traffic received from this UE";
                    }

                    leaf mpls-label {
                        type types-sros:mpls-label-full-range;
                        description "The MPLS label present in the traffic received from this UE";
                    }

                    leaf ssid {
                        type types-wlan:ssid;
                        description "Service Set ID (SSID) of this UE";
                    }

                    leaf previous-access-point-address {
                        type types-sros:ip-address;
                        description "IP address of the previous Access Point of this UE";
                    }

                    leaf last-move-time {
                        type yang:date-and-time;
                        description "Most recent Access Point move of this UE";
                    }

                    leaf service {
                        type types-services:service-name;
                        description
                            "Service identifier of the (internal) SAP associated with
                             this UE";
                    }

                    leaf encapsulation {
                        type types-wlangw:encapsulation;
                        description "Tunnel encapsulation type for this UE";
                    }

                    container session {
                        description "Enter the session context";

                        leaf subscriber {
                            type types-submgt:subscriber-id;
                            description "Subscriber Identification string";
                        }

                        leaf sla-profile-instance {
                            type types-submgt:sla-profile-instance-id;
                            description "Sla profile instance identifier";
                        }

                        leaf ipoe-session-id {
                            type types-submgt:session-id;
                            description "Session identifier";
                        }

                    } // container session

                } // list ue

                list per-retailer-qos {
                    key "retail-service";
                    description "Enter the per-retailer-qos list instance";

                    leaf retail-service {
                        type types-services:service-name;
                        description "Identifier of the retail service";
                    }

                    leaf oper-state {
                        type types-wlangw:qos-oper-state;
                        description "Operational state of per tunnel QoS enforcement";
                    }

                    leaf number-of-ues {
                        type uint32;
                        description "Number of User Equipment's using this aggregate QoS";
                    }

                    leaf remaining-hold-time {
                        type types-sros:time-duration;
                        description
                            "Remaining time before the tunnel QoS is removed when no UEs are
                             active";
                    }

                    container egress-encapsulation-group {
                        description "Enter the egress-encapsulation-group context";

                        leaf service {
                            type types-services:service-name;
                            description
                                "Name of the internal service where the encap group is
                                 applied";
                        }

                        leaf sap {
                            type types-sros:sap;
                            description "Internal SAP to which the encap-group is applied";
                        }

                        leaf name {
                            type string;
                            description "Name of the encapsulation group";
                        }

                        leaf member {
                            type types-services:isid;
                            description "Encapsulation group member (ISID) used";
                        }

                    } // container egress-encapsulation-group

                    container overrides {
                        description "Enter the overrides context";

                        leaf aggregate-rate-limit {
                            type types-qos:queue-pir-rate-override;
                            units "kilobps";
                            description "Overridden aggregate rate limit";
                        }

                        list scheduler {
                            key "name";
                            description "Enter the scheduler list instance";

                            leaf name {
                                type string;
                                description "Identifier of the overwritten QoS object";
                            }

                            leaf pir {
                                type types-qos:queue-pir-rate-override;
                                units "kilobps";
                                description "Overridden PIR";
                            }

                            leaf cir {
                                type types-qos:queue-cir-rate-override;
                                units "kilobps";
                                description "Overridden CIR";
                            }

                        } // list scheduler

                    } // container overrides

                } // list per-retailer-qos

            } // list wlan-gw-tunnel

            container sfm-overload {
                description "Enter the sfm-overload context";

                leaf state {
                    type enumeration {
                        enum "not-applicable"               { value 0; }
                        enum "normal"                       { value 1; }
                        enum "overload"                     { value 2; }
                    }
                    description "The IGP SFM overload state.";
                }

                leaf start {
                    type types-sros:date-time;
                    description "The last time the SFM overload state had a transition to 'overload'.";
                }

                leaf time {
                    type int32 {
                        range "0..max";
                    }
                    description "The duration of the most recent overload.";
                }

            } // container sfm-overload

            list interface {
                key "interface-name";
                description "Enter the interface list instance";

                leaf interface-name {
                    type types-sros:interface-name;
                    description "Router interface name";
                }

                leaf if-index {
                    type int32;
                    description "The interface index.";
                }

                leaf system-if-index {
                    type int32;
                    description "The interface system index.";
                }

                leaf protocol {
                    type bits {
                        bit ospfv2                         { position 0; }
                        bit rip                            { position 1; }
                        bit isis                           { position 2; }
                        bit bgp                            { position 3; }
                        bit mpls                           { position 4; }
                        bit rsvp                           { position 5; }
                        bit ldp                            { position 6; }
                        bit igmp                           { position 7; }
                        bit pim                            { position 8; }
                        bit ospfv3                         { position 9; }
                        bit mld                            { position 10; }
                        bit ripng                          { position 11; }
                    }
                    description
                        "Indicates which protocols are configured on the interface.;
                                         
                         Values:
                             ospfv2 - Indicates if OSPFv2 is configured.
                             rip    - Indicates if RIP is configured.
                             isis   - Indicates if ISIS is configured.
                             bgp    - Indicates if BGP is configured.
                             mpls   - Indicates if MPLS is configured.
                             rsvp   - Indicates if RSVP is configured.
                             ldp    - Indicates if LDP is configured.
                             igmp   - Indicates if IGMP is configured.
                             pim    - Indicates if PIM is configured.
                             ospfv3 - Indicates if OSPFv3 is configured.
                             mld    - Indicates if MLD is configured.
                             ripng  - Indicates if RIPng is configured.";
                }

                leaf oper-ip-mtu {
                    type uint32;
                    units "bytes";
                    description "Indicates the interface operational IP MTU.";
                }

                leaf creation-origin {
                    type types-sros:creation-origin;
                    description "Indicates the mechanism used to create this entry.";
                }

                leaf if-oper-status {
                    type enumeration {
                        enum "up"                           { value 1; }
                        enum "down"                         { value 2; }
                        enum "testing"                      { value 3; }
                        enum "unknown"                      { value 4; }
                        enum "dormant"                      { value 5; }
                        enum "not-present"                  { value 6; }
                        enum "lower-layer-down"             { value 7; }
                    }
                    description
                        "The current operational state of the interface.
                         This leaf has the same semantics as ifOperStatus. 
                         in RFC 2863: The Interfaces Group MIB";
                }

                leaf last-oper-change {
                    type yang:date-and-time;
                    description "The sysUpTime when the operational state of this interface last changed.";
                }

                leaf lag-active-port {
                    type types-sros:port;
                    description
                        "LAG active port associated with this interface when lag-per-link-hash is enabled
                         on the lag or when a lag-link-map-profile is configured on this interface.";
                }

                container distributed-cpu-protection {
                    description "Enter the distributed-cpu-protection context";

                    list static-policer {
                        key "name card fp-number";
                        description "Enter the static-policer list instance";

                        leaf name {
                            type types-sros:named-item;
                            description "Name of static policer.";
                        }

                        leaf card {
                            type types-card:iom-card-slot;
                            description "IOM card within a chassis in the system.";
                        }

                        leaf fp-number {
                            type uint32 {
                                range "1..8";
                            }
                            description "Forwarding plane within a specific IOM card in the system.";
                        }

                        leaf state {
                            type types-services:dist-cpu-prot-policer-state;
                            description "State of the policer configured on Distributed CPU Protection Policy.";
                        }

                        leaf exceed-count {
                            type uint64;
                            description
                                "Number of packets exceeding the policing parameters since the given
                                 policer was previously declared as conformant or newly instantiated.";
                        }

                        leaf hold-down-remain {
                            type types-services:dist-cpu-prot-action-duration;
                            units "seconds";
                            description "Remaining hold-down period for a given policer.";
                        }

                        leaf detection-time-remain {
                            type uint32;
                            units "seconds";
                            description "Detection time remaining for a given policer.";
                        }

                    } // list static-policer

                    list local-monitor-policer {
                        key "name card fp-number";
                        description "Enter the local-monitor-policer list instance";

                        leaf name {
                            type types-sros:named-item;
                            description "Name of local-monitor policer.";
                        }

                        leaf card {
                            type types-card:iom-card-slot;
                            description "IOM card within a chassis in the system.";
                        }

                        leaf fp-number {
                            type uint32 {
                                range "1..8";
                            }
                            description "Forwarding plane within a specific IOM card in the system.";
                        }

                        leaf state {
                            type types-services:dist-cpu-prot-policer-state;
                            description "State of the policer configured on Distributed CPU Protection Policy.";
                        }

                        leaf exceed-count {
                            type uint64;
                            description
                                "Number of packets exceeding the policing parameters since the given
                                 policer was previously declared as conformant or newly instantiated.";
                        }

                        leaf all-dynamic-policer-allocation {
                            type boolean;
                            description "All dynamic-policers allocation status";
                        }

                    } // list local-monitor-policer

                    list dynamic-policer {
                        key "protocol card fp-number";
                        description "Enter the dynamic-policer list instance";

                        leaf protocol {
                            type types-sros:dist-cpu-protection-protocol;
                            description "Dynamic policer protocol.";
                        }

                        leaf card {
                            type types-card:iom-card-slot;
                            description "IOM card within a chassis in the system.";
                        }

                        leaf fp-number {
                            type uint32 {
                                range "1..8";
                            }
                            description "Forwarding plane within a specific IOM card in the system.";
                        }

                        leaf state {
                            type types-services:dist-cpu-prot-policer-state;
                            description "State of the policer configured on Distributed CPU Protection Policy.";
                        }

                        leaf exceed-count {
                            type uint64;
                            description
                                "Number of packets exceeding the policing parameters since the given
                                 policer was previously declared as conformant or newly instantiated.";
                        }

                        leaf hold-down-remain {
                            type types-services:dist-cpu-prot-action-duration;
                            units "seconds";
                            description "Remaining hold-down period for a given policer.";
                        }

                        leaf detection-time-remain {
                            type uint32;
                            units "seconds";
                            description "Detection time remaining for a given policer.";
                        }

                        leaf dynamic-policer-allocation {
                            type boolean;
                            description "Dynamic-policer allocation status";
                        }

                    } // list dynamic-policer

                } // container distributed-cpu-protection

                container statistics {
                    description "Enter the statistics context";

                    container ip {
                        description "Enter the ip context";

                        leaf out-packets {
                            type yang:counter64;
                            description "The number of packets transmitted by this interface.";
                        }

                        leaf out-octets {
                            type yang:counter64;
                            description "The number of octets transmitted by this interface.";
                        }

                        leaf out-discard-packets {
                            type yang:counter64;
                            description "The number of transmit packets discarded.";
                        }

                        leaf out-discard-octets {
                            type yang:counter64;
                            description "The number of transmit octets discarded.";
                        }

                        leaf in-packets {
                            type yang:counter64;
                            description "The number of packets received.";
                        }

                        leaf in-octets {
                            type yang:counter64;
                            description "The number of octets received.";
                        }

                        leaf urpf-check-fail-packets {
                            type yang:counter64;
                            description "The number of packets that fail uRPF check on this interface.";
                        }

                        leaf urpf-check-fail-octets {
                            type yang:counter64;
                            description "The number of octets in the packets that fail uRPF check.";
                        }

                    } // container ip

                    container mpls {
                        description "Enter the mpls context";

                        leaf out-packets {
                            type yang:counter64;
                            description "The total number of MPLS packets sent by this interface.";
                        }

                        leaf out-octets {
                            type yang:counter64;
                            description "The total number of MPLS bytes sent by this interface.";
                        }

                        leaf in-packets {
                            type yang:counter64;
                            description "The number of MPLS packets received.";
                        }

                        leaf in-octets {
                            type yang:counter64;
                            description "The number of MPLS octets in packets received.";
                        }

                        leaf alt-out-packets {
                            type yang:counter64;
                            description "The total number of non-RSVP packets sent by this interface.";
                        }

                        leaf alt-out-octets {
                            type yang:counter64;
                            description "The total number of non-RSVP bytes sent by this interface.";
                        }

                        leaf alt-in-packets {
                            type yang:counter64;
                            description "The number of non-RSVP packets received.";
                        }

                        leaf alt-in-octets {
                            type yang:counter64;
                            description "The number of non-RSVP octets in packets received.";
                        }

                    } // container mpls

                    list mac {
                        key "mac-address";
                        description "Enter the mac list instance";

                        leaf mac-address {
                            type yang:mac-address;
                            description "Mac-address";
                        }

                        leaf out-packets {
                            type yang:counter64;
                            description "The number of packets sent to the mac address";
                        }

                        leaf out-octets {
                            type yang:counter64;
                            description "The number of bytes sent to the mac address";
                        }

                        leaf in-packets {
                            type yang:counter64;
                            description "The number of packets received from the mac address";
                        }

                        leaf in-octets {
                            type yang:counter64;
                            description "The number of bytes received from the mac address";
                        }

                    } // list mac

                } // container statistics

                container hold-time {
                    description "Enter the hold-time context";

                    container ipv4 {
                        description "Enter the ipv4 context";

                        leaf hold-timer {
                            type uint32;
                            units "seconds";
                            description
                                "The hold-timer indicates the time left before
                                 the interface comes up or goes down, depending on the ongoing
                                 transition state of the interface.";
                        }

                    } // container ipv4

                    container ipv6 {
                        description "Enter the ipv6 context";

                        leaf hold-timer {
                            type uint32;
                            units "seconds";
                            description
                                "The hold-timer indicates the time left before
                                 the interface comes up or goes down, depending on the ongoing
                                 transition state of the interface.";
                        }

                    } // container ipv6

                } // container hold-time

                container ipv4 {
                    description "Enter the ipv4 context";

                    leaf oper-state {
                        type types-sros:oper-state;
                        description "The current IPv4 operational status of this router interface.";
                    }

                    leaf down-reason {
                        type bits {
                            bit admin-disabled                 { position 0; }
                            bit service-admin-disabled         { position 1; }
                            bit port-down                      { position 2; }
                            bit address-or-parent-not-ready    { position 3; }
                            bit associated-object-not-ready    { position 4; }
                            bit rvpls-down                     { position 5; }
                            bit operational-group-down         { position 6; }
                            bit admin-destroy                  { position 7; }
                            bit no-address                     { position 8; }
                            bit no-info                        { position 9; }
                            bit hold-down-timer-running        { position 10; }
                            bit protocol-down                  { position 11; }
                            bit invalid-port-configuration     { position 12; }
                            bit unknown                        { position 13; }
                            bit no-route-distinguisher         { position 14; }
                            bit wlan-gateway-redundancy-standby { position 15; }
                            bit wlan-gateway-group-degraded    { position 16; }
                            bit ip-control-tunnel-down         { position 17; }
                            bit pdn-address-mismatch           { position 18; }
                            bit ping-check-failure             { position 19; }
                            bit port-internal-loopback         { position 20; }
                        }
                        description
                            "Indicates the reason for why the interface is operationally down.
                                             
                             Values:
                                 admin-disabled                  - Administratively disabled.
                                 service-admin-disabled          - Assiocated service is administratively disabled.
                                 port-down                       - Associated SAP/port is operationally down.
                                 address-or-parent-not-ready     - Associated address or parent interface is not ready.
                                 associated-object-not-ready     - Associated object is not ready.
                                 rvpls-down                      - Associated R-VPLS service is operationally down.
                                 operational-group-down          - Associated operational group is operationally down.
                                 admin-destroy                   - The interface is being destroyed.
                                 no-address                      - There is no address configured.
                                 no-info                         - The interface info is not present.
                                 hold-down-timer-running         - The hold down timer is running.
                                 protocol-down                   - The protocols are operationally down.
                                 invalid-port-configuration      - Invalid port configuration.
                                 unknown                         - The interface is operationally down due to some unknown reason.
                                 no-route-distinguisher          - No route-distinguisher configured in the VRF.
                                 wlan-gateway-redundancy-standby - The interface is in standby state for WLAN-GW redundancy.
                                 wlan-gateway-group-degraded     - The interface associated WLAN-GW group is in a degraded state.
                                 ip-control-tunnel-down          - The IP tunnel associated to a control-tunnel interface is operationally down.
                                 pdn-address-mismatch            - The IP address learned from the packet data network does not match the configured primary IP address.
                                 ping-check-failure              - The IP interface is or went down because of a ping-template failure.
                                 port-internal-loopback          - The IP interface is bound to a port that has an internal loopback configured.";
                    }

                    container icmp {
                        description "Enter the icmp context";

                        container statistics {
                            description "Enter the statistics context";

                            leaf icmp-in-msgs {
                                type yang:counter32;
                                description
                                    "Total Number of ICMPv4 messages received by this interface.
                                                     
                                     This includes all those counted by icmp-in-errors. Note that this
                                     interface is the interface to which the ICMPv4 messages were
                                     addressed which may not be necessarily the input interface
                                     for the messages.";
                            }

                            leaf icmp-in-errors {
                                type yang:counter32;
                                description
                                    "Number of ICMPv4 errored messages received by this interface.
                                                     
                                     This implies ICMPv4 messages determined as having specific
                                     ICMPv4 errors (bad ICMPv4 checksums, bad length, etc.).";
                            }

                            leaf icmp-in-dest-unreachables {
                                type yang:counter32;
                                description "Number of ICMPv4 destination unreachable messages received by this interface.";
                            }

                            leaf icmp-in-redirects {
                                type yang:counter32;
                                description "Number of ICMPv4 redirect messages received by this interface.";
                            }

                            leaf icmp-in-echos {
                                type yang:counter32;
                                description "Number of ICMPv4 echo (request) messages received by this interface.";
                            }

                            leaf icmp-in-echo-replies {
                                type yang:counter32;
                                description "Number of ICMPv4 echo reply messages received by this interface.";
                            }

                            leaf icmp-in-time-exceeds {
                                type yang:counter32;
                                description "Number of ICMPv4 time exceeded messages received by this interface.";
                            }

                            leaf icmp-in-src-quenches {
                                type yang:counter32;
                                description "Number of ICMPv4 source quench messages received by this interface.";
                            }

                            leaf icmp-in-timestamps {
                                type yang:counter32;
                                description "Number of ICMPv4 timestamp (request) messages received by this interface.";
                            }

                            leaf icmp-in-timestamp-replies {
                                type yang:counter32;
                                description "Number of ICMPv4 timestamp reply messages received by this interface.";
                            }

                            leaf icmp-in-address-masks {
                                type yang:counter32;
                                description "Number of ICMPv4 address mask request messages received by this interface.";
                            }

                            leaf icmp-in-address-mask-replies {
                                type yang:counter32;
                                description "Number of ICMPv4 address mask reply messages received by this interface.";
                            }

                            leaf icmp-in-parm-problems {
                                type yang:counter32;
                                description "Number of ICMPv4 parameter problem messages received by this interface.";
                            }

                            leaf icmp-out-msgs {
                                type yang:counter32;
                                description
                                    "Total number of ICMPv4 messages this interface attempted to send.
                                                     
                                     This includes all those counted by icmp-out-errors.";
                            }

                            leaf icmp-out-errors {
                                type yang:counter32;
                                description
                                    "Number of ICMPv4 messages this interface could not be send due to problems
                                     discovered within ICMPv4 such as lack of buffers.
                                                     
                                     This value should not include errors discovered outside the ICMPv4 layer such as
                                     the inability of VRtr IPv4 to route the resultant datagram. In some implementations
                                     there may be no types of error which contribute to this counter's value.";
                            }

                            leaf icmp-out-dest-unreachables {
                                type yang:counter32;
                                description "Number of ICMPv4 destination unreachable messages sent by this interface.";
                            }

                            leaf icmp-out-redirects {
                                type yang:counter32;
                                description "Number of ICMPv4 redirect messages sent by this interface.";
                            }

                            leaf icmp-out-echos {
                                type yang:counter32;
                                description "Number of ICMPv4 echo request messages sent by this interface.";
                            }

                            leaf icmp-out-echo-replies {
                                type yang:counter32;
                                description "Number of ICMPv4 echo reply messages sent by this interface.";
                            }

                            leaf icmp-out-time-exceeds {
                                type yang:counter32;
                                description "Number of ICMPv4 time exceeded messages sent by this interface.";
                            }

                            leaf icmp-out-src-quenches {
                                type yang:counter32;
                                description "Number of ICMPv4 source quench messages sent by this interface.";
                            }

                            leaf icmp-out-timestamps {
                                type yang:counter32;
                                description "Number of ICMPv4 timestamp (request) messages sent by this interface.";
                            }

                            leaf icmp-out-timestamp-replies {
                                type yang:counter32;
                                description "Number of ICMPv4 timestamp reply messages sent by this interface.";
                            }

                            leaf icmp-out-address-masks {
                                type yang:counter32;
                                description "Number of ICMPv4 address mask request messages sent by this interface.";
                            }

                            leaf icmp-out-address-mask-replies {
                                type yang:counter32;
                                description "Number of ICMPv4 address mask reply messages sent by this interface.";
                            }

                            leaf icmp-out-parm-problems {
                                type yang:counter32;
                                description "Number of ICMPv4 parameter problem messages sent by this interface.";
                            }

                            leaf icmp-out-discards {
                                type yang:counter32;
                                description "Number of discarded ICMPv4 messages on this interface.";
                            }

                        } // container statistics

                    } // container icmp

                    container dhcp {
                        description "Enter the dhcp context";

                        container statistics {
                            description "Enter the statistics context";

                            container total-rx-packets {
                                description "Enter the total-rx-packets context";

                                leaf received {
                                    type yang:counter32;
                                    description "The total number of packets received by the DHCP relay agent.";
                                }

                                leaf malformed {
                                    type yang:counter32;
                                    description "The total number of malformed packets received by the DHCP relay agent.";
                                }

                                leaf untrusted {
                                    type yang:counter32;
                                    description "The total number of untrusted packets received by the DHCP relay agent.";
                                }

                            } // container total-rx-packets

                            container total-tx-packets {
                                description "Enter the total-tx-packets context";

                                leaf transmitted {
                                    type yang:counter32;
                                    description "The total number of packets transmitted by the DHCP relay agent.";
                                }

                            } // container total-tx-packets

                            container client-packets {
                                description "Enter the client-packets context";

                                leaf dropped {
                                    type yang:counter32;
                                    description "The total number of client packets dropped by the DHCP relay agent.";
                                }

                                leaf relayed {
                                    type yang:counter32;
                                    description "The total number of client packets relayed by the DHCP relay agent.";
                                }

                                leaf snooped {
                                    type yang:counter32;
                                    description "The total number of client packets snooped by the DHCP relay agent.";
                                }

                            } // container client-packets

                            container server-packets {
                                description "Enter the server-packets context";

                                leaf dropped {
                                    type yang:counter32;
                                    description "The total number of server packets dropped by the DHCP relay agent.";
                                }

                                leaf relayed {
                                    type yang:counter32;
                                    description "The total number of server packets relayed by the DHCP relay agent.";
                                }

                                leaf snooped {
                                    type yang:counter32;
                                    description "The total number of server packets snooped by the DHCP relay agent.";
                                }

                            } // container server-packets

                        } // container statistics

                    } // container dhcp

                    container statistics {
                        description "Enter the statistics context";

                        leaf out-packets {
                            type yang:counter64;
                            description "The number of packets transmitted by this interface.";
                        }

                        leaf out-octets {
                            type yang:counter64;
                            description "The number of octets transmitted by this interface.";
                        }

                        leaf out-discard-packets {
                            type yang:counter64;
                            description "The number of transmit packets discarded.";
                        }

                        leaf out-discard-octets {
                            type yang:counter64;
                            description "The number of transmit octets discarded.";
                        }

                        leaf in-packets {
                            type yang:counter64;
                            description "The number of packets received.";
                        }

                        leaf in-octets {
                            type yang:counter64;
                            description "The number of octets received.";
                        }

                        leaf urpf-check-fail-packets {
                            type yang:counter64;
                            description "The number of packets that fail uRPF check on this interface.";
                        }

                        leaf urpf-check-fail-octets {
                            type yang:counter64;
                            description "The number of octets in the packets that fail uRPF check.";
                        }

                        leaf out-discard-dbcast-packets {
                            type yang:counter64;
                            description "The number of directed-broadcast packets dropped.";
                        }

                        leaf out-discard-dbcast-octets {
                            type yang:counter64;
                            description "The number of directed-broadcast octets dropped.";
                        }

                        leaf in-ip-helper-redirects-packets {
                            type yang:counter64;
                            description "The number of packets redirected to the ip-helper gateway.";
                        }

                        leaf in-ip-helper-redirects-octets {
                            type yang:counter64;
                            description "The number of bytes redirected to the ip-helper gateway.";
                        }

                    } // container statistics

                    container primary {
                        description "Enter the primary context";

                        leaf oper-address {
                            type types-sros:ip-address;
                            description "Indicates the operational address of this entry.";
                        }

                        leaf creation-origin {
                            type types-sros:creation-origin;
                            description "Indicates the mechanism used to create this entry.";
                        }

                    } // container primary

                    list secondary {
                        key "address";
                        description "Enter the secondary list instance";

                        leaf address {
                            type types-sros:ipv4-unicast-address;
                            description "Secondary IPv4 address assigned to the interface";
                        }

                        leaf oper-address {
                            type types-sros:ip-address;
                            description "Indicates the operational address of this entry.";
                        }

                        leaf creation-origin {
                            type types-sros:creation-origin;
                            description "Indicates the mechanism used to create this entry.";
                        }

                    } // list secondary

                    container neighbor-discovery {
                        description "Enter the neighbor-discovery context";

                        container neighbor-unnumbered {
                            description "Enter the neighbor-unnumbered context";

                            leaf oper-state {
                                type types-sros:oper-state;
                                description "Indicates if the ARP entry is being used actively in the ARP table.";
                            }

                            leaf mac-address {
                                type yang:mac-address;
                                description "The media-dependent physical address.";
                            }

                            leaf type {
                                type enumeration {
                                    enum "other"                        { value 0; }
                                    enum "static"                       { value 1; }
                                    enum "dynamic"                      { value 2; }
                                    enum "managed"                      { value 100; }
                                    enum "evpn"                         { value 101; }
                                }
                                description "The type of mapping.";
                            }

                            leaf timer {
                                type uint32 {
                                    range "0..65535";
                                }
                                units "seconds";
                                description
                                    "Indicates how much longer an ARP entry remains in the ARP cache.

                                     When timer has a value of zero, the entry is cleared from the cache.";
                            }

                        } // container neighbor-unnumbered

                        list neighbor {
                            key "ipv4-address";
                            description "Enter the neighbor list instance";

                            leaf ipv4-address {
                                type types-sros:ipv4-address;
                                description "IPv4 address corresponding to the media-dependent physical address";
                            }

                            leaf oper-state {
                                type types-sros:oper-state;
                                description "Indicates if the ARP entry is being used actively in the ARP table.";
                            }

                            leaf mac-address {
                                type yang:mac-address;
                                description "The media-dependent physical address.";
                            }

                            leaf type {
                                type enumeration {
                                    enum "other"                        { value 0; }
                                    enum "static"                       { value 1; }
                                    enum "dynamic"                      { value 2; }
                                    enum "managed"                      { value 100; }
                                    enum "evpn"                         { value 101; }
                                }
                                description "The type of mapping.";
                            }

                            leaf timer {
                                type uint32 {
                                    range "0..65535";
                                }
                                units "seconds";
                                description
                                    "Indicates how much longer an ARP entry remains in the ARP cache.

                                     When timer has a value of zero, the entry is cleared from the cache.";
                            }

                        } // list neighbor

                    } // container neighbor-discovery

                    list vrrp {
                        key "virtual-router-id";
                        description "Enter the vrrp list instance";

                        leaf virtual-router-id {
                            type int32 {
                                range "1..255";
                            }
                            description "Virtual Router Identifier (VRID) for the VRRP virtual router instance";
                        }

                        leaf authentication-type {
                            type enumeration {
                                enum "no-authentication"            { value 1; }
                                enum "simple-text-password"         { value 2; }
                                enum "ip-authentication-header"     { value 3; }
                            }
                            description
                                "Authentication type used for VRRP protocol exchanges between
                                 virtual routers. This value of this object is the same for a
                                 given ifIndex.

                                 New enumerations to this list can only be added via a new
                                 RFC on the standards track.";
                        }

                        leaf oper-state {
                            type types-sros:oper-state;
                            description "Operational state.";
                        }

                        leaf router-state {
                            type enumeration {
                                enum "initialize"                   { value 1; }
                                enum "backup"                       { value 2; }
                                enum "master"                       { value 3; }
                            }
                            description
                                "The current state of the virtual router. This object has
                                 three defined values:
                                  - `initialize', which indicates that all the
                                     virtual router is waiting for a startup event.

                                  - `backup', which indicates the virtual router is
                                     monitoring the availability of the master router.

                                  - `master', which indicates that the virtual router
                                     is forwarding packets for IP addresses that are
                                     associated with this router.

                                 Setting the `admin-state' object initiates
                                 transitions in the value of this object.";
                        }

                        leaf virtual-mac {
                            type yang:mac-address;
                            description
                                "The virtual MAC address of the virtual router. Although this
                                 object can be derived from the 'virtual-router-id' object, it is
                                 defined so that it is easily obtainable by a management
                                 application and can be included in VRRP-related SNMP traps.";
                        }

                        leaf master-ip-address {
                            type types-sros:ip-address;
                            description
                                "The master router's real (primary) IP address. This is
                                 the IP address listed as the source in VRRP advertisement
                                 last received by this virtual router.";
                        }

                        leaf primary-ip-address {
                            type types-sros:ip-address;
                            description
                                "In the case where there is more than one IP address for
                                 a given `interface', this object is used to specify the IP
                                 address that will become the `master-ip-addr', should
                                 the virtual router transition from backup to master. If
                                 this object is set to 0.0.0.0, the IP address which is
                                 numerically lowest will be selected.";
                        }

                        leaf up-time {
                            type yang:date-and-time;
                            description
                                "This is the value of the `system up time' object when this
                                 virtual router (i.e., the `oper-state') transitioned
                                 out of `initialized'.";
                        }

                        leaf in-use-priority {
                            type uint32 {
                                range "0..255";
                            }
                            description
                                "Indicates the current in-use priority
                                 associated with the VRRP VRRP.";
                        }

                        leaf master-since {
                            type yang:date-and-time;
                            description
                                "In case of a virtual router which
                                 is the current master, is the sysUpTime when operational state
                                 (oper-state) of the virtual router changed to master(3).
                                 In case of a backup virtual router, this value specifies the
                                 sysUpTime when it received the first VRRP advertisement message
                                 from the virtual router which is the current master.";
                        }

                        leaf master-priority {
                            type uint32 {
                                range "0..255";
                            }
                            description
                                "The value indicates the priority of
                                 the VRRP which is the current master";
                        }

                        leaf master-down-interval {
                            type types-sros:time-duration;
                            units "milliseconds";
                            description
                                "The value indicates the time
                                 interval for the backup router to declare the master as down.
                                 It is calculated as
                                        (3 * Advertisement_Interval) + Skew_time
                                 where Skew_Time is calculated as
                                        (256 - Priority) / 256";
                        }

                        leaf master-down-timer {
                            type types-sros:time-duration;
                            units "milliseconds";
                            description
                                "The value indicates the current
                                 value of the Master Down Timer.

                                 When a backup router receives a VRRP advertisement from a master,
                                 it resets this timer to the value of the Master Down Interval
                                 and begins to count down. If the backup router does not receive
                                 an advertisement till this timer times out, it will assume that
                                 the master is down and will declare itself to be the master.";
                        }

                        leaf in-use-advertisement-interval {
                            type int64;
                            units "milliseconds";
                            description "Indicates the operational value for the advertisement interval.";
                        }

                        leaf init-timer {
                            type types-sros:time-duration;
                            units "milliseconds";
                            description
                                "The value indicates the current value of
                                 initialization delay timer for VRRP, in milliseconds.";
                        }

                        leaf down-reason {
                            type enumeration {
                                enum "unknown"                      { value 0; }
                                enum "not-active"                   { value 1; }
                                enum "admin-down"                   { value 2; }
                                enum "if-down"                      { value 3; }
                                enum "no-link-lcl-addr-cfg"         { value 4; }
                                enum "rtr-adv-no-proper-cfg"        { value 5; }
                                enum "invalid-mac"                  { value 6; }
                            }
                            description
                                "The value indicates the reason for the
                                 operational state to be 'down'.";
                        }

                        container bfd-liveness {
                            description "Enter the bfd-liveness context";

                            leaf src-ip {
                                type types-sros:ip-address;
                                description
                                    "The value indicates the source
                                     IP address on the interface running BFD.";
                            }

                            leaf session-state {
                                type enumeration {
                                    enum "unknown"                      { value 1; }
                                    enum "connected"                    { value 2; }
                                    enum "broken"                       { value 3; }
                                    enum "peer-detects-down"            { value 4; }
                                    enum "not-configured"               { value 5; }
                                    enum "no-resources"                 { value 6; }
                                }
                                description
                                    "The value indicates the operational
                                     state of the BFD session the VRRP is relying
                                     upon for its fast triggering mechanism.";
                            }

                        } // container bfd-liveness

                        list master {
                            key "primary-ip-address";
                            description "Enter the master list instance";

                            leaf primary-ip-address {
                                type types-sros:ipv4-address;
                                description
                                    "This Object is set as read-only in mib. We use it to pass values to the sia-check
                                     function where it should fail.";
                            }

                            leaf last-seen {
                                type yang:date-and-time;
                                description
                                    "The value indicates the sysUpTime
                                     when the master was last seen by this VRRP. In
                                     other words it is the timestamp of the last advertisement message
                                     that was received from that master.";
                            }

                            leaf auth-sequence {
                                type int32;
                                description
                                    "The value indicates the last
                                     sequence number seen in the IP Authentication header of the
                                     advertisement messages received from the master.
                                     A negative value implies that the master was not being
                                     authenticated via IP authentication header.";
                            }

                            leaf ip-list-match {
                                type boolean;
                                description
                                    "The value indicates whether or not
                                     the IP address list in the advertisement messages received from
                                     the master matched the configured virtual router IP address list.";
                            }

                            container statistics {
                                description "Enter the statistics context";

                                leaf messages-received {
                                    type yang:counter32;
                                    description
                                        "The value indicates the total
                                         number of VRRP advertisement messages that have been received
                                         from the master.";
                                }

                            } // container statistics

                        } // list master

                        container statistics {
                            description "Enter the statistics context";

                            leaf authentication-failure-packets-received {
                                type yang:counter32;
                                description
                                    "The total number of VRRP packets received that do not pass
                                     the authentication check.";
                            }

                            leaf authentication-type-mismatch-packets-received {
                                type yang:counter32;
                                description
                                    "The total number of packets received with 'Auth Type' not
                                     equal to the locally configured authentication method
                                     (`vrrpOperAuthType').";
                            }

                            leaf address-list-discards {
                                type yang:counter32;
                                description
                                    "The total number of VRRP advertisement packets discarded
                                     because the address list did not match the locally configured
                                     list for the virtual router.";
                            }

                            leaf become-master {
                                type yang:counter32;
                                description
                                    "The total number of times that this virtual router's state
                                     has transitioned to MASTER.";
                            }

                            leaf advertisements-received {
                                type yang:counter32;
                                description
                                    "The total number of VRRP advertisements received by this
                                     virtual router.";
                            }

                            leaf advertisements-sent {
                                type yang:counter32;
                                description
                                    "The total number of VRRP advertisements sent by this virtual
                                     router.";
                            }

                            leaf advertisement-interval-errors {
                                type yang:counter32;
                                description
                                    "The total number of VRRP advertisement packets received
                                     for which the advertisement interval is different than the
                                     one configured for the local virtual router.";
                            }

                            leaf ttl-error-packets-received {
                                type yang:counter32;
                                description
                                    "The total number of VRRP packets received by the virtual
                                     router with IP TTL (Time-To-Live) not equal to 255.";
                            }

                            leaf zero-priority-packets-received {
                                type yang:counter32;
                                description
                                    "The total number of VRRP packets received by the virtual
                                     router with a priority of '0'.";
                            }

                            leaf zero-priority-packets-sent {
                                type yang:counter32;
                                description
                                    "The total number of VRRP packets sent by the virtual router
                                     with a priority of '0'.";
                            }

                            leaf invalid-type-packets-received {
                                type yang:counter32;
                                description
                                    "The number of VRRP packets received by the virtual router
                                     with an invalid value in the 'type' field.";
                            }

                            leaf address-list-error-packets-received {
                                type yang:counter32;
                                description
                                    "The total number of packets received for which the address
                                     list does not match the locally configured list for the
                                     virtual router.";
                            }

                            leaf error-length-packets-received {
                                type yang:counter32;
                                description
                                    "The total number of packets received with a packet length
                                     less than the length of the VRRP header.";
                            }

                            leaf invalid-authentication-type-packets-received {
                                type yang:counter32;
                                description
                                    "The total number of packets received with an unknown
                                     authentication type.";
                            }

                            leaf preempt-events {
                                type yang:counter32;
                                description
                                    "The value indicates the total
                                     number of times the virtual router has preempted another
                                     non-owner master with lower priority.";
                            }

                            leaf preempted-events {
                                type yang:counter32;
                                description
                                    "The value indicates the total
                                     number of times the virtual router has been preempted by another
                                     non-owner master with higher priority.";
                            }

                            leaf master-changes {
                                type yang:counter32;
                                description
                                    "The value indicates the total
                                     number of times the virtual router has seen the master virtual
                                     router change.";
                            }

                            leaf advertise-interval-discards {
                                type yang:counter32;
                                description
                                    "The total number of VRRP advertisement packets discarded
                                     because the advertisement interval in the received packet
                                     was different than the one configured for the local virtual
                                     router.";
                            }

                            leaf total-discards {
                                type yang:counter32;
                                description
                                    "The total number of VRRP advertisement packets discarded
                                     for any reason. This includes the packets discarded due to
                                     advertise interval mismatch and address list mismatch.";
                            }

                        } // container statistics

                    } // list vrrp

                } // container ipv4

                container ipv6 {
                    description "Enter the ipv6 context";

                    leaf oper-state {
                        type types-sros:oper-state;
                        description "The current IPv6 operational status of this router interface.";
                    }

                    leaf down-reason {
                        type bits {
                            bit admin-disabled                 { position 0; }
                            bit service-admin-disabled         { position 1; }
                            bit port-down                      { position 2; }
                            bit address-or-parent-not-ready    { position 3; }
                            bit associated-object-not-ready    { position 4; }
                            bit rvpls-down                     { position 5; }
                            bit operational-group-down         { position 6; }
                            bit admin-destroy                  { position 7; }
                            bit no-address                     { position 8; }
                            bit no-info                        { position 9; }
                            bit hold-down-timer-running        { position 10; }
                            bit protocol-down                  { position 11; }
                            bit invalid-port-configuration     { position 12; }
                            bit unknown                        { position 13; }
                            bit no-route-distinguisher         { position 14; }
                            bit wlan-gateway-redundancy-standby { position 15; }
                            bit wlan-gateway-group-degraded    { position 16; }
                            bit ip-control-tunnel-down         { position 17; }
                            bit pdn-address-mismatch           { position 18; }
                            bit ping-check-failure             { position 19; }
                            bit port-internal-loopback         { position 20; }
                        }
                        description
                            "Indicates the reason for why the interface is operationally down.
                                             
                             Values:
                                 admin-disabled                  - Administratively disabled.
                                 service-admin-disabled          - Assiocated service is administratively disabled.
                                 port-down                       - Associated SAP/port is operationally down.
                                 address-or-parent-not-ready     - Associated address or parent interface is not ready.
                                 associated-object-not-ready     - Associated object is not ready.
                                 rvpls-down                      - Associated R-VPLS service is operationally down.
                                 operational-group-down          - Associated operational group is operationally down.
                                 admin-destroy                   - The interface is being destroyed.
                                 no-address                      - There is no address configured.
                                 no-info                         - The interface info is not present.
                                 hold-down-timer-running         - The hold down timer is running.
                                 protocol-down                   - The protocols are operationally down.
                                 invalid-port-configuration      - Invalid port configuration.
                                 unknown                         - The interface is operationally down due to some unknown reason.
                                 no-route-distinguisher          - No route-distinguisher configured in the VRF.
                                 wlan-gateway-redundancy-standby - The interface is in standby state for WLAN-GW redundancy.
                                 wlan-gateway-group-degraded     - The interface associated WLAN-GW group is in a degraded state.
                                 ip-control-tunnel-down          - The IP tunnel associated to a control-tunnel interface is operationally down.
                                 pdn-address-mismatch            - The IP address learned from the packet data network does not match the configured primary IP address.
                                 ping-check-failure              - The IP interface is or went down because of a ping-template failure.
                                 port-internal-loopback          - The IP interface is bound to a port that has an internal loopback configured.";
                    }

                    container icmp6 {
                        description "Enter the icmp6 context";

                        container statistics {
                            description "Enter the statistics context";

                            leaf icmp6-in-msgs {
                                type yang:counter32;
                                description
                                    "Total number of ICMPv6 messages received by this interface.
                                                     
                                     This includes all those counted by icmp6-in-errors. Note that this
                                     interface is the interface to which the ICMPv6 messages were
                                     addressed which may not be necessarily the input interface
                                     for the messages.";
                            }

                            leaf icmp6-in-errors {
                                type yang:counter32;
                                description
                                    "Number of ICMPv6 errored messages received by this interface.
                                                     
                                     This implies ICMPv6 messages determined as having specific
                                     ICMPv6 errors (bad ICMP checksums, bad length, etc.).";
                            }

                            leaf icmp6-in-dest-unreachables {
                                type yang:counter32;
                                description "Nmber of ICMPv6 destination unreachable messages received by this interface.";
                            }

                            leaf icmp6-in-admin-prohibs {
                                type yang:counter32;
                                description
                                    "Number of ICMPv6 destination unreachable/communication administratively
                                     prohibited messages received by this interface.";
                            }

                            leaf icmp6-in-time-exceeds {
                                type yang:counter32;
                                description "Number of ICMPv6 time exceeded messages received by this interface.";
                            }

                            leaf icmp6-in-parm-problems {
                                type yang:counter32;
                                description "Number of ICMPv6 parameter problem messages received by this interface.";
                            }

                            leaf icmp6-in-pkt-too-bigs {
                                type yang:counter32;
                                description "Number of ICMPv6 packet too big messages received by this interface.";
                            }

                            leaf icmp6-in-echos {
                                type yang:counter32;
                                description "Number of ICMPv6 echo (request) messages received by this interface.";
                            }

                            leaf icmp6-in-echo-replies {
                                type yang:counter32;
                                description "Number of ICMPv6 echo reply messages received by this interface.";
                            }

                            leaf icmp6-in-rtr-solicits {
                                type yang:counter32;
                                description "Number of ICMPv6 router solicitation messages received by this interface.";
                            }

                            leaf icmp6-in-rtr-advertisements {
                                type yang:counter32;
                                description "Number of ICMPv6 router advertisement messages received by this interface.";
                            }

                            leaf icmp6-in-nbr-solicits {
                                type yang:counter32;
                                description "Number of ICMPv6 neighbor solicitation messages received by this interface.";
                            }

                            leaf icmp6-in-nbr-advertisements {
                                type yang:counter32;
                                description "Number of ICMPv6 neighbor advertisement messages received by this interface.";
                            }

                            leaf icmp6-in-redirects {
                                type yang:counter32;
                                description "Number of ICMPv6 redirect messages received by this interface.";
                            }

                            leaf icmp6-in-grp-memb-queries {
                                type yang:counter32;
                                description "Number of ICMPv6 group membership query messages received by this interface.";
                            }

                            leaf icmp6-in-grp-memb-repsonses {
                                type yang:counter32;
                                description "Number of ICMPv6 group membership response messages received by this interface.";
                            }

                            leaf icmp6-in-grp-memb-reductions {
                                type yang:counter32;
                                description "Number of ICMPv6 group membership reduction messages received by this interface.";
                            }

                            leaf icmp6-out-msgs {
                                type yang:counter32;
                                description
                                    "Total number of ICMPv6 messages this interface attempted to send.
                                                     
                                     This includes all those counted by icmp6-out-errors.";
                            }

                            leaf icmp6-out-errors {
                                type yang:counter32;
                                description
                                    "Number of ICMPv6 messages this interface could not be send due to problems
                                     discovered within ICMPv6 such as lack of buffers.
                                                     
                                     This value should not include errors discovered outside the ICMPv6 layer such as
                                     the inability of VRtr IPv6 to route the resultant datagram. In some implementations
                                     there may be no types of error which contribute to this counter's value.";
                            }

                            leaf icmp6-out-dest-unreachables {
                                type yang:counter32;
                                description "Number of ICMPv6 destination unreachable messages sent by this interface.";
                            }

                            leaf icmp6-out-admin-prohibs {
                                type yang:counter32;
                                description
                                    "Number of ICMPv6 destination unreachable/communication administratively prohibited
                                     messages sent by this interface.";
                            }

                            leaf icmp6-out-time-exceeds {
                                type yang:counter32;
                                description "Number of ICMPv6 time exceeded messages sent by this interface.";
                            }

                            leaf icmp6-out-parm-problems {
                                type yang:counter32;
                                description "Number of ICMPv6 parameter problem messages sent by this interface.";
                            }

                            leaf icmp6-out-pkt-too-bigs {
                                type yang:counter32;
                                description "Number of ICMPv6 packet too big messages sent by this interface.";
                            }

                            leaf icmp6-out-echos {
                                type yang:counter32;
                                description "Number of ICMPv6 echo request messages sent by this interface.";
                            }

                            leaf icmp6-out-echo-replies {
                                type yang:counter32;
                                description "Number of ICMPv6 echo reply messages sent by this interface.";
                            }

                            leaf icmp6-out-rtr-solicits {
                                type yang:counter32;
                                description "Number of ICMPv6 router solicitation messages sent by this interface.";
                            }

                            leaf icmp6-out-rtr-advertisements {
                                type yang:counter32;
                                description "Number of ICMPv6 router advertisement messages sent by this interface.";
                            }

                            leaf icmp6-out-nbr-solicits {
                                type yang:counter32;
                                description "Number of ICMPv6 neighbor solicitation messages sent by this interface.";
                            }

                            leaf icmp6-out-nbr-advertisements {
                                type yang:counter32;
                                description "Number of ICMPv6 neighbor advertisement messages sent by this interface.";
                            }

                            leaf icmp6-out-redirects {
                                type yang:counter32;
                                description "Number of ICMPv6 redirect messages sent by this interface.";
                            }

                            leaf icmp6-out-grp-memb-queries {
                                type yang:counter32;
                                description "Number of ICMPv6 group membership query messages sent by this interface.";
                            }

                            leaf icmp6-out-grp-memb-responses {
                                type yang:counter32;
                                description "Number of ICMPv6 group membership response messages sent by this interface.";
                            }

                            leaf icmp6-out-grp-memb-reductions {
                                type yang:counter32;
                                description "Number of ICMPv6 group membership reduction messages sent by this interface.";
                            }

                            leaf icmp6-out-discards {
                                type yang:counter32;
                                description "Number of discarded ICMPv6 messages on this interface.";
                            }

                        } // container statistics

                    } // container icmp6

                    container link-local-address {
                        description "Enter the link-local-address context";

                        leaf oper-address {
                            type types-sros:ipv6-address;
                            description "Indicates the link-local IPv6 address of this router interface.";
                        }

                        leaf address-state {
                            type types-sros:address-state;
                            description "Indicates the address state of the IPv6 address of the interface.";
                        }

                    } // container link-local-address

                    container statistics {
                        description "Enter the statistics context";

                        leaf out-packets {
                            type yang:counter64;
                            description "The number of packets transmitted by this interface.";
                        }

                        leaf out-octets {
                            type yang:counter64;
                            description "The number of octets transmitted by this interface.";
                        }

                        leaf out-discard-packets {
                            type yang:counter64;
                            description "The number of transmit packets discarded.";
                        }

                        leaf out-discard-octets {
                            type yang:counter64;
                            description "The number of transmit octets discarded.";
                        }

                        leaf in-packets {
                            type yang:counter64;
                            description "The number of packets received.";
                        }

                        leaf in-octets {
                            type yang:counter64;
                            description "The number of octets received.";
                        }

                        leaf urpf-check-fail-packets {
                            type yang:counter64;
                            description "The number of packets that fail uRPF check on this interface.";
                        }

                        leaf urpf-check-fail-octets {
                            type yang:counter64;
                            description "The number of octets in the packets that fail uRPF check.";
                        }

                    } // container statistics

                    list address {
                        key "ipv6-address";
                        description "Enter the address list instance";

                        leaf ipv6-address {
                            type types-sros:ipv6-address;
                            description "IPv6 address assigned to the interface";
                        }

                        leaf address-state {
                            type types-sros:address-state;
                            description "Indicates the address state of the IPv6 address of the interface.";
                        }

                        leaf oper-address {
                            type types-sros:ip-address;
                            description "Indicates the operational address of this entry.";
                        }

                        leaf creation-origin {
                            type types-sros:creation-origin;
                            description "Indicates the mechanism used to create this entry.";
                        }

                        leaf primary-preferred {
                            type boolean;
                            description "Indicates whether this IP address is selected as the preferred primary address.";
                        }

                    } // list address

                    container neighbor-discovery {
                        description "Enter the neighbor-discovery context";

                        list neighbor {
                            key "ipv6-address";
                            description "Enter the neighbor list instance";

                            leaf ipv6-address {
                                type types-sros:ipv6-address;
                                description "IPv6 address corresponding to the media-dependent physical address";
                            }

                            leaf state {
                                type enumeration {
                                    enum "incomplete"                   { value 0; }
                                    enum "reachable"                    { value 1; }
                                    enum "stale"                        { value 2; }
                                    enum "delay"                        { value 3; }
                                    enum "probe"                        { value 4; }
                                }
                                description
                                    "The Neighbor Unreachability Detection state for the interface
                                     when the address mapping is used.";
                            }

                            leaf is-router {
                                type boolean;
                                description "Indicates whether this entry is a router.";
                            }

                            leaf secure-nd {
                                type enumeration {
                                    enum "not-applicable"               { value 0; }
                                    enum "secure"                       { value 1; }
                                    enum "unsecure"                     { value 2; }
                                }
                                description
                                    "Indicates whether the physical address is received
                                     via Secured Neighbor Discovery messages.";
                            }

                            leaf mtu {
                                type uint32;
                                description "The MTU of the link attached to this entry.";
                            }

                            leaf mac-address {
                                type yang:mac-address;
                                description "The media-dependent physical address.";
                            }

                            leaf type {
                                type enumeration {
                                    enum "other"                        { value 0; }
                                    enum "static"                       { value 1; }
                                    enum "dynamic"                      { value 2; }
                                    enum "managed"                      { value 100; }
                                    enum "evpn"                         { value 101; }
                                }
                                description "The type of mapping.";
                            }

                            leaf timer {
                                type uint32 {
                                    range "0..65535";
                                }
                                units "seconds";
                                description
                                    "Indicates how much longer an ARP entry remains in the ARP cache.

                                     When timer has a value of zero, the entry is cleared from the cache.";
                            }

                        } // list neighbor

                    } // container neighbor-discovery

                    list vrrp {
                        key "virtual-router-id";
                        description "Enter the vrrp list instance";

                        leaf virtual-router-id {
                            type int32 {
                                range "1..255";
                            }
                            description "Virtual Router Identifier (VRID) for the VRRP virtual router instance";
                        }

                        leaf oper-state {
                            type types-sros:oper-state;
                            description "Operational state.";
                        }

                        leaf router-state {
                            type enumeration {
                                enum "initialize"                   { value 1; }
                                enum "backup"                       { value 2; }
                                enum "master"                       { value 3; }
                            }
                            description
                                "The current state of the virtual router. This object has
                                 three defined values:
                                  - `initialize', which indicates that all the
                                     virtual router is waiting for a startup event.

                                  - `backup', which indicates the virtual router is
                                     monitoring the availability of the master router.

                                  - `master', which indicates that the virtual router
                                     is forwarding packets for IP addresses that are
                                     associated with this router.

                                 Setting the `admin-state' object initiates
                                 transitions in the value of this object.";
                        }

                        leaf virtual-mac {
                            type yang:mac-address;
                            description
                                "The virtual MAC address of the virtual router. Although this
                                 object can be derived from the 'virtual-router-id' object, it is
                                 defined so that it is easily obtainable by a management
                                 application and can be included in VRRP-related SNMP traps.";
                        }

                        leaf master-ip-address {
                            type types-sros:ip-address;
                            description
                                "The master router's real (primary) IP address. This is
                                 the IP address listed as the source in VRRP advertisement
                                 last received by this virtual router.";
                        }

                        leaf primary-ip-address {
                            type types-sros:ip-address;
                            description
                                "In the case where there is more than one IP address for
                                 a given `interface', this object is used to specify the IP
                                 address that will become the `master-ip-addr', should
                                 the virtual router transition from backup to master. If
                                 this object is set to 0.0.0.0, the IP address which is
                                 numerically lowest will be selected.";
                        }

                        leaf up-time {
                            type yang:date-and-time;
                            description
                                "This is the value of the `system up time' object when this
                                 virtual router (i.e., the `oper-state') transitioned
                                 out of `initialized'.";
                        }

                        leaf in-use-priority {
                            type uint32 {
                                range "0..255";
                            }
                            description
                                "Indicates the current in-use priority
                                 associated with the VRRP VRRP.";
                        }

                        leaf master-since {
                            type yang:date-and-time;
                            description
                                "In case of a virtual router which
                                 is the current master, is the sysUpTime when operational state
                                 (oper-state) of the virtual router changed to master(3).
                                 In case of a backup virtual router, this value specifies the
                                 sysUpTime when it received the first VRRP advertisement message
                                 from the virtual router which is the current master.";
                        }

                        leaf master-priority {
                            type uint32 {
                                range "0..255";
                            }
                            description
                                "The value indicates the priority of
                                 the VRRP which is the current master";
                        }

                        leaf master-down-interval {
                            type types-sros:time-duration;
                            units "milliseconds";
                            description
                                "The value indicates the time
                                 interval for the backup router to declare the master as down.
                                 It is calculated as
                                        (3 * Advertisement_Interval) + Skew_time
                                 where Skew_Time is calculated as
                                        (256 - Priority) / 256";
                        }

                        leaf master-down-timer {
                            type types-sros:time-duration;
                            units "milliseconds";
                            description
                                "The value indicates the current
                                 value of the Master Down Timer.

                                 When a backup router receives a VRRP advertisement from a master,
                                 it resets this timer to the value of the Master Down Interval
                                 and begins to count down. If the backup router does not receive
                                 an advertisement till this timer times out, it will assume that
                                 the master is down and will declare itself to be the master.";
                        }

                        leaf in-use-advertisement-interval {
                            type int64;
                            units "milliseconds";
                            description "Indicates the operational value for the advertisement interval.";
                        }

                        leaf init-timer {
                            type types-sros:time-duration;
                            units "milliseconds";
                            description
                                "The value indicates the current value of
                                 initialization delay timer for VRRP, in milliseconds.";
                        }

                        leaf down-reason {
                            type enumeration {
                                enum "unknown"                      { value 0; }
                                enum "not-active"                   { value 1; }
                                enum "admin-down"                   { value 2; }
                                enum "if-down"                      { value 3; }
                                enum "no-link-lcl-addr-cfg"         { value 4; }
                                enum "rtr-adv-no-proper-cfg"        { value 5; }
                                enum "invalid-mac"                  { value 6; }
                            }
                            description
                                "The value indicates the reason for the
                                 operational state to be 'down'.";
                        }

                        container bfd-liveness {
                            description "Enter the bfd-liveness context";

                            leaf src-ip {
                                type types-sros:ip-address;
                                description
                                    "The value indicates the source
                                     IP address on the interface running BFD.";
                            }

                            leaf session-state {
                                type enumeration {
                                    enum "unknown"                      { value 1; }
                                    enum "connected"                    { value 2; }
                                    enum "broken"                       { value 3; }
                                    enum "peer-detects-down"            { value 4; }
                                    enum "not-configured"               { value 5; }
                                    enum "no-resources"                 { value 6; }
                                }
                                description
                                    "The value indicates the operational
                                     state of the BFD session the VRRP is relying
                                     upon for its fast triggering mechanism.";
                            }

                        } // container bfd-liveness

                        list master {
                            key "primary-ip-address";
                            description "Enter the master list instance";

                            leaf primary-ip-address {
                                type types-sros:ipv6-address;
                                description
                                    "This Object is set as read-only in mib. We use it to pass values to the sia-check
                                     function where it should fail.";
                            }

                            leaf last-seen {
                                type yang:date-and-time;
                                description
                                    "The value indicates the sysUpTime
                                     when the master was last seen by this VRRP. In
                                     other words it is the timestamp of the last advertisement message
                                     that was received from that master.";
                            }

                            leaf auth-sequence {
                                type int32;
                                description
                                    "The value indicates the last
                                     sequence number seen in the IP Authentication header of the
                                     advertisement messages received from the master.
                                     A negative value implies that the master was not being
                                     authenticated via IP authentication header.";
                            }

                            leaf ip-list-match {
                                type boolean;
                                description
                                    "The value indicates whether or not
                                     the IP address list in the advertisement messages received from
                                     the master matched the configured virtual router IP address list.";
                            }

                            container statistics {
                                description "Enter the statistics context";

                                leaf messages-received {
                                    type yang:counter32;
                                    description
                                        "The value indicates the total
                                         number of VRRP advertisement messages that have been received
                                         from the master.";
                                }

                            } // container statistics

                        } // list master

                        container statistics {
                            description "Enter the statistics context";

                            leaf discontinuity-time {
                                type yang:date-and-time;
                                description
                                    "The value of sysUpTime on the most recent occasion at
                                     which any one or more of this entry's counters suffered
                                     a discontinuity.

                                     If no such discontinuities have occurred since the last
                                     re-initialization of the local management subsystem,
                                     then this object contains a zero value.";
                            }

                            leaf refresh-rate {
                                type uint32;
                                units "milliseconds";
                                description
                                    "The minimum reasonable polling interval for this entry.
                                     This object provides an indication of the minimum
                                     Amount of time required to update the counters in this
                                     entry.";
                            }

                            leaf become-master {
                                type yang:counter32;
                                description
                                    "The total number of times that this virtual router's state
                                     has transitioned to MASTER.";
                            }

                            leaf advertisements-received {
                                type yang:counter32;
                                description
                                    "The total number of VRRP advertisements received by this
                                     virtual router.";
                            }

                            leaf advertisements-sent {
                                type yang:counter32;
                                description
                                    "The total number of VRRP advertisements sent by this virtual
                                     router.";
                            }

                            leaf advertisement-interval-errors {
                                type yang:counter32;
                                description
                                    "The total number of VRRP advertisement packets received
                                     for which the advertisement interval is different than the
                                     one configured for the local virtual router.";
                            }

                            leaf ttl-error-packets-received {
                                type yang:counter32;
                                description
                                    "The total number of VRRP packets received by the virtual
                                     router with IP TTL (Time-To-Live) not equal to 255.";
                            }

                            leaf zero-priority-packets-received {
                                type yang:counter32;
                                description
                                    "The total number of VRRP packets received by the virtual
                                     router with a priority of '0'.";
                            }

                            leaf zero-priority-packets-sent {
                                type yang:counter32;
                                description
                                    "The total number of VRRP packets sent by the virtual router
                                     with a priority of '0'.";
                            }

                            leaf invalid-type-packets-received {
                                type yang:counter32;
                                description
                                    "The number of VRRP packets received by the virtual router
                                     with an invalid value in the 'type' field.";
                            }

                            leaf address-list-error-packets-received {
                                type yang:counter32;
                                description
                                    "The total number of packets received for which the address
                                     list does not match the locally configured list for the
                                     virtual router.";
                            }

                            leaf error-length-packets-received {
                                type yang:counter32;
                                description
                                    "The total number of packets received with a packet length
                                     less than the length of the VRRP header.";
                            }

                            leaf invalid-authentication-type-packets-received {
                                type yang:counter32;
                                description
                                    "The total number of packets received with an unknown
                                     authentication type.";
                            }

                            leaf preempt-events {
                                type yang:counter32;
                                description
                                    "The value indicates the total
                                     number of times the virtual router has preempted another
                                     non-owner master with lower priority.";
                            }

                            leaf preempted-events {
                                type yang:counter32;
                                description
                                    "The value indicates the total
                                     number of times the virtual router has been preempted by another
                                     non-owner master with higher priority.";
                            }

                            leaf master-changes {
                                type yang:counter32;
                                description
                                    "The value indicates the total
                                     number of times the virtual router has seen the master virtual
                                     router change.";
                            }

                            leaf advertise-interval-discards {
                                type yang:counter32;
                                description
                                    "The total number of VRRP advertisement packets discarded
                                     because the advertisement interval in the received packet
                                     was different than the one configured for the local virtual
                                     router.";
                            }

                            leaf total-discards {
                                type yang:counter32;
                                description
                                    "The total number of VRRP advertisement packets discarded
                                     for any reason. This includes the packets discarded due to
                                     advertise interval mismatch and address list mismatch.";
                            }

                        } // container statistics

                    } // list vrrp

                } // container ipv6

            } // list interface

            container ipv4 {
                description "Enter the ipv4 context";

                container icmp {
                    description "Enter the icmp context";

                    container statistics {
                        description "Enter the statistics context";

                        leaf icmp-in-msgs {
                            type yang:counter32;
                            description
                                "Number of ICMPv4 messages received by this router instance.

                                 This includes all those counted by icmp-in-errors.";
                        }

                        leaf icmp-in-errors {
                            type yang:counter32;
                            description
                                "Number of ICMPv4 errored messages received by this router instance.
                                                 
                                 This implies ICMPv4 messages determined as having specific
                                 ICMPv4 errors (bad ICMPv4 checksums, bad length, etc.).";
                        }

                        leaf icmp-in-dest-unreachables {
                            type yang:counter32;
                            description "Number of ICMPv4 destination unreachable messages received by this router instance.";
                        }

                        leaf icmp-in-redirects {
                            type yang:counter32;
                            description "Number of ICMPv4 redirect messages received by this router instance.";
                        }

                        leaf icmp-in-echos {
                            type yang:counter32;
                            description "Number of ICMPv4 echo (request) messages received by this router instance.";
                        }

                        leaf icmp-in-echo-replies {
                            type yang:counter32;
                            description "Number of ICMPv4 echo reply messages received by this router instance.";
                        }

                        leaf icmp-in-time-exceeds {
                            type yang:counter32;
                            description "Number of ICMPv4 time exceeded messages received by this router instance.";
                        }

                        leaf icmp-in-src-quenches {
                            type yang:counter32;
                            description "Number of ICMPv4 source quench messages received by this router instance.";
                        }

                        leaf icmp-in-timestamps {
                            type yang:counter32;
                            description "Number of ICMPv4 timestamp (request) messages received by this router instance.";
                        }

                        leaf icmp-in-timestamp-replies {
                            type yang:counter32;
                            description "Number of ICMPv4 timestamp reply messages received by this router instance.";
                        }

                        leaf icmp-in-address-masks {
                            type yang:counter32;
                            description "Number of ICMPv4 address mask request messages received by this router instance.";
                        }

                        leaf icmp-in-address-mask-replies {
                            type yang:counter32;
                            description "Number of ICMPv4 address mask reply messages received by this router instance.";
                        }

                        leaf icmp-in-parm-problems {
                            type yang:counter32;
                            description "Number of ICMPv4 parameter problem messages received by this router instance.";
                        }

                        leaf icmp-out-msgs {
                            type yang:counter32;
                            description
                                "Total number of ICMPv4 messages this router instance attempted to send.
                                                 
                                 This includes all those counted by icmp-out-errors.";
                        }

                        leaf icmp-out-errors {
                            type yang:counter32;
                            description
                                "Number of ICMPv4 messages that could not be send due to problems discovered within ICMPv4
                                 such as lack of buffers.
                                                 
                                 This value should not include errors discovered outside the ICMPv4 layer such as
                                 the inability of VRtr IPv4 to route the resultant datagram. In some implementations
                                 there may be no types of error which contribute to this counter's value.";
                        }

                        leaf icmp-out-dest-unreachables {
                            type yang:counter32;
                            description "Number of ICMPv4 destination unreachable messages sent by this router instance.";
                        }

                        leaf icmp-out-redirects {
                            type yang:counter32;
                            description "Number of ICMPv4 redirect messages sent by this router instance.";
                        }

                        leaf icmp-out-echos {
                            type yang:counter32;
                            description "Number of ICMPv4 echo request messages sent by this router instance.";
                        }

                        leaf icmp-out-echo-replies {
                            type yang:counter32;
                            description "Number of ICMPv4 echo reply messages sent by this router instance.";
                        }

                        leaf icmp-out-time-exceeds {
                            type yang:counter32;
                            description "Number of ICMPv4 time exceeded messages sent by this router instance.";
                        }

                        leaf icmp-out-src-quenches {
                            type yang:counter32;
                            description "Number of ICMPv4 source quench messages sent by this router instance.";
                        }

                        leaf icmp-out-timestamps {
                            type yang:counter32;
                            description "Number of ICMPv4 timestamp (request) messages sent by this router instance.";
                        }

                        leaf icmp-out-timestamp-replies {
                            type yang:counter32;
                            description "Number of ICMPv4 timestamp reply messages sent by this router instance.";
                        }

                        leaf icmp-out-address-masks {
                            type yang:counter32;
                            description "Number of ICMPv4 address mask request messages sent by this router instance.";
                        }

                        leaf icmp-out-address-mask-replies {
                            type yang:counter32;
                            description "Number of ICMPv4 address mask reply messages sent by this router instance.";
                        }

                        leaf icmp-out-parm-problems {
                            type yang:counter32;
                            description "Number of ICMPv4 parameter problem messages sent by this router instance.";
                        }

                        leaf icmp-out-discards {
                            type yang:counter32;
                            description "Number of discarded ICMPv4 messages on this router instance.";
                        }

                    } // container statistics

                } // container icmp

            } // container ipv4

            container ipv6 {
                description "Enter the ipv6 context";

                container icmp6 {
                    description "Enter the icmp6 context";

                    container statistics {
                        description "Enter the statistics context";

                        leaf icmp6-in-msgs {
                            type yang:counter32;
                            description
                                "Total number of ICMPv6 messages received by this router instance.
                                                 
                                 This includes all those counted by icmp6-in-errors.";
                        }

                        leaf icmp6-in-errors {
                            type yang:counter32;
                            description
                                "Number of ICMPv6 errored messages received by this router instance.

                                 This implies ICMPv6 messages determined as having specific
                                 ICMPv6 errors (bad ICMP checksums, bad length, etc.).";
                        }

                        leaf icmp6-in-dest-unreachables {
                            type yang:counter32;
                            description "Number of ICMPv6 destination unreachable messages received by this router instance.";
                        }

                        leaf icmp6-in-admin-prohibs {
                            type yang:counter32;
                            description
                                "Number of ICMPv6 destination unreachable/communication administratively
                                 prohibited messages received by this router instance.";
                        }

                        leaf icmp6-in-time-exceeds {
                            type yang:counter32;
                            description "Number of ICMPv6 time exceeded messages received by this router instance.";
                        }

                        leaf icmp6-in-parm-problems {
                            type yang:counter32;
                            description "Number of ICMPv6 parameter problem messages received by this router instance.";
                        }

                        leaf icmp6-in-pkt-too-bigs {
                            type yang:counter32;
                            description "Number of ICMPv6 packet too big messages received by this router instance.";
                        }

                        leaf icmp6-in-echos {
                            type yang:counter32;
                            description "Number of ICMPv6 echo (request) messages received by this router instance.";
                        }

                        leaf icmp6-in-echo-replies {
                            type yang:counter32;
                            description "Number of ICMPv6 echo reply messages received by this router instance.";
                        }

                        leaf icmp6-in-rtr-solicits {
                            type yang:counter32;
                            description "Number of ICMPv6 router solicitation messages received by this router instance.";
                        }

                        leaf icmp6-in-rtr-advertisements {
                            type yang:counter32;
                            description "Number of ICMPv6 router advertisement messages received by this router instance.";
                        }

                        leaf icmp6-in-nbr-solicits {
                            type yang:counter32;
                            description "Number of ICMPv6 neighbor solicitation messages received by this router instance.";
                        }

                        leaf icmp6-in-nbr-advertisements {
                            type yang:counter32;
                            description "Number of ICMPv6 neighbor advertisement messages received by this router instance.";
                        }

                        leaf icmp6-in-redirects {
                            type yang:counter32;
                            description "Number of ICMPv6 redirect messages received by this router instance.";
                        }

                        leaf icmp6-in-grp-memb-queries {
                            type yang:counter32;
                            description "Number of ICMPv6 group membership query messages received by this router instance.";
                        }

                        leaf icmp6-in-grp-memb-repsonses {
                            type yang:counter32;
                            description "Number of ICMPv6 group membership response messages received by this router instance.";
                        }

                        leaf icmp6-in-grp-memb-reductions {
                            type yang:counter32;
                            description "Number of ICMPv6 group membership reduction messages received by this router instance.";
                        }

                        leaf icmp6-out-msgs {
                            type yang:counter32;
                            description
                                "Total number of ICMPv6 messages this router instance attempted to send.
                                                 
                                 This includes all those counted by icmp6-out-errors.";
                        }

                        leaf icmp6-out-errors {
                            type yang:counter32;
                            description
                                "Number of ICMPv6 messages this router instance could not be send due to problems
                                 discovered within ICMPv6 such as lack of buffers.
                                                 
                                 This value should not include errors discovered outside the ICMPv6 layer such as
                                 the inability of VRtr IPv6 to route the resultant datagram. In some implementations
                                 there may be no types of error which contribute to this counter's value.";
                        }

                        leaf icmp6-out-dest-unreachables {
                            type yang:counter32;
                            description "Number of ICMPv6 destination unreachable messages sent by this router instance.";
                        }

                        leaf icmp6-out-admin-prohibs {
                            type yang:counter32;
                            description
                                "Number of ICMPv6 destination unreachable/communication administratively
                                 prohibited messages sent by this router instance.";
                        }

                        leaf icmp6-out-time-exceeds {
                            type yang:counter32;
                            description "Number of ICMPv6 time exceeded messages sent by this router instance.";
                        }

                        leaf icmp6-out-parm-problems {
                            type yang:counter32;
                            description "Number of ICMPv6 parameter problem messages sent by this router instance.";
                        }

                        leaf icmp6-out-pkt-too-bigs {
                            type yang:counter32;
                            description "Number of ICMPv6 packet too big messages sent by this router instance.";
                        }

                        leaf icmp6-out-echos {
                            type yang:counter32;
                            description "Number of ICMPv6 echo request messages sent by this router instance.";
                        }

                        leaf icmp6-out-echo-replies {
                            type yang:counter32;
                            description "Number of ICMPv6 echo reply messages sent by this router instance.";
                        }

                        leaf icmp6-out-rtr-solicits {
                            type yang:counter32;
                            description "Number of ICMPv6 router solicitation messages sent by this router instance.";
                        }

                        leaf icmp6-out-rtr-advertisements {
                            type yang:counter32;
                            description "Number of ICMPv6 router advertisement messages sent by this router instance.";
                        }

                        leaf icmp6-out-nbr-solicits {
                            type yang:counter32;
                            description "Number of ICMPv6 neighbor solicitation messages sent by this router instance.";
                        }

                        leaf icmp6-out-nbr-advertisements {
                            type yang:counter32;
                            description "Number of ICMPv6 neighbor advertisement messages sent by this router instance.";
                        }

                        leaf icmp6-out-redirects {
                            type yang:counter32;
                            description "Number of ICMPv6 redirect messages sent by this router instance.";
                        }

                        leaf icmp6-out-grp-memb-queries {
                            type yang:counter32;
                            description "Number of ICMPv6 group membership query messages sent by this router instance.";
                        }

                        leaf icmp6-out-grp-memb-responses {
                            type yang:counter32;
                            description "Number of ICMPv6 group membership response messages sent by this router instance.";
                        }

                        leaf icmp6-out-grp-memb-reductions {
                            type yang:counter32;
                            description "Number of ICMPv6 group membership reduction messages sent by this router instance.";
                        }

                        leaf icmp6-out-discards {
                            type yang:counter32;
                            description "Number of discarded ICMPv6 messages on this router instance.";
                        }

                    } // container statistics

                } // container icmp6

                container router-advertisement {
                    description "Enter the router-advertisement context";

                    list interface {
                        key "ip-int-name";
                        description "Enter the interface list instance";

                        leaf ip-int-name {
                            type types-sros:interface-name;
                            description "Router interface name";
                        }

                        leaf creation-origin {
                            type types-sros:creation-origin;
                            description "Indicates the mechanism which created this router advertisement.";
                        }

                    } // list interface

                } // container router-advertisement

            } // container ipv6

            container tunnel-interface {
                description "Enter the tunnel-interface context";

                list rsvp-p2mp-root {
                    key "lsp-name";
                    description "Enter the rsvp-p2mp-root list instance";

                    leaf lsp-name {
                        type types-sros:named-item;
                        description "LSP name of the P2MP RSVP tunnel interface";
                    }

                    leaf interface-index {
                        type uint32;
                        description "The tunnel interface index of the P2MP RSVP tunnel interface";
                    }

                } // list rsvp-p2mp-root

                list rsvp-p2mp-leaf {
                    key "lsp-name sender-address";
                    description "Enter the rsvp-p2mp-leaf list instance";

                    leaf lsp-name {
                        type types-sros:named-item;
                        description "LSP name of the P2MP RSVP tunnel interface";
                    }

                    leaf sender-address {
                        type types-sros:ipv4-unicast-address;
                        description "Address of a sender for the P2MP RSVP tunnel interface instance";
                    }

                    leaf interface-index {
                        type uint32;
                        description "The tunnel interface index of the P2MP RSVP tunnel interface";
                    }

                } // list rsvp-p2mp-leaf

                list ldp-p2mp-root {
                    key "p2mp-id sender-address";
                    description "Enter the ldp-p2mp-root list instance";

                    leaf p2mp-id {
                        type uint32 {
                            range "1..8192";
                        }
                        description "Identifier used for signaling MLDP P2MP LSP";
                    }

                    leaf sender-address {
                        type types-sros:ipv4-unicast-address;
                        description "Address of an LDP sender for the P2MP RSVP tunnel interface instance";
                    }

                    leaf interface-index {
                        type uint32;
                        description "The interface index of the virtual router LDP tunnel interface";
                    }

                } // list ldp-p2mp-root

                list ldp-p2mp-leaf {
                    key "p2mp-id sender-address";
                    description "Enter the ldp-p2mp-leaf list instance";

                    leaf p2mp-id {
                        type uint32;
                        description "Identifier used for signaling MLDP P2MP LSP";
                    }

                    leaf sender-address {
                        type types-sros:ipv4-unicast-address;
                        description "Address of an LDP sender for the P2MP RSVP tunnel interface instance";
                    }

                    leaf interface-index {
                        type uint32;
                        description "The interface index of the virtual router LDP tunnel interface";
                    }

                } // list ldp-p2mp-leaf

            } // container tunnel-interface

            container pcp {
                description "Enter the pcp context";

                list server {
                    key "name";
                    description "Enter the server list instance";

                    leaf name {
                        type types-sros:named-item;
                        description "PCP server name";
                    }

                    leaf oper-state {
                        type types-sros:oper-state;
                        description "Operational state of PCP server";
                    }

                    leaf oper-state-reason {
                        type string;
                        description "Description of the state of the PCP server";
                    }

                    leaf epoch {
                        type uint32;
                        description "PCP server epoch";
                    }

                    list interface {
                        key "name";
                        description "Enter the interface list instance";

                        leaf name {
                            type leafref {
                                path "../../../../interface/interface-name";
                            }
                            description "Interface name";
                        }

                        container statistics {
                            description "Enter the statistics context";

                            container received {
                                description "Enter the received context";

                                container opcode {
                                    description "Enter the opcode context";

                                    leaf announce {
                                        type yang:counter64;
                                        description "Received announce requests";
                                    }

                                    leaf map {
                                        type yang:counter64;
                                        description "Received map requests";
                                    }

                                    leaf peer {
                                        type yang:counter64;
                                        description "Received peer requests";
                                    }

                                    leaf get {
                                        type yang:counter64;
                                        description "Received get requests";
                                    }

                                    leaf unknown {
                                        type yang:counter64;
                                        description "Received requests with an unknown or unsupported opcodes";
                                    }

                                } // container opcode

                                container option {
                                    description "Enter the option context";

                                    leaf description {
                                        type yang:counter64;
                                        description "Received requests containing the description option";
                                    }

                                    leaf filter {
                                        type yang:counter64;
                                        description "Received requests containing the filter option";
                                    }

                                    leaf next {
                                        type yang:counter64;
                                        description "Received requests containing the next option";
                                    }

                                    leaf port-reservation {
                                        type yang:counter64;
                                        description "Received PCP requests containing the port-reservation option";
                                    }

                                    leaf prefer-failure {
                                        type yang:counter64;
                                        description "Received requests containing the prefer-failure option";
                                    }

                                    leaf third-party {
                                        type yang:counter64;
                                        description "Received requests containing a third-party option";
                                    }

                                    leaf unknown {
                                        type yang:counter64;
                                        description "Received requests containing unknown or unsupported options";
                                    }

                                } // container option

                                container dropped {
                                    description "Enter the dropped context";

                                    leaf packet-too-short {
                                        type yang:counter64;
                                        description "Dropped requests due to the packet being too short";
                                    }

                                    leaf wrong-r-bit {
                                        type yang:counter64;
                                        description "Dropped requests due to the wrong r bit";
                                    }

                                    leaf invalid-source-address {
                                        type yang:counter64;
                                        description "Dropped requests due to the use of an invalid source address";
                                    }

                                    leaf oper-down {
                                        type yang:counter64;
                                        description "Dropped requests due to the PCP server being operationally down";
                                    }

                                } // container dropped

                            } // container received

                            container transmitted {
                                description "Enter the transmitted context";

                                leaf v4 {
                                    type yang:counter64;
                                    description "Replies sent via IPv4";
                                }

                                leaf v6 {
                                    type yang:counter64;
                                    description "Replies sent via IPv6";
                                }

                                container result {
                                    description "Enter the result context";

                                    leaf address-mismatch {
                                        type yang:counter64;
                                        description "Replies sent with result address mismatch";
                                    }

                                    leaf ambiguous {
                                        type yang:counter64;
                                        description "Replies sent with result ambiguous";
                                    }

                                    leaf cannot-provide-external {
                                        type yang:counter64;
                                        description "Replies sent with result cannot-provide-external";
                                    }

                                    leaf malformed-option {
                                        type yang:counter64;
                                        description "Replies sent with result malformed-option";
                                    }

                                    leaf malformed-request {
                                        type yang:counter64;
                                        description "Replies sent with result malformed-request";
                                    }

                                    leaf network-failure {
                                        type yang:counter64;
                                        description "Replies sent with result network-failure";
                                    }

                                    leaf no-more-mappings {
                                        type yang:counter64;
                                        description "Replies sent with result no-more-mappings";
                                    }

                                    leaf no-resources {
                                        type yang:counter64;
                                        description "Replies sent with result no-resources";
                                    }

                                    leaf not-authorized {
                                        type yang:counter64;
                                        description "Replies sent with result not-authorized";
                                    }

                                    leaf success {
                                        type yang:counter64;
                                        description "Replies sent with result success";
                                    }

                                    leaf unsupported-opcode {
                                        type yang:counter64;
                                        description "Replies sent with result unsupported-opcode";
                                    }

                                    leaf unsupported-option {
                                        type yang:counter64;
                                        description "Replies sent with result unsupported-option";
                                    }

                                    leaf unsupported-protocol {
                                        type yang:counter64;
                                        description "Replies sent with result unsupported-protocol";
                                    }

                                    leaf unsupported-version {
                                        type yang:counter64;
                                        description "Replies sent with result unsupported-version";
                                    }

                                    leaf user-exceeded-quota {
                                        type yang:counter64;
                                        description "Replies sent with result user-exceeded-quota";
                                    }

                                } // container result

                            } // container transmitted

                            container dropped {
                                description "Enter the dropped context";

                                leaf tx-error {
                                    type yang:counter64;
                                    description "Replies that could not be sent due to transmission errors";
                                }

                            } // container dropped

                        } // container statistics

                    } // list interface

                } // list server

            } // container pcp

            container tunnel-table {
                description "Enter the tunnel-table context";

                container ipv4 {
                    description "Enter the ipv4 context";

                    container statistics {
                        description "Enter the statistics context";

                        container bgp {
                            description "Enter the bgp context";

                            leaf tunnel-count {
                                type yang:counter32;
                                description "Indicates the current number of BGP tunnels.";
                            }

                        } // container bgp

                        container fpe {
                            description "Enter the fpe context";

                            leaf tunnel-count {
                                type yang:counter32;
                                description "Indicates the current number of FPE tunnels.";
                            }

                        } // container fpe

                        container isis {
                            description "Enter the isis context";

                            leaf tunnel-count {
                                type yang:counter32;
                                description "Indicates the current number of ISIS tunnels.";
                            }

                        } // container isis

                        container ldp {
                            description "Enter the ldp context";

                            leaf tunnel-count {
                                type yang:counter32;
                                description "Indicates the current number of LDP tunnels.";
                            }

                        } // container ldp

                        container mpls-fwd-policy {
                            description "Enter the mpls-fwd-policy context";

                            leaf tunnel-count {
                                type yang:counter32;
                                description "Indicates the current number of MPLS Forwarding Policy tunnels.";
                            }

                        } // container mpls-fwd-policy

                        container ospf {
                            description "Enter the ospf context";

                            leaf tunnel-count {
                                type yang:counter32;
                                description "Indicates the current number of OSPF tunnels.";
                            }

                        } // container ospf

                        container ospfv3 {
                            description "Enter the ospfv3 context";

                            leaf tunnel-count {
                                type yang:counter32;
                                description "Indicates the current number of OSPFv3 tunnels.";
                            }

                        } // container ospfv3

                        container rib-api {
                            description "Enter the rib-api context";

                            leaf tunnel-count {
                                type yang:counter32;
                                description "Indicates the current number of RIB-API tunnels.";
                            }

                        } // container rib-api

                        container rsvp {
                            description "Enter the rsvp context";

                            leaf tunnel-count {
                                type yang:counter32;
                                description "Indicates the current number of RSVP tunnels.";
                            }

                        } // container rsvp

                        container sdp {
                            description "Enter the sdp context";

                            leaf tunnel-count {
                                type yang:counter32;
                                description "Indicates the current number of SDP tunnels.";
                            }

                        } // container sdp

                        container sr-policy {
                            description "Enter the sr-policy context";

                            leaf tunnel-count {
                                type yang:counter32;
                                description "Indicates the current number of SR Policy tunnels.";
                            }

                        } // container sr-policy

                        container sr-te {
                            description "Enter the sr-te context";

                            leaf tunnel-count {
                                type yang:counter32;
                                description "Indicates the current number of SR-TE tunnels.";
                            }

                        } // container sr-te

                        container udp {
                            description "Enter the udp context";

                            leaf tunnel-count {
                                type yang:counter32;
                                description "Indicates the current number of UDP tunnels.";
                            }

                        } // container udp

                    } // container statistics

                    list tunnel {
                        key "ipv4-prefix list-index nexthop-index";
                        description "Enter the tunnel list instance";

                        leaf ipv4-prefix {
                            type types-sros:ipv4-prefix;
                            description "The value of this object specifies the IPv4 prefix.";
                        }

                        leaf list-index {
                            type uint32;
                            description "Index of tunnel to destination.";
                        }

                        leaf nexthop-index {
                            type uint32;
                            description "Index of ECMP next-hop or backup next-hop.";
                        }

                        leaf preference {
                            type uint8;
                            description
                                "Indicates the priority of this tunnel versus the other tunnels
                                 from different sources such as LDP, RSVP, GRE etc.

                                 Lowest value signifies the most preferred entry in the table.";
                        }

                        leaf protocol {
                            type types-router:tunnel-type;
                            description "Indicates the type of this tunnel entity.";
                        }

                        leaf instance {
                            type uint32;
                            description "Indicates an instance of the tunnel of the type indicated by protocol.";
                        }

                        leaf id {
                            type types-sros:tunnel-id;
                            description "Indicates a global value and represents a particular tunnel type like an MPLS type tunnel or an SDP.";
                        }

                        leaf next-hop {
                            type types-sros:ip-address-with-zone;
                            description "IP address of the next-hop.";
                        }

                        leaf metric {
                            type uint32;
                            description
                                "Indicates the metric of the tunnel.

                                 This is used in addition to the preference for this tunnel.";
                        }

                        leaf age {
                            type uint32;
                            description
                                "Indicates the number of seconds since this tunnel entry was last updated
                                 or otherwise determined to be correct.

                                 No semantics of 'too old' can be implied except through knowledge of owner of the tunnel.";
                        }

                        leaf lsp-bandwidth {
                            type yang:counter64;
                            description
                                "Indicates the reserved bandwidth that is available in the LSP.

                                 When the value of the object is set to zero then it indicates that
                                 there is no reserved bandwidth in this tunnel.";
                        }

                        leaf lsp-weight {
                            type uint32;
                            description "Indicates the load balancing weight applicable to the LSP.";
                        }

                        leaf lsp-id {
                            type uint32;
                            description "Indicates an instance/epoch identifier associated with a RSVP tunnel.";
                        }

                        leaf bypass-label {
                            type int32;
                            description "Indicates the MPLS bypass tunnel label.";
                        }

                        leaf mtu {
                            type uint32;
                            description "Indicates the MTU value for the tunnel.";
                        }

                        leaf next-hop-flags {
                            type types-router:next-hop-type;
                            description "Indicates the properties of the tunnel next hop.";
                        }

                        leaf tunnel-flags {
                            type types-router:tunnel-flags;
                            description "The value of tunnel-flags indicates some properties of the tunnel";
                        }

                        leaf relative-metric {
                            type int32;
                            description
                                "Indicates the metric offset to IGP cost to tunnel destination.

                                 This value is applicable only if 'useRelativeMetric' bit is set in the tunnel-flags.";
                        }

                        leaf label {
                            type int32;
                            description "Indicates the label corresponding to tunnel.";
                        }

                        leaf cbf-classes {
                            type types-sros:cbf-classes;
                            description
                                "Indicates a set of forwarding classes configured for this LSP expressed as a bit map.

                                 If a bit from 0 through 7 is set, then the corresponding forwarding class has been
                                 configured for this LSP. If bit 8 is set, the LSP has been designated as the default forwarding LSP.

                                 If no bits are set, then class-based forwarding is not enabled for this LSP.";
                        }

                        leaf max-label-stack {
                            type int32;
                            description
                                "Indicates the sum of the maximum number of labels that will be used by this tunnel
                                 and all underlying tunnels.";
                        }

                        leaf next-hop-type {
                            type types-router:tunnel-type;
                            description "Indicates the type of this tunnel entity.";
                        }

                        leaf next-hop-instance {
                            type uint32;
                            description "Indicates an instance of the tunnel of the type indicated by type.";
                        }

                        leaf next-hop-id {
                            type types-sros:tunnel-id;
                            description "Indicates a global value and represents a particular tunnel type like an MPLS type tunnel or an SDP.";
                        }

                        leaf weight {
                            type uint32;
                            description "Indicates the weight associated with this tunnel next-hop.";
                        }

                        leaf next-hop-bit-flags {
                            type types-router:next-hop-flags;
                            description "Indicates additional properties of the tunnel next-hop.";
                        }

                        leaf next-hop-group-id {
                            type uint32;
                            description
                                "Group ID of a next-hop group the next hop belongs to. Only one
                                 next hop in the group will be active at any time. The inactive
                                 next hop has the 'is-not-active' flag in the 'next-hop-bit-flags'
                                 leaf. Not all next hops belong to a group and if this value is
                                 not returned, there is no group associated with this next hop.";
                        }

                        leaf color {
                            type uint32;
                            description "The value of 'color' indicates the color associated with the tunnel.";
                        }

                        leaf flex-algo {
                            type uint32;
                            description
                                "Indicates a specific Algorithm in the system.
                                 The value identifies a defined IGP Flexible Algorithm (range 128..255).";
                        }

                    } // list tunnel

                } // container ipv4

                container ipv6 {
                    description "Enter the ipv6 context";

                    container statistics {
                        description "Enter the statistics context";

                        container isis {
                            description "Enter the isis context";

                            leaf tunnel-count {
                                type yang:counter32;
                                description "Indicates the current number of ISIS tunnels.";
                            }

                        } // container isis

                        container ldp {
                            description "Enter the ldp context";

                            leaf tunnel-count {
                                type yang:counter32;
                                description "Indicates the current number of LDP tunnels.";
                            }

                        } // container ldp

                        container mpls-fwd-policy {
                            description "Enter the mpls-fwd-policy context";

                            leaf tunnel-count {
                                type yang:counter32;
                                description "Indicates the current number of MPLS Forwarding Policy tunnels.";
                            }

                        } // container mpls-fwd-policy

                        container ospfv3 {
                            description "Enter the ospfv3 context";

                            leaf tunnel-count {
                                type yang:counter32;
                                description "Indicates the current number of OSPFv3 tunnels.";
                            }

                        } // container ospfv3

                        container rib-api {
                            description "Enter the rib-api context";

                            leaf tunnel-count {
                                type yang:counter32;
                                description "Indicates the current number of RIB-API tunnels.";
                            }

                        } // container rib-api

                        container sdp {
                            description "Enter the sdp context";

                            leaf tunnel-count {
                                type yang:counter32;
                                description "Indicates the current number of SDP tunnels.";
                            }

                        } // container sdp

                        container sr-policy {
                            description "Enter the sr-policy context";

                            leaf tunnel-count {
                                type yang:counter32;
                                description "Indicates the current number of SR Policy tunnels.";
                            }

                        } // container sr-policy

                        container sr-te {
                            description "Enter the sr-te context";

                            leaf tunnel-count {
                                type yang:counter32;
                                description "Indicates the current number of SR-TE tunnels.";
                            }

                        } // container sr-te

                    } // container statistics

                    list tunnel {
                        key "ipv6-prefix list-index nexthop-index";
                        description "Enter the tunnel list instance";

                        leaf ipv6-prefix {
                            type types-sros:ipv6-prefix;
                            description "The value of this object specifies the IPv4 prefix.";
                        }

                        leaf list-index {
                            type uint32;
                            description "Index of tunnel to destination.";
                        }

                        leaf nexthop-index {
                            type uint32;
                            description "Index of ECMP next-hop or backup next-hop.";
                        }

                        leaf preference {
                            type uint8;
                            description
                                "Indicates the priority of this tunnel versus the other tunnels
                                 from different sources such as LDP, RSVP, GRE etc.

                                 Lowest value signifies the most preferred entry in the table.";
                        }

                        leaf protocol {
                            type types-router:tunnel-type;
                            description "Indicates the type of this tunnel entity.";
                        }

                        leaf instance {
                            type uint32;
                            description "Indicates an instance of the tunnel of the type indicated by protocol.";
                        }

                        leaf id {
                            type types-sros:tunnel-id;
                            description "Indicates a global value and represents a particular tunnel type like an MPLS type tunnel or an SDP.";
                        }

                        leaf next-hop {
                            type types-sros:ip-address-with-zone;
                            description "IP address of the next-hop.";
                        }

                        leaf metric {
                            type uint32;
                            description
                                "Indicates the metric of the tunnel.

                                 This is used in addition to the preference for this tunnel.";
                        }

                        leaf age {
                            type uint32;
                            description
                                "Indicates the number of seconds since this tunnel entry was last updated
                                 or otherwise determined to be correct.

                                 No semantics of 'too old' can be implied except through knowledge of owner of the tunnel.";
                        }

                        leaf lsp-bandwidth {
                            type yang:counter64;
                            description
                                "Indicates the reserved bandwidth that is available in the LSP.

                                 When the value of the object is set to zero then it indicates that
                                 there is no reserved bandwidth in this tunnel.";
                        }

                        leaf lsp-weight {
                            type uint32;
                            description "Indicates the load balancing weight applicable to the LSP.";
                        }

                        leaf lsp-id {
                            type uint32;
                            description "Indicates an instance/epoch identifier associated with a RSVP tunnel.";
                        }

                        leaf bypass-label {
                            type int32;
                            description "Indicates the MPLS bypass tunnel label.";
                        }

                        leaf mtu {
                            type uint32;
                            description "Indicates the MTU value for the tunnel.";
                        }

                        leaf next-hop-flags {
                            type types-router:next-hop-type;
                            description "Indicates the properties of the tunnel next hop.";
                        }

                        leaf tunnel-flags {
                            type types-router:tunnel-flags;
                            description "The value of tunnel-flags indicates some properties of the tunnel";
                        }

                        leaf relative-metric {
                            type int32;
                            description
                                "Indicates the metric offset to IGP cost to tunnel destination.

                                 This value is applicable only if 'useRelativeMetric' bit is set in the tunnel-flags.";
                        }

                        leaf label {
                            type int32;
                            description "Indicates the label corresponding to tunnel.";
                        }

                        leaf cbf-classes {
                            type types-sros:cbf-classes;
                            description
                                "Indicates a set of forwarding classes configured for this LSP expressed as a bit map.

                                 If a bit from 0 through 7 is set, then the corresponding forwarding class has been
                                 configured for this LSP. If bit 8 is set, the LSP has been designated as the default forwarding LSP.

                                 If no bits are set, then class-based forwarding is not enabled for this LSP.";
                        }

                        leaf max-label-stack {
                            type int32;
                            description
                                "Indicates the sum of the maximum number of labels that will be used by this tunnel
                                 and all underlying tunnels.";
                        }

                        leaf next-hop-type {
                            type types-router:tunnel-type;
                            description "Indicates the type of this tunnel entity.";
                        }

                        leaf next-hop-instance {
                            type uint32;
                            description "Indicates an instance of the tunnel of the type indicated by type.";
                        }

                        leaf next-hop-id {
                            type types-sros:tunnel-id;
                            description "Indicates a global value and represents a particular tunnel type like an MPLS type tunnel or an SDP.";
                        }

                        leaf weight {
                            type uint32;
                            description "Indicates the weight associated with this tunnel next-hop.";
                        }

                        leaf next-hop-bit-flags {
                            type types-router:next-hop-flags;
                            description "Indicates additional properties of the tunnel next-hop.";
                        }

                        leaf next-hop-group-id {
                            type uint32;
                            description
                                "Group ID of a next-hop group the next hop belongs to. Only one
                                 next hop in the group will be active at any time. The inactive
                                 next hop has the 'is-not-active' flag in the 'next-hop-bit-flags'
                                 leaf. Not all next hops belong to a group and if this value is
                                 not returned, there is no group associated with this next hop.";
                        }

                        leaf color {
                            type uint32;
                            description "The value of 'color' indicates the color associated with the tunnel.";
                        }

                        leaf flex-algo {
                            type uint32;
                            description
                                "Indicates a specific Algorithm in the system.
                                 The value identifies a defined IGP Flexible Algorithm (range 128..255).";
                        }

                    } // list tunnel

                } // container ipv6

            } // container tunnel-table

            container route-table {
                description "Enter the route-table context";

                container unicast {
                    description "Enter the unicast context";

                    container ipv4 {
                        description "Enter the ipv4 context";

                        container statistics {
                            description "Enter the statistics context";

                            container aggregate {
                                description "Enter the aggregate context";

                                leaf active-routes {
                                    type uint32;
                                    description "Count of routes of a routing protocol active in the FIB.";
                                }

                                leaf available-routes {
                                    type uint32;
                                    description
                                        "Count of routes of a routing protocol, both active in the FIB
                                         and inactive in the RIB.";
                                }

                            } // container aggregate

                            container arp-nd {
                                description "Enter the arp-nd context";

                                leaf active-routes {
                                    type uint32;
                                    description "Count of routes of a routing protocol active in the FIB.";
                                }

                                leaf available-routes {
                                    type uint32;
                                    description
                                        "Count of routes of a routing protocol, both active in the FIB
                                         and inactive in the RIB.";
                                }

                            } // container arp-nd

                            container bgp {
                                description "Enter the bgp context";

                                leaf active-routes {
                                    type uint32;
                                    description "Count of routes of a routing protocol active in the FIB.";
                                }

                                leaf available-routes {
                                    type uint32;
                                    description
                                        "Count of routes of a routing protocol, both active in the FIB
                                         and inactive in the RIB.";
                                }

                            } // container bgp

                            container bgp-backup {
                                description "Enter the bgp-backup context";

                                leaf active-routes {
                                    type uint32;
                                    description "Count of routes of a routing protocol active in the FIB.";
                                }

                                leaf available-routes {
                                    type uint32;
                                    description
                                        "Count of routes of a routing protocol, both active in the FIB
                                         and inactive in the RIB.";
                                }

                            } // container bgp-backup

                            container bgp-label {
                                description "Enter the bgp-label context";

                                leaf active-routes {
                                    type uint32;
                                    description "Count of routes of a routing protocol active in the FIB.";
                                }

                                leaf available-routes {
                                    type uint32;
                                    description
                                        "Count of routes of a routing protocol, both active in the FIB
                                         and inactive in the RIB.";
                                }

                            } // container bgp-label

                            container direct {
                                description "Enter the direct context";

                                leaf active-routes {
                                    type uint32;
                                    description "Count of routes of a routing protocol active in the FIB.";
                                }

                                leaf available-routes {
                                    type uint32;
                                    description
                                        "Count of routes of a routing protocol, both active in the FIB
                                         and inactive in the RIB.";
                                }

                            } // container direct

                            container host {
                                description "Enter the host context";

                                leaf active-routes {
                                    type uint32;
                                    description "Count of routes of a routing protocol active in the FIB.";
                                }

                                leaf available-routes {
                                    type uint32;
                                    description
                                        "Count of routes of a routing protocol, both active in the FIB
                                         and inactive in the RIB.";
                                }

                            } // container host

                            container isis {
                                description "Enter the isis context";

                                leaf active-routes {
                                    type uint32;
                                    description "Count of routes of a routing protocol active in the FIB.";
                                }

                                leaf available-routes {
                                    type uint32;
                                    description
                                        "Count of routes of a routing protocol, both active in the FIB
                                         and inactive in the RIB.";
                                }

                            } // container isis

                            container isis-lfa {
                                description "Enter the isis-lfa context";

                                leaf active-routes {
                                    type uint32;
                                    description "Count of routes of a routing protocol active in the FIB.";
                                }

                                leaf available-routes {
                                    type uint32;
                                    description
                                        "Count of routes of a routing protocol, both active in the FIB
                                         and inactive in the RIB.";
                                }

                            } // container isis-lfa

                            container ldp {
                                description "Enter the ldp context";

                                leaf active-routes {
                                    type uint32;
                                    description "Count of routes of a routing protocol active in the FIB.";
                                }

                                leaf available-routes {
                                    type uint32;
                                    description
                                        "Count of routes of a routing protocol, both active in the FIB
                                         and inactive in the RIB.";
                                }

                            } // container ldp

                            container managed {
                                description "Enter the managed context";

                                leaf active-routes {
                                    type uint32;
                                    description "Count of routes of a routing protocol active in the FIB.";
                                }

                                leaf available-routes {
                                    type uint32;
                                    description
                                        "Count of routes of a routing protocol, both active in the FIB
                                         and inactive in the RIB.";
                                }

                            } // container managed

                            container nat {
                                description "Enter the nat context";

                                leaf active-routes {
                                    type uint32;
                                    description "Count of routes of a routing protocol active in the FIB.";
                                }

                                leaf available-routes {
                                    type uint32;
                                    description
                                        "Count of routes of a routing protocol, both active in the FIB
                                         and inactive in the RIB.";
                                }

                            } // container nat

                            container ospf {
                                description "Enter the ospf context";

                                leaf active-routes {
                                    type uint32;
                                    description "Count of routes of a routing protocol active in the FIB.";
                                }

                                leaf available-routes {
                                    type uint32;
                                    description
                                        "Count of routes of a routing protocol, both active in the FIB
                                         and inactive in the RIB.";
                                }

                            } // container ospf

                            container ospf-lfa {
                                description "Enter the ospf-lfa context";

                                leaf active-routes {
                                    type uint32;
                                    description "Count of routes of a routing protocol active in the FIB.";
                                }

                                leaf available-routes {
                                    type uint32;
                                    description
                                        "Count of routes of a routing protocol, both active in the FIB
                                         and inactive in the RIB.";
                                }

                            } // container ospf-lfa

                            container ospfv3 {
                                description "Enter the ospfv3 context";

                                leaf active-routes {
                                    type uint32;
                                    description "Count of routes of a routing protocol active in the FIB.";
                                }

                                leaf available-routes {
                                    type uint32;
                                    description
                                        "Count of routes of a routing protocol, both active in the FIB
                                         and inactive in the RIB.";
                                }

                            } // container ospfv3

                            container ospfv3-lfa {
                                description "Enter the ospfv3-lfa context";

                                leaf active-routes {
                                    type uint32;
                                    description "Count of routes of a routing protocol active in the FIB.";
                                }

                                leaf available-routes {
                                    type uint32;
                                    description
                                        "Count of routes of a routing protocol, both active in the FIB
                                         and inactive in the RIB.";
                                }

                            } // container ospfv3-lfa

                            container periodic {
                                description "Enter the periodic context";

                                leaf active-routes {
                                    type uint32;
                                    description "Count of routes of a routing protocol active in the FIB.";
                                }

                                leaf available-routes {
                                    type uint32;
                                    description
                                        "Count of routes of a routing protocol, both active in the FIB
                                         and inactive in the RIB.";
                                }

                            } // container periodic

                            container rib-api {
                                description "Enter the rib-api context";

                                leaf active-routes {
                                    type uint32;
                                    description "Count of routes of a routing protocol active in the FIB.";
                                }

                                leaf available-routes {
                                    type uint32;
                                    description
                                        "Count of routes of a routing protocol, both active in the FIB
                                         and inactive in the RIB.";
                                }

                            } // container rib-api

                            container rip {
                                description "Enter the rip context";

                                leaf active-routes {
                                    type uint32;
                                    description "Count of routes of a routing protocol active in the FIB.";
                                }

                                leaf available-routes {
                                    type uint32;
                                    description
                                        "Count of routes of a routing protocol, both active in the FIB
                                         and inactive in the RIB.";
                                }

                            } // container rip

                            container static {
                                description "Enter the static context";

                                leaf active-routes {
                                    type uint32;
                                    description "Count of routes of a routing protocol active in the FIB.";
                                }

                                leaf available-routes {
                                    type uint32;
                                    description
                                        "Count of routes of a routing protocol, both active in the FIB
                                         and inactive in the RIB.";
                                }

                            } // container static

                            container sub-mgmt {
                                description "Enter the sub-mgmt context";

                                leaf active-routes {
                                    type uint32;
                                    description "Count of routes of a routing protocol active in the FIB.";
                                }

                                leaf available-routes {
                                    type uint32;
                                    description
                                        "Count of routes of a routing protocol, both active in the FIB
                                         and inactive in the RIB.";
                                }

                            } // container sub-mgmt

                            container vpn-leak {
                                description "Enter the vpn-leak context";

                                leaf active-routes {
                                    type uint32;
                                    description "Count of routes of a routing protocol active in the FIB.";
                                }

                                leaf available-routes {
                                    type uint32;
                                    description
                                        "Count of routes of a routing protocol, both active in the FIB
                                         and inactive in the RIB.";
                                }

                            } // container vpn-leak

                        } // container statistics

                        list route {
                            key "ipv4-prefix";
                            description "Enter the route list instance";

                            leaf ipv4-prefix {
                                type types-sros:ipv4-prefix;
                                description "Indicates the IPv4 prefix for this route table entry.";
                            }

                            leaf age {
                                type uint32 {
                                    range "0..4294967295";
                                }
                                description "The number of seconds since this route was last updated.";
                            }

                            leaf instance {
                                type uint8;
                                description "The protocol instance the route belongs to.";
                            }

                            leaf flags {
                                type bits {
                                    bit sticky-flag                    { position 0; }
                                }
                                description
                                    "Bit flags that indicate different properties of this route.

                                     If the 'stickyFlag' bit is set, it indicates the ECMP
                                     sticky flag is set on this route.";
                            }

                            leaf preference {
                                type uint8;
                                description
                                    "Indicates the priority of this route versus the routes
                                     from different sources such as BGP or OSPF etc.";
                            }

                            leaf protocol {
                                type types-router:protocol-type;
                                description "Identifies the routing protocol.";
                            }

                            list nexthop {
                                key "nexthop-index";
                                description "Enter the nexthop list instance";

                                leaf nexthop-index {
                                    type uint32;
                                    description "Index of ECMP next-hop or backup next-hop.";
                                }

                                leaf flags {
                                    type bits {
                                        bit nh-is-indirect                 { position 0; }
                                        bit nh-is-tunneled                 { position 1; }
                                        bit nh-is-lfa                      { position 2; }
                                        bit nh-is-backup                   { position 3; }
                                        bit nh-is-unnumbered               { position 4; }
                                    }
                                    description
                                        "Bit flags that indicate different properties of this next-hop.

                                         If the 'nh-is-indirect' bit is set, it indicates the next-hop is
                                         an indirect next-hop IP. An additional lookup will have to be
                                         made to map the indirect IP address to the resolving IP
                                         address(es) The 'if-index' leaf will be 0 in this case.

                                         If the 'nh-is-tunneled' bit is set, it indicates the next-hop is
                                         a tunnel destination (the 'nexthop-ip' leaf is a far-end tunnel
                                         destination). The 'if-index' leaf will be 0 in this case.

                                         If the 'nh-is-lfa' bit is set, it indicates the next-hop is a
                                         loop-free alternate (LFA) of the next-hop immediately preceding
                                         this next-hop.

                                         If the 'nh-is-backup' bit is set, it indicates the next-hop is
                                         a BGP backup next-hop.

                                         If the 'nh-is-unnumbered' bit is set, it indicates the next-hop is
                                         unnumbered.";
                                }

                                leaf if-index {
                                    type uint32;
                                    description
                                        "This is the index of the egress interface where the
                                         next-hop resides.";
                                }

                                leaf if-vrtr-id {
                                    type uint32;
                                    description
                                        "Indicates the virtual router instance of the egress interface
                                         defined by 'if-index'.";
                                }

                                leaf metric {
                                    type uint32;
                                    description "Indicates the routing metric for the next-hop.";
                                }

                                leaf nexthop-ip {
                                    type types-sros:ip-address;
                                    description
                                        "Indicates the next-hop IP address of the route entry.

                                         The nexthop-ip is a tunnel far-end IP if the 'flags' leaf
                                         has the 'nh-is-tunneled' bit set.

                                         The nexthop-ip is an indirect IP if the 'flags' leaf has
                                         the 'nh-is-indirect' bit set.";
                                }

                                leaf nexthop-tunnel-id {
                                    type uint32;
                                    description
                                        "This indicates the next-hop tunnel ID when there are
                                         multiple tunnels to a destination or SDP ID.";
                                }

                                leaf nexthop-tunnel-type {
                                    type types-router:tunnel-type;
                                    description
                                        "This indicates the next-hop tunnel type if the
                                         'flags' leaf has the 'nh-is-tunneled' bit set.";
                                }

                                leaf nexthop-tunnel-type-instance {
                                    type uint8;
                                    description
                                        "This indicates the next-hop tunnel type instance if
                                         the 'flags' leaf has the 'nh-is-tunneled' bit set.";
                                }

                                leaf nexthop-label {
                                    type uint32 {
                                        range "0..1048575";
                                    }
                                    description "This is a VPRN or route label associated with the route entry.";
                                }

                                leaf forwarding-class {
                                    type types-sros:fc-name;
                                    description "This is the forwarding class associated with the next-hop.";
                                }

                                leaf priority {
                                    type types-router:nexthop-priority;
                                    description "This is the priority associated with packets to the next-hop.";
                                }

                                leaf source-class-index {
                                    type uint8 {
                                        range "1..255";
                                    }
                                    description "This is the source class index associated with the next-hop.";
                                }

                                leaf dest-class-index {
                                    type uint8 {
                                        range "1..255";
                                    }
                                    description "This is the destination class index associated with the next-hop.";
                                }

                                leaf weight {
                                    type types-router:ip-ecmp;
                                    description
                                        "The value of this leaf indicates the weight given to traffic using this
                                         particular next-hop among the ECMP set of next-hops.";
                                }

                                list resolving-nexthop {
                                    key "resolving-nexthop-index";
                                    description "Enter the resolving-nexthop list instance";

                                    leaf resolving-nexthop-index {
                                        type uint32;
                                        description "Index of ECMP resolving next-hop or LFA next-hop.";
                                    }

                                    leaf flags {
                                        type bits {
                                            bit nh-is-indirect                 { position 0; }
                                            bit nh-is-tunneled                 { position 1; }
                                            bit nh-is-lfa                      { position 2; }
                                            bit nh-is-backup                   { position 3; }
                                            bit nh-is-unnumbered               { position 4; }
                                        }
                                        description
                                            "Bit flags that indicate different properties of this next-hop.

                                             If the 'nh-is-indirect' bit is set, it indicates the next-hop is
                                             an indirect next-hop IP. An additional lookup will have to be
                                             made to map the indirect IP address to the resolving IP
                                             address(es) The 'if-index' leaf will be 0 in this case.

                                             If the 'nh-is-tunneled' bit is set, it indicates the next-hop is
                                             a tunnel destination (the 'nexthop-ip' leaf is a far-end tunnel
                                             destination). The 'if-index' leaf will be 0 in this case.

                                             If the 'nh-is-lfa' bit is set, it indicates the next-hop is a
                                             loop-free alternate (LFA) of the next-hop immediately preceding
                                             this next-hop.

                                             If the 'nh-is-backup' bit is set, it indicates the next-hop is
                                             a BGP backup next-hop.

                                             If the 'nh-is-unnumbered' bit is set, it indicates the next-hop is
                                             unnumbered.";
                                    }

                                    leaf if-index {
                                        type uint32;
                                        description
                                            "This is the index of the egress interface where the
                                             next-hop resides.";
                                    }

                                    leaf if-vrtr-id {
                                        type uint32;
                                        description
                                            "Indicates the virtual router instance of the egress interface
                                             defined by 'if-index'.";
                                    }

                                    leaf metric {
                                        type uint32;
                                        description "Indicates the routing metric for the next-hop.";
                                    }

                                    leaf nexthop-ip {
                                        type types-sros:ip-address;
                                        description
                                            "Indicates the next-hop IP address of the route entry.

                                             The nexthop-ip is a tunnel far-end IP if the 'flags' leaf
                                             has the 'nh-is-tunneled' bit set.

                                             The nexthop-ip is an indirect IP if the 'flags' leaf has
                                             the 'nh-is-indirect' bit set.";
                                    }

                                    leaf nexthop-tunnel-id {
                                        type uint32;
                                        description
                                            "This indicates the next-hop tunnel ID when there are
                                             multiple tunnels to a destination or SDP ID.";
                                    }

                                    leaf nexthop-tunnel-type {
                                        type types-router:tunnel-type;
                                        description
                                            "This indicates the next-hop tunnel type if the
                                             'flags' leaf has the 'nh-is-tunneled' bit set.";
                                    }

                                    leaf nexthop-tunnel-type-instance {
                                        type uint8;
                                        description
                                            "This indicates the next-hop tunnel type instance if
                                             the 'flags' leaf has the 'nh-is-tunneled' bit set.";
                                    }

                                    leaf nexthop-label {
                                        type uint32 {
                                            range "0..1048575";
                                        }
                                        description "This is a VPRN or route label associated with the route entry.";
                                    }

                                    leaf forwarding-class {
                                        type types-sros:fc-name;
                                        description "This is the forwarding class associated with the next-hop.";
                                    }

                                    leaf priority {
                                        type types-router:nexthop-priority;
                                        description "This is the priority associated with packets to the next-hop.";
                                    }

                                    leaf source-class-index {
                                        type uint8 {
                                            range "1..255";
                                        }
                                        description "This is the source class index associated with the next-hop.";
                                    }

                                    leaf dest-class-index {
                                        type uint8 {
                                            range "1..255";
                                        }
                                        description "This is the destination class index associated with the next-hop.";
                                    }

                                    leaf weight {
                                        type types-router:ip-ecmp;
                                        description
                                            "The value of this leaf indicates the weight given to traffic using this
                                             particular next-hop among the ECMP set of next-hops.";
                                    }

                                } // list resolving-nexthop

                            } // list nexthop

                        } // list route

                    } // container ipv4

                    container ipv6 {
                        description "Enter the ipv6 context";

                        container statistics {
                            description "Enter the statistics context";

                            container aggregate {
                                description "Enter the aggregate context";

                                leaf active-routes {
                                    type uint32;
                                    description "Count of routes of a routing protocol active in the FIB.";
                                }

                                leaf available-routes {
                                    type uint32;
                                    description
                                        "Count of routes of a routing protocol, both active in the FIB
                                         and inactive in the RIB.";
                                }

                            } // container aggregate

                            container arp-nd {
                                description "Enter the arp-nd context";

                                leaf active-routes {
                                    type uint32;
                                    description "Count of routes of a routing protocol active in the FIB.";
                                }

                                leaf available-routes {
                                    type uint32;
                                    description
                                        "Count of routes of a routing protocol, both active in the FIB
                                         and inactive in the RIB.";
                                }

                            } // container arp-nd

                            container bgp {
                                description "Enter the bgp context";

                                leaf active-routes {
                                    type uint32;
                                    description "Count of routes of a routing protocol active in the FIB.";
                                }

                                leaf available-routes {
                                    type uint32;
                                    description
                                        "Count of routes of a routing protocol, both active in the FIB
                                         and inactive in the RIB.";
                                }

                            } // container bgp

                            container bgp-backup {
                                description "Enter the bgp-backup context";

                                leaf active-routes {
                                    type uint32;
                                    description "Count of routes of a routing protocol active in the FIB.";
                                }

                                leaf available-routes {
                                    type uint32;
                                    description
                                        "Count of routes of a routing protocol, both active in the FIB
                                         and inactive in the RIB.";
                                }

                            } // container bgp-backup

                            container bgp-label {
                                description "Enter the bgp-label context";

                                leaf active-routes {
                                    type uint32;
                                    description "Count of routes of a routing protocol active in the FIB.";
                                }

                                leaf available-routes {
                                    type uint32;
                                    description
                                        "Count of routes of a routing protocol, both active in the FIB
                                         and inactive in the RIB.";
                                }

                            } // container bgp-label

                            container dhcpv6-bh {
                                description "Enter the dhcpv6-bh context";

                                leaf active-routes {
                                    type uint32;
                                    description "Count of routes of a routing protocol active in the FIB.";
                                }

                                leaf available-routes {
                                    type uint32;
                                    description
                                        "Count of routes of a routing protocol, both active in the FIB
                                         and inactive in the RIB.";
                                }

                            } // container dhcpv6-bh

                            container dhcpv6-na {
                                description "Enter the dhcpv6-na context";

                                leaf active-routes {
                                    type uint32;
                                    description "Count of routes of a routing protocol active in the FIB.";
                                }

                                leaf available-routes {
                                    type uint32;
                                    description
                                        "Count of routes of a routing protocol, both active in the FIB
                                         and inactive in the RIB.";
                                }

                            } // container dhcpv6-na

                            container dhcpv6-pd {
                                description "Enter the dhcpv6-pd context";

                                leaf active-routes {
                                    type uint32;
                                    description "Count of routes of a routing protocol active in the FIB.";
                                }

                                leaf available-routes {
                                    type uint32;
                                    description
                                        "Count of routes of a routing protocol, both active in the FIB
                                         and inactive in the RIB.";
                                }

                            } // container dhcpv6-pd

                            container dhcpv6-ta {
                                description "Enter the dhcpv6-ta context";

                                leaf active-routes {
                                    type uint32;
                                    description "Count of routes of a routing protocol active in the FIB.";
                                }

                                leaf available-routes {
                                    type uint32;
                                    description
                                        "Count of routes of a routing protocol, both active in the FIB
                                         and inactive in the RIB.";
                                }

                            } // container dhcpv6-ta

                            container direct {
                                description "Enter the direct context";

                                leaf active-routes {
                                    type uint32;
                                    description "Count of routes of a routing protocol active in the FIB.";
                                }

                                leaf available-routes {
                                    type uint32;
                                    description
                                        "Count of routes of a routing protocol, both active in the FIB
                                         and inactive in the RIB.";
                                }

                            } // container direct

                            container host {
                                description "Enter the host context";

                                leaf active-routes {
                                    type uint32;
                                    description "Count of routes of a routing protocol active in the FIB.";
                                }

                                leaf available-routes {
                                    type uint32;
                                    description
                                        "Count of routes of a routing protocol, both active in the FIB
                                         and inactive in the RIB.";
                                }

                            } // container host

                            container isis {
                                description "Enter the isis context";

                                leaf active-routes {
                                    type uint32;
                                    description "Count of routes of a routing protocol active in the FIB.";
                                }

                                leaf available-routes {
                                    type uint32;
                                    description
                                        "Count of routes of a routing protocol, both active in the FIB
                                         and inactive in the RIB.";
                                }

                            } // container isis

                            container isis-lfa {
                                description "Enter the isis-lfa context";

                                leaf active-routes {
                                    type uint32;
                                    description "Count of routes of a routing protocol active in the FIB.";
                                }

                                leaf available-routes {
                                    type uint32;
                                    description
                                        "Count of routes of a routing protocol, both active in the FIB
                                         and inactive in the RIB.";
                                }

                            } // container isis-lfa

                            container ldp {
                                description "Enter the ldp context";

                                leaf active-routes {
                                    type uint32;
                                    description "Count of routes of a routing protocol active in the FIB.";
                                }

                                leaf available-routes {
                                    type uint32;
                                    description
                                        "Count of routes of a routing protocol, both active in the FIB
                                         and inactive in the RIB.";
                                }

                            } // container ldp

                            container managed {
                                description "Enter the managed context";

                                leaf active-routes {
                                    type uint32;
                                    description "Count of routes of a routing protocol active in the FIB.";
                                }

                                leaf available-routes {
                                    type uint32;
                                    description
                                        "Count of routes of a routing protocol, both active in the FIB
                                         and inactive in the RIB.";
                                }

                            } // container managed

                            container nat {
                                description "Enter the nat context";

                                leaf active-routes {
                                    type uint32;
                                    description "Count of routes of a routing protocol active in the FIB.";
                                }

                                leaf available-routes {
                                    type uint32;
                                    description
                                        "Count of routes of a routing protocol, both active in the FIB
                                         and inactive in the RIB.";
                                }

                            } // container nat

                            container ospfv3 {
                                description "Enter the ospfv3 context";

                                leaf active-routes {
                                    type uint32;
                                    description "Count of routes of a routing protocol active in the FIB.";
                                }

                                leaf available-routes {
                                    type uint32;
                                    description
                                        "Count of routes of a routing protocol, both active in the FIB
                                         and inactive in the RIB.";
                                }

                            } // container ospfv3

                            container ospfv3-lfa {
                                description "Enter the ospfv3-lfa context";

                                leaf active-routes {
                                    type uint32;
                                    description "Count of routes of a routing protocol active in the FIB.";
                                }

                                leaf available-routes {
                                    type uint32;
                                    description
                                        "Count of routes of a routing protocol, both active in the FIB
                                         and inactive in the RIB.";
                                }

                            } // container ospfv3-lfa

                            container periodic {
                                description "Enter the periodic context";

                                leaf active-routes {
                                    type uint32;
                                    description "Count of routes of a routing protocol active in the FIB.";
                                }

                                leaf available-routes {
                                    type uint32;
                                    description
                                        "Count of routes of a routing protocol, both active in the FIB
                                         and inactive in the RIB.";
                                }

                            } // container periodic

                            container rib-api {
                                description "Enter the rib-api context";

                                leaf active-routes {
                                    type uint32;
                                    description "Count of routes of a routing protocol active in the FIB.";
                                }

                                leaf available-routes {
                                    type uint32;
                                    description
                                        "Count of routes of a routing protocol, both active in the FIB
                                         and inactive in the RIB.";
                                }

                            } // container rib-api

                            container rip {
                                description "Enter the rip context";

                                leaf active-routes {
                                    type uint32;
                                    description "Count of routes of a routing protocol active in the FIB.";
                                }

                                leaf available-routes {
                                    type uint32;
                                    description
                                        "Count of routes of a routing protocol, both active in the FIB
                                         and inactive in the RIB.";
                                }

                            } // container rip

                            container static {
                                description "Enter the static context";

                                leaf active-routes {
                                    type uint32;
                                    description "Count of routes of a routing protocol active in the FIB.";
                                }

                                leaf available-routes {
                                    type uint32;
                                    description
                                        "Count of routes of a routing protocol, both active in the FIB
                                         and inactive in the RIB.";
                                }

                            } // container static

                            container sub-mgmt {
                                description "Enter the sub-mgmt context";

                                leaf active-routes {
                                    type uint32;
                                    description "Count of routes of a routing protocol active in the FIB.";
                                }

                                leaf available-routes {
                                    type uint32;
                                    description
                                        "Count of routes of a routing protocol, both active in the FIB
                                         and inactive in the RIB.";
                                }

                            } // container sub-mgmt

                            container vpn-leak {
                                description "Enter the vpn-leak context";

                                leaf active-routes {
                                    type uint32;
                                    description "Count of routes of a routing protocol active in the FIB.";
                                }

                                leaf available-routes {
                                    type uint32;
                                    description
                                        "Count of routes of a routing protocol, both active in the FIB
                                         and inactive in the RIB.";
                                }

                            } // container vpn-leak

                        } // container statistics

                        list route {
                            key "ipv6-prefix";
                            description "Enter the route list instance";

                            leaf ipv6-prefix {
                                type types-sros:ipv6-prefix;
                                description "Indicates the IPv6 prefix for this route table entry.";
                            }

                            leaf age {
                                type uint32 {
                                    range "0..4294967295";
                                }
                                description "The number of seconds since this route was last updated.";
                            }

                            leaf instance {
                                type uint8;
                                description "The protocol instance the route belongs to.";
                            }

                            leaf flags {
                                type bits {
                                    bit sticky-flag                    { position 0; }
                                }
                                description
                                    "Bit flags that indicate different properties of this route.

                                     If the 'stickyFlag' bit is set, it indicates the ECMP
                                     sticky flag is set on this route.";
                            }

                            leaf preference {
                                type uint8;
                                description
                                    "Indicates the priority of this route versus the routes
                                     from different sources such as BGP or OSPF etc.";
                            }

                            leaf protocol {
                                type types-router:protocol-type;
                                description "Identifies the routing protocol.";
                            }

                            list nexthop {
                                key "nexthop-index";
                                description "Enter the nexthop list instance";

                                leaf nexthop-index {
                                    type uint32;
                                    description "Index of ECMP next-hop or backup next-hop.";
                                }

                                leaf flags {
                                    type bits {
                                        bit nh-is-indirect                 { position 0; }
                                        bit nh-is-tunneled                 { position 1; }
                                        bit nh-is-lfa                      { position 2; }
                                        bit nh-is-backup                   { position 3; }
                                        bit nh-is-unnumbered               { position 4; }
                                    }
                                    description
                                        "Bit flags that indicate different properties of this next-hop.

                                         If the 'nh-is-indirect' bit is set, it indicates the next-hop is
                                         an indirect next-hop IP. An additional lookup will have to be
                                         made to map the indirect IP address to the resolving IP
                                         address(es) The 'if-index' leaf will be 0 in this case.

                                         If the 'nh-is-tunneled' bit is set, it indicates the next-hop is
                                         a tunnel destination (the 'nexthop-ip' leaf is a far-end tunnel
                                         destination). The 'if-index' leaf will be 0 in this case.

                                         If the 'nh-is-lfa' bit is set, it indicates the next-hop is a
                                         loop-free alternate (LFA) of the next-hop immediately preceding
                                         this next-hop.

                                         If the 'nh-is-backup' bit is set, it indicates the next-hop is
                                         a BGP backup next-hop.

                                         If the 'nh-is-unnumbered' bit is set, it indicates the next-hop is
                                         unnumbered.";
                                }

                                leaf if-index {
                                    type uint32;
                                    description
                                        "This is the index of the egress interface where the
                                         next-hop resides.";
                                }

                                leaf if-vrtr-id {
                                    type uint32;
                                    description
                                        "Indicates the virtual router instance of the egress interface
                                         defined by 'if-index'.";
                                }

                                leaf metric {
                                    type uint32;
                                    description "Indicates the routing metric for the next-hop.";
                                }

                                leaf nexthop-ip {
                                    type types-sros:ip-address;
                                    description
                                        "Indicates the next-hop IP address of the route entry.

                                         The nexthop-ip is a tunnel far-end IP if the 'flags' leaf
                                         has the 'nh-is-tunneled' bit set.

                                         The nexthop-ip is an indirect IP if the 'flags' leaf has
                                         the 'nh-is-indirect' bit set.";
                                }

                                leaf nexthop-tunnel-id {
                                    type uint32;
                                    description
                                        "This indicates the next-hop tunnel ID when there are
                                         multiple tunnels to a destination or SDP ID.";
                                }

                                leaf nexthop-tunnel-type {
                                    type types-router:tunnel-type;
                                    description
                                        "This indicates the next-hop tunnel type if the
                                         'flags' leaf has the 'nh-is-tunneled' bit set.";
                                }

                                leaf nexthop-tunnel-type-instance {
                                    type uint8;
                                    description
                                        "This indicates the next-hop tunnel type instance if
                                         the 'flags' leaf has the 'nh-is-tunneled' bit set.";
                                }

                                leaf nexthop-label {
                                    type uint32 {
                                        range "0..1048575";
                                    }
                                    description "This is a VPRN or route label associated with the route entry.";
                                }

                                leaf forwarding-class {
                                    type types-sros:fc-name;
                                    description "This is the forwarding class associated with the next-hop.";
                                }

                                leaf priority {
                                    type types-router:nexthop-priority;
                                    description "This is the priority associated with packets to the next-hop.";
                                }

                                leaf source-class-index {
                                    type uint8 {
                                        range "1..255";
                                    }
                                    description "This is the source class index associated with the next-hop.";
                                }

                                leaf dest-class-index {
                                    type uint8 {
                                        range "1..255";
                                    }
                                    description "This is the destination class index associated with the next-hop.";
                                }

                                leaf weight {
                                    type types-router:ip-ecmp;
                                    description
                                        "The value of this leaf indicates the weight given to traffic using this
                                         particular next-hop among the ECMP set of next-hops.";
                                }

                                list resolving-nexthop {
                                    key "resolving-nexthop-index";
                                    description "Enter the resolving-nexthop list instance";

                                    leaf resolving-nexthop-index {
                                        type uint32;
                                        description "Index of ECMP resolving next-hop or LFA next-hop.";
                                    }

                                    leaf flags {
                                        type bits {
                                            bit nh-is-indirect                 { position 0; }
                                            bit nh-is-tunneled                 { position 1; }
                                            bit nh-is-lfa                      { position 2; }
                                            bit nh-is-backup                   { position 3; }
                                            bit nh-is-unnumbered               { position 4; }
                                        }
                                        description
                                            "Bit flags that indicate different properties of this next-hop.

                                             If the 'nh-is-indirect' bit is set, it indicates the next-hop is
                                             an indirect next-hop IP. An additional lookup will have to be
                                             made to map the indirect IP address to the resolving IP
                                             address(es) The 'if-index' leaf will be 0 in this case.

                                             If the 'nh-is-tunneled' bit is set, it indicates the next-hop is
                                             a tunnel destination (the 'nexthop-ip' leaf is a far-end tunnel
                                             destination). The 'if-index' leaf will be 0 in this case.

                                             If the 'nh-is-lfa' bit is set, it indicates the next-hop is a
                                             loop-free alternate (LFA) of the next-hop immediately preceding
                                             this next-hop.

                                             If the 'nh-is-backup' bit is set, it indicates the next-hop is
                                             a BGP backup next-hop.

                                             If the 'nh-is-unnumbered' bit is set, it indicates the next-hop is
                                             unnumbered.";
                                    }

                                    leaf if-index {
                                        type uint32;
                                        description
                                            "This is the index of the egress interface where the
                                             next-hop resides.";
                                    }

                                    leaf if-vrtr-id {
                                        type uint32;
                                        description
                                            "Indicates the virtual router instance of the egress interface
                                             defined by 'if-index'.";
                                    }

                                    leaf metric {
                                        type uint32;
                                        description "Indicates the routing metric for the next-hop.";
                                    }

                                    leaf nexthop-ip {
                                        type types-sros:ip-address;
                                        description
                                            "Indicates the next-hop IP address of the route entry.

                                             The nexthop-ip is a tunnel far-end IP if the 'flags' leaf
                                             has the 'nh-is-tunneled' bit set.

                                             The nexthop-ip is an indirect IP if the 'flags' leaf has
                                             the 'nh-is-indirect' bit set.";
                                    }

                                    leaf nexthop-tunnel-id {
                                        type uint32;
                                        description
                                            "This indicates the next-hop tunnel ID when there are
                                             multiple tunnels to a destination or SDP ID.";
                                    }

                                    leaf nexthop-tunnel-type {
                                        type types-router:tunnel-type;
                                        description
                                            "This indicates the next-hop tunnel type if the
                                             'flags' leaf has the 'nh-is-tunneled' bit set.";
                                    }

                                    leaf nexthop-tunnel-type-instance {
                                        type uint8;
                                        description
                                            "This indicates the next-hop tunnel type instance if
                                             the 'flags' leaf has the 'nh-is-tunneled' bit set.";
                                    }

                                    leaf nexthop-label {
                                        type uint32 {
                                            range "0..1048575";
                                        }
                                        description "This is a VPRN or route label associated with the route entry.";
                                    }

                                    leaf forwarding-class {
                                        type types-sros:fc-name;
                                        description "This is the forwarding class associated with the next-hop.";
                                    }

                                    leaf priority {
                                        type types-router:nexthop-priority;
                                        description "This is the priority associated with packets to the next-hop.";
                                    }

                                    leaf source-class-index {
                                        type uint8 {
                                            range "1..255";
                                        }
                                        description "This is the source class index associated with the next-hop.";
                                    }

                                    leaf dest-class-index {
                                        type uint8 {
                                            range "1..255";
                                        }
                                        description "This is the destination class index associated with the next-hop.";
                                    }

                                    leaf weight {
                                        type types-router:ip-ecmp;
                                        description
                                            "The value of this leaf indicates the weight given to traffic using this
                                             particular next-hop among the ECMP set of next-hops.";
                                    }

                                } // list resolving-nexthop

                            } // list nexthop

                        } // list route

                    } // container ipv6

                } // container unicast

                container multicast {
                    description "Enter the multicast context";

                    container ipv4 {
                        description "Enter the ipv4 context";

                        container statistics {
                            description "Enter the statistics context";

                            container bgp {
                                description "Enter the bgp context";

                                leaf active-routes {
                                    type uint32;
                                    description "Count of routes of a routing protocol active in the FIB.";
                                }

                                leaf available-routes {
                                    type uint32;
                                    description
                                        "Count of routes of a routing protocol, both active in the FIB
                                         and inactive in the RIB.";
                                }

                            } // container bgp

                            container direct {
                                description "Enter the direct context";

                                leaf active-routes {
                                    type uint32;
                                    description "Count of routes of a routing protocol active in the FIB.";
                                }

                                leaf available-routes {
                                    type uint32;
                                    description
                                        "Count of routes of a routing protocol, both active in the FIB
                                         and inactive in the RIB.";
                                }

                            } // container direct

                            container host {
                                description "Enter the host context";

                                leaf active-routes {
                                    type uint32;
                                    description "Count of routes of a routing protocol active in the FIB.";
                                }

                                leaf available-routes {
                                    type uint32;
                                    description
                                        "Count of routes of a routing protocol, both active in the FIB
                                         and inactive in the RIB.";
                                }

                            } // container host

                            container isis {
                                description "Enter the isis context";

                                leaf active-routes {
                                    type uint32;
                                    description "Count of routes of a routing protocol active in the FIB.";
                                }

                                leaf available-routes {
                                    type uint32;
                                    description
                                        "Count of routes of a routing protocol, both active in the FIB
                                         and inactive in the RIB.";
                                }

                            } // container isis

                            container ospf {
                                description "Enter the ospf context";

                                leaf active-routes {
                                    type uint32;
                                    description "Count of routes of a routing protocol active in the FIB.";
                                }

                                leaf available-routes {
                                    type uint32;
                                    description
                                        "Count of routes of a routing protocol, both active in the FIB
                                         and inactive in the RIB.";
                                }

                            } // container ospf

                            container ospfv3 {
                                description "Enter the ospfv3 context";

                                leaf active-routes {
                                    type uint32;
                                    description "Count of routes of a routing protocol active in the FIB.";
                                }

                                leaf available-routes {
                                    type uint32;
                                    description
                                        "Count of routes of a routing protocol, both active in the FIB
                                         and inactive in the RIB.";
                                }

                            } // container ospfv3

                            container static {
                                description "Enter the static context";

                                leaf active-routes {
                                    type uint32;
                                    description "Count of routes of a routing protocol active in the FIB.";
                                }

                                leaf available-routes {
                                    type uint32;
                                    description
                                        "Count of routes of a routing protocol, both active in the FIB
                                         and inactive in the RIB.";
                                }

                            } // container static

                        } // container statistics

                        list route {
                            key "ipv4-prefix";
                            description "Enter the route list instance";

                            leaf ipv4-prefix {
                                type types-sros:ipv4-prefix;
                                description "Indicates the IPv4 prefix for this route table entry.";
                            }

                            leaf age {
                                type uint32 {
                                    range "0..4294967295";
                                }
                                description "The number of seconds since this route was last updated.";
                            }

                            leaf instance {
                                type uint8;
                                description "The protocol instance the route belongs to.";
                            }

                            leaf flags {
                                type bits {
                                    bit sticky-flag                    { position 0; }
                                }
                                description
                                    "Bit flags that indicate different properties of this route.

                                     If the 'stickyFlag' bit is set, it indicates the ECMP
                                     sticky flag is set on this route.";
                            }

                            leaf preference {
                                type uint8;
                                description
                                    "Indicates the priority of this route versus the routes
                                     from different sources such as BGP or OSPF etc.";
                            }

                            leaf protocol {
                                type types-router:protocol-type;
                                description "Identifies the routing protocol.";
                            }

                            list nexthop {
                                key "nexthop-index";
                                description "Enter the nexthop list instance";

                                leaf nexthop-index {
                                    type uint32;
                                    description "Index of ECMP next-hop or backup next-hop.";
                                }

                                leaf flags {
                                    type bits {
                                        bit nh-is-indirect                 { position 0; }
                                        bit nh-is-tunneled                 { position 1; }
                                        bit nh-is-lfa                      { position 2; }
                                        bit nh-is-backup                   { position 3; }
                                        bit nh-is-unnumbered               { position 4; }
                                    }
                                    description
                                        "Bit flags that indicate different properties of this next-hop.

                                         If the 'nh-is-indirect' bit is set, it indicates the next-hop is
                                         an indirect next-hop IP. An additional lookup will have to be
                                         made to map the indirect IP address to the resolving IP
                                         address(es) The 'if-index' leaf will be 0 in this case.

                                         If the 'nh-is-tunneled' bit is set, it indicates the next-hop is
                                         a tunnel destination (the 'nexthop-ip' leaf is a far-end tunnel
                                         destination). The 'if-index' leaf will be 0 in this case.

                                         If the 'nh-is-lfa' bit is set, it indicates the next-hop is a
                                         loop-free alternate (LFA) of the next-hop immediately preceding
                                         this next-hop.

                                         If the 'nh-is-backup' bit is set, it indicates the next-hop is
                                         a BGP backup next-hop.

                                         If the 'nh-is-unnumbered' bit is set, it indicates the next-hop is
                                         unnumbered.";
                                }

                                leaf if-index {
                                    type uint32;
                                    description
                                        "This is the index of the egress interface where the
                                         next-hop resides.";
                                }

                                leaf if-vrtr-id {
                                    type uint32;
                                    description
                                        "Indicates the virtual router instance of the egress interface
                                         defined by 'if-index'.";
                                }

                                leaf metric {
                                    type uint32;
                                    description "Indicates the routing metric for the next-hop.";
                                }

                                leaf nexthop-ip {
                                    type types-sros:ip-address;
                                    description
                                        "Indicates the next-hop IP address of the route entry.

                                         The nexthop-ip is a tunnel far-end IP if the 'flags' leaf
                                         has the 'nh-is-tunneled' bit set.

                                         The nexthop-ip is an indirect IP if the 'flags' leaf has
                                         the 'nh-is-indirect' bit set.";
                                }

                                leaf nexthop-tunnel-id {
                                    type uint32;
                                    description
                                        "This indicates the next-hop tunnel ID when there are
                                         multiple tunnels to a destination or SDP ID.";
                                }

                                leaf nexthop-tunnel-type {
                                    type types-router:tunnel-type;
                                    description
                                        "This indicates the next-hop tunnel type if the
                                         'flags' leaf has the 'nh-is-tunneled' bit set.";
                                }

                                leaf nexthop-tunnel-type-instance {
                                    type uint8;
                                    description
                                        "This indicates the next-hop tunnel type instance if
                                         the 'flags' leaf has the 'nh-is-tunneled' bit set.";
                                }

                                leaf nexthop-label {
                                    type uint32 {
                                        range "0..1048575";
                                    }
                                    description "This is a VPRN or route label associated with the route entry.";
                                }

                                leaf forwarding-class {
                                    type types-sros:fc-name;
                                    description "This is the forwarding class associated with the next-hop.";
                                }

                                leaf priority {
                                    type types-router:nexthop-priority;
                                    description "This is the priority associated with packets to the next-hop.";
                                }

                                leaf source-class-index {
                                    type uint8 {
                                        range "1..255";
                                    }
                                    description "This is the source class index associated with the next-hop.";
                                }

                                leaf dest-class-index {
                                    type uint8 {
                                        range "1..255";
                                    }
                                    description "This is the destination class index associated with the next-hop.";
                                }

                                leaf weight {
                                    type types-router:ip-ecmp;
                                    description
                                        "The value of this leaf indicates the weight given to traffic using this
                                         particular next-hop among the ECMP set of next-hops.";
                                }

                                list resolving-nexthop {
                                    key "resolving-nexthop-index";
                                    description "Enter the resolving-nexthop list instance";

                                    leaf resolving-nexthop-index {
                                        type uint32;
                                        description "Index of ECMP resolving next-hop or LFA next-hop.";
                                    }

                                    leaf flags {
                                        type bits {
                                            bit nh-is-indirect                 { position 0; }
                                            bit nh-is-tunneled                 { position 1; }
                                            bit nh-is-lfa                      { position 2; }
                                            bit nh-is-backup                   { position 3; }
                                            bit nh-is-unnumbered               { position 4; }
                                        }
                                        description
                                            "Bit flags that indicate different properties of this next-hop.

                                             If the 'nh-is-indirect' bit is set, it indicates the next-hop is
                                             an indirect next-hop IP. An additional lookup will have to be
                                             made to map the indirect IP address to the resolving IP
                                             address(es) The 'if-index' leaf will be 0 in this case.

                                             If the 'nh-is-tunneled' bit is set, it indicates the next-hop is
                                             a tunnel destination (the 'nexthop-ip' leaf is a far-end tunnel
                                             destination). The 'if-index' leaf will be 0 in this case.

                                             If the 'nh-is-lfa' bit is set, it indicates the next-hop is a
                                             loop-free alternate (LFA) of the next-hop immediately preceding
                                             this next-hop.

                                             If the 'nh-is-backup' bit is set, it indicates the next-hop is
                                             a BGP backup next-hop.

                                             If the 'nh-is-unnumbered' bit is set, it indicates the next-hop is
                                             unnumbered.";
                                    }

                                    leaf if-index {
                                        type uint32;
                                        description
                                            "This is the index of the egress interface where the
                                             next-hop resides.";
                                    }

                                    leaf if-vrtr-id {
                                        type uint32;
                                        description
                                            "Indicates the virtual router instance of the egress interface
                                             defined by 'if-index'.";
                                    }

                                    leaf metric {
                                        type uint32;
                                        description "Indicates the routing metric for the next-hop.";
                                    }

                                    leaf nexthop-ip {
                                        type types-sros:ip-address;
                                        description
                                            "Indicates the next-hop IP address of the route entry.

                                             The nexthop-ip is a tunnel far-end IP if the 'flags' leaf
                                             has the 'nh-is-tunneled' bit set.

                                             The nexthop-ip is an indirect IP if the 'flags' leaf has
                                             the 'nh-is-indirect' bit set.";
                                    }

                                    leaf nexthop-tunnel-id {
                                        type uint32;
                                        description
                                            "This indicates the next-hop tunnel ID when there are
                                             multiple tunnels to a destination or SDP ID.";
                                    }

                                    leaf nexthop-tunnel-type {
                                        type types-router:tunnel-type;
                                        description
                                            "This indicates the next-hop tunnel type if the
                                             'flags' leaf has the 'nh-is-tunneled' bit set.";
                                    }

                                    leaf nexthop-tunnel-type-instance {
                                        type uint8;
                                        description
                                            "This indicates the next-hop tunnel type instance if
                                             the 'flags' leaf has the 'nh-is-tunneled' bit set.";
                                    }

                                    leaf nexthop-label {
                                        type uint32 {
                                            range "0..1048575";
                                        }
                                        description "This is a VPRN or route label associated with the route entry.";
                                    }

                                    leaf forwarding-class {
                                        type types-sros:fc-name;
                                        description "This is the forwarding class associated with the next-hop.";
                                    }

                                    leaf priority {
                                        type types-router:nexthop-priority;
                                        description "This is the priority associated with packets to the next-hop.";
                                    }

                                    leaf source-class-index {
                                        type uint8 {
                                            range "1..255";
                                        }
                                        description "This is the source class index associated with the next-hop.";
                                    }

                                    leaf dest-class-index {
                                        type uint8 {
                                            range "1..255";
                                        }
                                        description "This is the destination class index associated with the next-hop.";
                                    }

                                    leaf weight {
                                        type types-router:ip-ecmp;
                                        description
                                            "The value of this leaf indicates the weight given to traffic using this
                                             particular next-hop among the ECMP set of next-hops.";
                                    }

                                } // list resolving-nexthop

                            } // list nexthop

                        } // list route

                    } // container ipv4

                    container ipv6 {
                        description "Enter the ipv6 context";

                        container statistics {
                            description "Enter the statistics context";

                            container bgp {
                                description "Enter the bgp context";

                                leaf active-routes {
                                    type uint32;
                                    description "Count of routes of a routing protocol active in the FIB.";
                                }

                                leaf available-routes {
                                    type uint32;
                                    description
                                        "Count of routes of a routing protocol, both active in the FIB
                                         and inactive in the RIB.";
                                }

                            } // container bgp

                            container direct {
                                description "Enter the direct context";

                                leaf active-routes {
                                    type uint32;
                                    description "Count of routes of a routing protocol active in the FIB.";
                                }

                                leaf available-routes {
                                    type uint32;
                                    description
                                        "Count of routes of a routing protocol, both active in the FIB
                                         and inactive in the RIB.";
                                }

                            } // container direct

                            container host {
                                description "Enter the host context";

                                leaf active-routes {
                                    type uint32;
                                    description "Count of routes of a routing protocol active in the FIB.";
                                }

                                leaf available-routes {
                                    type uint32;
                                    description
                                        "Count of routes of a routing protocol, both active in the FIB
                                         and inactive in the RIB.";
                                }

                            } // container host

                            container isis {
                                description "Enter the isis context";

                                leaf active-routes {
                                    type uint32;
                                    description "Count of routes of a routing protocol active in the FIB.";
                                }

                                leaf available-routes {
                                    type uint32;
                                    description
                                        "Count of routes of a routing protocol, both active in the FIB
                                         and inactive in the RIB.";
                                }

                            } // container isis

                            container ospfv3 {
                                description "Enter the ospfv3 context";

                                leaf active-routes {
                                    type uint32;
                                    description "Count of routes of a routing protocol active in the FIB.";
                                }

                                leaf available-routes {
                                    type uint32;
                                    description
                                        "Count of routes of a routing protocol, both active in the FIB
                                         and inactive in the RIB.";
                                }

                            } // container ospfv3

                            container static {
                                description "Enter the static context";

                                leaf active-routes {
                                    type uint32;
                                    description "Count of routes of a routing protocol active in the FIB.";
                                }

                                leaf available-routes {
                                    type uint32;
                                    description
                                        "Count of routes of a routing protocol, both active in the FIB
                                         and inactive in the RIB.";
                                }

                            } // container static

                        } // container statistics

                        list route {
                            key "ipv6-prefix";
                            description "Enter the route list instance";

                            leaf ipv6-prefix {
                                type types-sros:ipv6-prefix;
                                description "Indicates the IPv6 prefix for this route table entry.";
                            }

                            leaf age {
                                type uint32 {
                                    range "0..4294967295";
                                }
                                description "The number of seconds since this route was last updated.";
                            }

                            leaf instance {
                                type uint8;
                                description "The protocol instance the route belongs to.";
                            }

                            leaf flags {
                                type bits {
                                    bit sticky-flag                    { position 0; }
                                }
                                description
                                    "Bit flags that indicate different properties of this route.

                                     If the 'stickyFlag' bit is set, it indicates the ECMP
                                     sticky flag is set on this route.";
                            }

                            leaf preference {
                                type uint8;
                                description
                                    "Indicates the priority of this route versus the routes
                                     from different sources such as BGP or OSPF etc.";
                            }

                            leaf protocol {
                                type types-router:protocol-type;
                                description "Identifies the routing protocol.";
                            }

                            list nexthop {
                                key "nexthop-index";
                                description "Enter the nexthop list instance";

                                leaf nexthop-index {
                                    type uint32;
                                    description "Index of ECMP next-hop or backup next-hop.";
                                }

                                leaf flags {
                                    type bits {
                                        bit nh-is-indirect                 { position 0; }
                                        bit nh-is-tunneled                 { position 1; }
                                        bit nh-is-lfa                      { position 2; }
                                        bit nh-is-backup                   { position 3; }
                                        bit nh-is-unnumbered               { position 4; }
                                    }
                                    description
                                        "Bit flags that indicate different properties of this next-hop.

                                         If the 'nh-is-indirect' bit is set, it indicates the next-hop is
                                         an indirect next-hop IP. An additional lookup will have to be
                                         made to map the indirect IP address to the resolving IP
                                         address(es) The 'if-index' leaf will be 0 in this case.

                                         If the 'nh-is-tunneled' bit is set, it indicates the next-hop is
                                         a tunnel destination (the 'nexthop-ip' leaf is a far-end tunnel
                                         destination). The 'if-index' leaf will be 0 in this case.

                                         If the 'nh-is-lfa' bit is set, it indicates the next-hop is a
                                         loop-free alternate (LFA) of the next-hop immediately preceding
                                         this next-hop.

                                         If the 'nh-is-backup' bit is set, it indicates the next-hop is
                                         a BGP backup next-hop.

                                         If the 'nh-is-unnumbered' bit is set, it indicates the next-hop is
                                         unnumbered.";
                                }

                                leaf if-index {
                                    type uint32;
                                    description
                                        "This is the index of the egress interface where the
                                         next-hop resides.";
                                }

                                leaf if-vrtr-id {
                                    type uint32;
                                    description
                                        "Indicates the virtual router instance of the egress interface
                                         defined by 'if-index'.";
                                }

                                leaf metric {
                                    type uint32;
                                    description "Indicates the routing metric for the next-hop.";
                                }

                                leaf nexthop-ip {
                                    type types-sros:ip-address;
                                    description
                                        "Indicates the next-hop IP address of the route entry.

                                         The nexthop-ip is a tunnel far-end IP if the 'flags' leaf
                                         has the 'nh-is-tunneled' bit set.

                                         The nexthop-ip is an indirect IP if the 'flags' leaf has
                                         the 'nh-is-indirect' bit set.";
                                }

                                leaf nexthop-tunnel-id {
                                    type uint32;
                                    description
                                        "This indicates the next-hop tunnel ID when there are
                                         multiple tunnels to a destination or SDP ID.";
                                }

                                leaf nexthop-tunnel-type {
                                    type types-router:tunnel-type;
                                    description
                                        "This indicates the next-hop tunnel type if the
                                         'flags' leaf has the 'nh-is-tunneled' bit set.";
                                }

                                leaf nexthop-tunnel-type-instance {
                                    type uint8;
                                    description
                                        "This indicates the next-hop tunnel type instance if
                                         the 'flags' leaf has the 'nh-is-tunneled' bit set.";
                                }

                                leaf nexthop-label {
                                    type uint32 {
                                        range "0..1048575";
                                    }
                                    description "This is a VPRN or route label associated with the route entry.";
                                }

                                leaf forwarding-class {
                                    type types-sros:fc-name;
                                    description "This is the forwarding class associated with the next-hop.";
                                }

                                leaf priority {
                                    type types-router:nexthop-priority;
                                    description "This is the priority associated with packets to the next-hop.";
                                }

                                leaf source-class-index {
                                    type uint8 {
                                        range "1..255";
                                    }
                                    description "This is the source class index associated with the next-hop.";
                                }

                                leaf dest-class-index {
                                    type uint8 {
                                        range "1..255";
                                    }
                                    description "This is the destination class index associated with the next-hop.";
                                }

                                leaf weight {
                                    type types-router:ip-ecmp;
                                    description
                                        "The value of this leaf indicates the weight given to traffic using this
                                         particular next-hop among the ECMP set of next-hops.";
                                }

                                list resolving-nexthop {
                                    key "resolving-nexthop-index";
                                    description "Enter the resolving-nexthop list instance";

                                    leaf resolving-nexthop-index {
                                        type uint32;
                                        description "Index of ECMP resolving next-hop or LFA next-hop.";
                                    }

                                    leaf flags {
                                        type bits {
                                            bit nh-is-indirect                 { position 0; }
                                            bit nh-is-tunneled                 { position 1; }
                                            bit nh-is-lfa                      { position 2; }
                                            bit nh-is-backup                   { position 3; }
                                            bit nh-is-unnumbered               { position 4; }
                                        }
                                        description
                                            "Bit flags that indicate different properties of this next-hop.

                                             If the 'nh-is-indirect' bit is set, it indicates the next-hop is
                                             an indirect next-hop IP. An additional lookup will have to be
                                             made to map the indirect IP address to the resolving IP
                                             address(es) The 'if-index' leaf will be 0 in this case.

                                             If the 'nh-is-tunneled' bit is set, it indicates the next-hop is
                                             a tunnel destination (the 'nexthop-ip' leaf is a far-end tunnel
                                             destination). The 'if-index' leaf will be 0 in this case.

                                             If the 'nh-is-lfa' bit is set, it indicates the next-hop is a
                                             loop-free alternate (LFA) of the next-hop immediately preceding
                                             this next-hop.

                                             If the 'nh-is-backup' bit is set, it indicates the next-hop is
                                             a BGP backup next-hop.

                                             If the 'nh-is-unnumbered' bit is set, it indicates the next-hop is
                                             unnumbered.";
                                    }

                                    leaf if-index {
                                        type uint32;
                                        description
                                            "This is the index of the egress interface where the
                                             next-hop resides.";
                                    }

                                    leaf if-vrtr-id {
                                        type uint32;
                                        description
                                            "Indicates the virtual router instance of the egress interface
                                             defined by 'if-index'.";
                                    }

                                    leaf metric {
                                        type uint32;
                                        description "Indicates the routing metric for the next-hop.";
                                    }

                                    leaf nexthop-ip {
                                        type types-sros:ip-address;
                                        description
                                            "Indicates the next-hop IP address of the route entry.

                                             The nexthop-ip is a tunnel far-end IP if the 'flags' leaf
                                             has the 'nh-is-tunneled' bit set.

                                             The nexthop-ip is an indirect IP if the 'flags' leaf has
                                             the 'nh-is-indirect' bit set.";
                                    }

                                    leaf nexthop-tunnel-id {
                                        type uint32;
                                        description
                                            "This indicates the next-hop tunnel ID when there are
                                             multiple tunnels to a destination or SDP ID.";
                                    }

                                    leaf nexthop-tunnel-type {
                                        type types-router:tunnel-type;
                                        description
                                            "This indicates the next-hop tunnel type if the
                                             'flags' leaf has the 'nh-is-tunneled' bit set.";
                                    }

                                    leaf nexthop-tunnel-type-instance {
                                        type uint8;
                                        description
                                            "This indicates the next-hop tunnel type instance if
                                             the 'flags' leaf has the 'nh-is-tunneled' bit set.";
                                    }

                                    leaf nexthop-label {
                                        type uint32 {
                                            range "0..1048575";
                                        }
                                        description "This is a VPRN or route label associated with the route entry.";
                                    }

                                    leaf forwarding-class {
                                        type types-sros:fc-name;
                                        description "This is the forwarding class associated with the next-hop.";
                                    }

                                    leaf priority {
                                        type types-router:nexthop-priority;
                                        description "This is the priority associated with packets to the next-hop.";
                                    }

                                    leaf source-class-index {
                                        type uint8 {
                                            range "1..255";
                                        }
                                        description "This is the source class index associated with the next-hop.";
                                    }

                                    leaf dest-class-index {
                                        type uint8 {
                                            range "1..255";
                                        }
                                        description "This is the destination class index associated with the next-hop.";
                                    }

                                    leaf weight {
                                        type types-router:ip-ecmp;
                                        description
                                            "The value of this leaf indicates the weight given to traffic using this
                                             particular next-hop among the ECMP set of next-hops.";
                                    }

                                } // list resolving-nexthop

                            } // list nexthop

                        } // list route

                    } // container ipv6

                } // container multicast

            } // container route-table

            container network-domains {
                description "Enter the network-domains context";

                list network-domain {
                    key "domain-name";
                    description "Enter the network-domain list instance";

                    leaf domain-name {
                        type types-sros:named-item;
                        description "Specifies the network-domain name.";
                    }

                    leaf associated-interfaces {
                        type yang:gauge32;
                        description "Specifies the number of associated interfaces.";
                    }

                    leaf associated-sdps {
                        type yang:gauge32;
                        description "Specifies the number of associated SDPs.";
                    }

                    leaf associated-multicast-domains {
                        type yang:gauge32;
                        description "Specifies the number of associated multicast network-domains.";
                    }

                } // list network-domain

            } // container network-domains

            container dhcp6 {
                description "Enter the dhcp6 context";

                container statistics {
                    description "Enter the statistics context";

                    list message {
                        key "type";
                        description "Enter the message list instance";

                        leaf type {
                            type enumeration {
                                enum "solicit"                      { value 1; }
                                enum "advertise"                    { value 2; }
                                enum "request"                      { value 3; }
                                enum "confirm"                      { value 4; }
                                enum "renew"                        { value 5; }
                                enum "rebind"                       { value 6; }
                                enum "reply"                        { value 7; }
                                enum "release"                      { value 8; }
                                enum "decline"                      { value 9; }
                                enum "reconfigure"                  { value 10; }
                                enum "info-request"                 { value 11; }
                                enum "relay-forward"                { value 12; }
                                enum "relay-reply"                  { value 13; }
                                enum "lease-query"                  { value 14; }
                                enum "lease-query-reply"            { value 15; }
                            }
                        }

                        leaf received {
                            type yang:counter32;
                            description "Number of packets received";
                        }

                        leaf transmitted {
                            type yang:counter32;
                            description "Number of packets transmitted";
                        }

                        leaf dropped {
                            type yang:counter32;
                            description "Number of packets dropped";
                        }

                        leaf last-cleared {
                            type yang:date-and-time;
                            description "Date and time when this drop reason counter was last reset";
                        }

                    } // list message

                    container dropped {
                        description "Enter the dropped context";

                        container none {
                            description "Enter the none context";

                            leaf counter {
                                type yang:counter32;
                                description "Number of packets dropped";
                            }

                            leaf last-cleared {
                                type yang:date-and-time;
                                description "Date and time when this drop reason counter was last reset";
                            }

                        } // container none

                        container source-operational-down {
                            description "Enter the source-operational-down context";

                            leaf counter {
                                type yang:counter32;
                                description "Number of packets dropped";
                            }

                            leaf last-cleared {
                                type yang:date-and-time;
                                description "Date and time when this drop reason counter was last reset";
                            }

                        } // container source-operational-down

                        container destination-operational-down {
                            description "Enter the destination-operational-down context";

                            leaf counter {
                                type yang:counter32;
                                description "Number of packets dropped";
                            }

                            leaf last-cleared {
                                type yang:date-and-time;
                                description "Date and time when this drop reason counter was last reset";
                            }

                        } // container destination-operational-down

                        container relay-reply-on-client-interface {
                            description "Enter the relay-reply-on-client-interface context";

                            leaf counter {
                                type yang:counter32;
                                description "Number of packets dropped";
                            }

                            leaf last-cleared {
                                type yang:date-and-time;
                                description "Date and time when this drop reason counter was last reset";
                            }

                        } // container relay-reply-on-client-interface

                        container hop-count {
                            description "Enter the hop-count context";

                            leaf counter {
                                type yang:counter32;
                                description "Number of packets dropped";
                            }

                            leaf last-cleared {
                                type yang:date-and-time;
                                description "Date and time when this drop reason counter was last reset";
                            }

                        } // container hop-count

                        container bad-relayed-message {
                            description "Enter the bad-relayed-message context";

                            leaf counter {
                                type yang:counter32;
                                description "Number of packets dropped";
                            }

                            leaf last-cleared {
                                type yang:date-and-time;
                                description "Date and time when this drop reason counter was last reset";
                            }

                        } // container bad-relayed-message

                        container client-interface-not-found {
                            description "Enter the client-interface-not-found context";

                            leaf counter {
                                type yang:counter32;
                                description "Number of packets dropped";
                            }

                            leaf last-cleared {
                                type yang:date-and-time;
                                description "Date and time when this drop reason counter was last reset";
                            }

                        } // container client-interface-not-found

                        container no-memory {
                            description "Enter the no-memory context";

                            leaf counter {
                                type yang:counter32;
                                description "Number of packets dropped";
                            }

                            leaf last-cleared {
                                type yang:date-and-time;
                                description "Date and time when this drop reason counter was last reset";
                            }

                        } // container no-memory

                        container no-global-prefix {
                            description "Enter the no-global-prefix context";

                            leaf counter {
                                type yang:counter32;
                                description "Number of packets dropped";
                            }

                            leaf last-cleared {
                                type yang:date-and-time;
                                description "Date and time when this drop reason counter was last reset";
                            }

                        } // container no-global-prefix

                        container no-source-ip {
                            description "Enter the no-source-ip context";

                            leaf counter {
                                type yang:counter32;
                                description "Number of packets dropped";
                            }

                            leaf last-cleared {
                                type yang:date-and-time;
                                description "Date and time when this drop reason counter was last reset";
                            }

                        } // container no-source-ip

                        container no-route-to-server {
                            description "Enter the no-route-to-server context";

                            leaf counter {
                                type yang:counter32;
                                description "Number of packets dropped";
                            }

                            leaf last-cleared {
                                type yang:date-and-time;
                                description "Date and time when this drop reason counter was last reset";
                            }

                        } // container no-route-to-server

                        container update-failed {
                            description "Enter the update-failed context";

                            leaf counter {
                                type yang:counter32;
                                description "Number of packets dropped";
                            }

                            leaf last-cleared {
                                type yang:date-and-time;
                                description "Date and time when this drop reason counter was last reset";
                            }

                        } // container update-failed

                        container rx-relay-forward-message {
                            description "Enter the rx-relay-forward-message context";

                            leaf counter {
                                type yang:counter32;
                                description "Number of packets dropped";
                            }

                            leaf last-cleared {
                                type yang:date-and-time;
                                description "Date and time when this drop reason counter was last reset";
                            }

                        } // container rx-relay-forward-message

                        container message-too-small {
                            description "Enter the message-too-small context";

                            leaf counter {
                                type yang:counter32;
                                description "Number of packets dropped";
                            }

                            leaf last-cleared {
                                type yang:date-and-time;
                                description "Date and time when this drop reason counter was last reset";
                            }

                        } // container message-too-small

                        container message-not-for-server {
                            description "Enter the message-not-for-server context";

                            leaf counter {
                                type yang:counter32;
                                description "Number of packets dropped";
                            }

                            leaf last-cleared {
                                type yang:date-and-time;
                                description "Date and time when this drop reason counter was last reset";
                            }

                        } // container message-not-for-server

                        container no-server-id {
                            description "Enter the no-server-id context";

                            leaf counter {
                                type yang:counter32;
                                description "Number of packets dropped";
                            }

                            leaf last-cleared {
                                type yang:date-and-time;
                                description "Date and time when this drop reason counter was last reset";
                            }

                        } // container no-server-id

                        container no-client-id {
                            description "Enter the no-client-id context";

                            leaf counter {
                                type yang:counter32;
                                description "Number of packets dropped";
                            }

                            leaf last-cleared {
                                type yang:date-and-time;
                                description "Date and time when this drop reason counter was last reset";
                            }

                        } // container no-client-id

                        container server-id-in-client-message {
                            description "Enter the server-id-in-client-message context";

                            leaf counter {
                                type yang:counter32;
                                description "Number of packets dropped";
                            }

                            leaf last-cleared {
                                type yang:date-and-time;
                                description "Date and time when this drop reason counter was last reset";
                            }

                        } // container server-id-in-client-message

                        container wrong-server-id {
                            description "Enter the wrong-server-id context";

                            leaf counter {
                                type yang:counter32;
                                description "Number of packets dropped";
                            }

                            leaf last-cleared {
                                type yang:date-and-time;
                                description "Date and time when this drop reason counter was last reset";
                            }

                        } // container wrong-server-id

                        container unicast {
                            description "Enter the unicast context";

                            leaf counter {
                                type yang:counter32;
                                description "Number of packets dropped";
                            }

                            leaf last-cleared {
                                type yang:date-and-time;
                                description "Date and time when this drop reason counter was last reset";
                            }

                        } // container unicast

                        container invalid-source-address {
                            description "Enter the invalid-source-address context";

                            leaf counter {
                                type yang:counter32;
                                description "Number of packets dropped";
                            }

                            leaf last-cleared {
                                type yang:date-and-time;
                                description "Date and time when this drop reason counter was last reset";
                            }

                        } // container invalid-source-address

                        container prefix-delegation-message-not-supported {
                            description "Enter the prefix-delegation-message-not-supported context";

                            leaf counter {
                                type yang:counter32;
                                description "Number of packets dropped";
                            }

                            leaf last-cleared {
                                type yang:date-and-time;
                                description "Date and time when this drop reason counter was last reset";
                            }

                        } // container prefix-delegation-message-not-supported

                        container number-of-addresses-exceeded {
                            description "Enter the number-of-addresses-exceeded context";

                            leaf counter {
                                type yang:counter32;
                                description "Number of packets dropped";
                            }

                            leaf last-cleared {
                                type yang:date-and-time;
                                description "Date and time when this drop reason counter was last reset";
                            }

                        } // container number-of-addresses-exceeded

                        container client-mac-not-resolved {
                            description "Enter the client-mac-not-resolved context";

                            leaf counter {
                                type yang:counter32;
                                description "Number of packets dropped";
                            }

                            leaf last-cleared {
                                type yang:date-and-time;
                                description "Date and time when this drop reason counter was last reset";
                            }

                        } // container client-mac-not-resolved

                        container invalid-assigned-address {
                            description "Enter the invalid-assigned-address context";

                            leaf counter {
                                type yang:counter32;
                                description "Number of packets dropped";
                            }

                            leaf last-cleared {
                                type yang:date-and-time;
                                description "Date and time when this drop reason counter was last reset";
                            }

                        } // container invalid-assigned-address

                        container illegal-message-encoding {
                            description "Enter the illegal-message-encoding context";

                            leaf counter {
                                type yang:counter32;
                                description "Number of packets dropped";
                            }

                            leaf last-cleared {
                                type yang:date-and-time;
                                description "Date and time when this drop reason counter was last reset";
                            }

                        } // container illegal-message-encoding

                        container routed-central-office-message-not-supported {
                            description "Enter the routed-central-office-message-not-supported context";

                            leaf counter {
                                type yang:counter32;
                                description "Number of packets dropped";
                            }

                            leaf last-cleared {
                                type yang:date-and-time;
                                description "Date and time when this drop reason counter was last reset";
                            }

                        } // container routed-central-office-message-not-supported

                        container ia-in-info-request {
                            description "Enter the ia-in-info-request context";

                            leaf counter {
                                type yang:counter32;
                                description "Number of packets dropped";
                            }

                            leaf last-cleared {
                                type yang:date-and-time;
                                description "Date and time when this drop reason counter was last reset";
                            }

                        } // container ia-in-info-request

                        container no-ia-in-client-message {
                            description "Enter the no-ia-in-client-message context";

                            leaf counter {
                                type yang:counter32;
                                description "Number of packets dropped";
                            }

                            leaf last-cleared {
                                type yang:date-and-time;
                                description "Date and time when this drop reason counter was last reset";
                            }

                        } // container no-ia-in-client-message

                        container no-address-in-confirm-message {
                            description "Enter the no-address-in-confirm-message context";

                            leaf counter {
                                type yang:counter32;
                                description "Number of packets dropped";
                            }

                            leaf last-cleared {
                                type yang:date-and-time;
                                description "Date and time when this drop reason counter was last reset";
                            }

                        } // container no-address-in-confirm-message

                        container no-relay-servers {
                            description "Enter the no-relay-servers context";

                            leaf counter {
                                type yang:counter32;
                                description "Number of packets dropped";
                            }

                            leaf last-cleared {
                                type yang:date-and-time;
                                description "Date and time when this drop reason counter was last reset";
                            }

                        } // container no-relay-servers

                        container host-lockout {
                            description "Enter the host-lockout context";

                            leaf counter {
                                type yang:counter32;
                                description "Number of packets dropped";
                            }

                            leaf last-cleared {
                                type yang:date-and-time;
                                description "Date and time when this drop reason counter was last reset";
                            }

                        } // container host-lockout

                        container no-link-address {
                            description "Enter the no-link-address context";

                            leaf counter {
                                type yang:counter32;
                                description "Number of packets dropped";
                            }

                            leaf last-cleared {
                                type yang:date-and-time;
                                description "Date and time when this drop reason counter was last reset";
                            }

                        } // container no-link-address

                        container dropped-by-python {
                            description "Enter the dropped-by-python context";

                            leaf counter {
                                type yang:counter32;
                                description "Number of packets dropped";
                            }

                            leaf last-cleared {
                                type yang:date-and-time;
                                description "Date and time when this drop reason counter was last reset";
                            }

                        } // container dropped-by-python

                        container invalid-forced-server {
                            description "Enter the invalid-forced-server context";

                            leaf counter {
                                type yang:counter32;
                                description "Number of packets dropped";
                            }

                            leaf last-cleared {
                                type yang:date-and-time;
                                description "Date and time when this drop reason counter was last reset";
                            }

                        } // container invalid-forced-server

                        container rx-on-srrp-backup-interface {
                            description "Enter the rx-on-srrp-backup-interface context";

                            leaf counter {
                                type yang:counter32;
                                description "Number of packets dropped";
                            }

                            leaf last-cleared {
                                type yang:date-and-time;
                                description "Date and time when this drop reason counter was last reset";
                            }

                        } // container rx-on-srrp-backup-interface

                        container dhcp-transaction-not-found {
                            description "Enter the dhcp-transaction-not-found context";

                            leaf counter {
                                type yang:counter32;
                                description "Number of packets dropped";
                            }

                            leaf last-cleared {
                                type yang:date-and-time;
                                description "Date and time when this drop reason counter was last reset";
                            }

                        } // container dhcp-transaction-not-found

                        container retail-interface-not-found {
                            description "Enter the retail-interface-not-found context";

                            leaf counter {
                                type yang:counter32;
                                description "Number of packets dropped";
                            }

                            leaf last-cleared {
                                type yang:date-and-time;
                                description "Date and time when this drop reason counter was last reset";
                            }

                        } // container retail-interface-not-found

                        container dropped-by-dhcp-filter {
                            description "Enter the dropped-by-dhcp-filter context";

                            leaf counter {
                                type yang:counter32;
                                description "Number of packets dropped";
                            }

                            leaf last-cleared {
                                type yang:date-and-time;
                                description "Date and time when this drop reason counter was last reset";
                            }

                        } // container dropped-by-dhcp-filter

                        container authentication-failed {
                            description "Enter the authentication-failed context";

                            leaf counter {
                                type yang:counter32;
                                description "Number of packets dropped";
                            }

                            leaf last-cleared {
                                type yang:date-and-time;
                                description "Date and time when this drop reason counter was last reset";
                            }

                        } // container authentication-failed

                        container invalid-forced-source-address {
                            description "Enter the invalid-forced-source-address context";

                            leaf counter {
                                type yang:counter32;
                                description "Number of packets dropped";
                            }

                            leaf last-cleared {
                                type yang:date-and-time;
                                description "Date and time when this drop reason counter was last reset";
                            }

                        } // container invalid-forced-source-address

                    } // container dropped

                } // container statistics

            } // container dhcp6

            uses state-router-bgp;
            uses state-router-bier;
            uses state-router-dhcp-server;
            uses state-router-igmp;
            uses state-router-isis;
            uses state-router-l2tp;
            uses state-router-fib-telemetry-label-fib;
            uses state-router-ldp;
            uses state-router-mld;
            uses state-router-mpls;
            uses state-router-msdp;
            uses state-router-nat;
            uses state-router-origin-validation;
            uses state-router-ospf;
            uses state-router-ospf3;
            uses state-router-pcep;
            uses state-router-pim;
            uses state-router-radius;
            uses state-router-rib-api;
            uses state-router-rip;
            uses state-router-ripng;
            uses state-router-fib-telemetry-route-fib;
            uses state-router-rsvp;
            uses state-router-segment-routing;
            uses state-router-static-route-static-routes;
            uses state-router-fib-telemetry-tunnel-fib;
            uses state-router-twamp-light;
            uses state-router-wpp;
        } // list router

    } // grouping state-router

}
