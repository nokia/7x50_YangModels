submodule nokia-conf-system-security-pki {

    yang-version "1.1";

    belongs-to nokia-conf { prefix "conf"; }

    import nokia-sros-yang-extensions     { prefix "sros-ext"; }
    import nokia-types-security           { prefix "types-security"; }
    import nokia-types-services           { prefix "types-services"; }
    import nokia-types-sros               { prefix "types-sros"; }

    include nokia-conf-groups;
    include nokia-conf-system;

    sros-ext:sros-major-release "rel20";

    organization "Nokia";

    contact
        "Nokia SR OS Support
         Web: <http://www.nokia.com>";

    description
        "Nokia YANG Data model to configure system security pki parameters. on SR OS based routers.

         Copyright 2016 Nokia. All rights reserved. Reproduction of this document
         is authorized on the condition that the foregoing copyright notice is included.

         This nokia-conf-system-security-pki YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";

    revision "2020-05-20";

    grouping conf-system-security-pki {
        container pki {
            description "Enter the pki context";

            leaf certificate-display-format {
                type enumeration {
                    enum "ascii"                        { value 1; }
                    enum "utf8"                         { value 2; }
                }
                default "ascii";
                description "Display format for certificates and Certificate Revocation Lists (CRLs)";
            }

            leaf imported-format {
                type enumeration {
                    enum "any"                          { value 1; }
                    enum "secure"                       { value 2; }
                }
                default "any";
                description "The supported encrypted file formats";
            }

            leaf maximum-cert-chain-depth {
                type uint32 {
                    range "1..7";
                }
                default "7";
                description "Maximum depth of certificate chain verification";
            }

            leaf-list apply-groups {
                type leafref {
                    path "../../../../groups/group/name";
                }
                max-elements 8;
                ordered-by user;
                description "Apply a configuration group at this level";
            }

            container certificate-expiration-warning {
                description "Enter the certificate-expiration-warning context";

                leaf hours {
                    type int32 {
                        range "0..8760";
                    }
                    units "hours";
                    description "Time at which the system generates the certificate expiration warning trap for in-use certificates";
                }

                leaf repeat-hours {
                    type int32 {
                        range "0..8760";
                    }
                    units "hours";
                    default "0";
                    description "Time period when the system repeatedly generates the certificate expiration warning trap";
                }

            } // container certificate-expiration-warning

            container crl-expiration-warning {
                description "Enter the crl-expiration-warning context";

                leaf hours {
                    type int32 {
                        range "0..8760";
                    }
                    units "hours";
                    description "Time when the system generates the Certificate Revocation List (CRL) expiration warning trap";
                }

                leaf repeat-hours {
                    type int32 {
                        range "0..8760";
                    }
                    units "hours";
                    default "0";
                    description "Time when the system repeatedly generates the Certificate Revocation List (CRL) expiration warning trap";
                }

            } // container crl-expiration-warning

            list ca-profile {
                key "ca-profile-name";
                max-elements 128;
                description "Enter the ca-profile list instance";

                leaf ca-profile-name {
                    type types-sros:named-item;
                    description "Certificate Authority (CA) profile name";
                }

                leaf admin-state {
                    type types-sros:admin-state;
                    default "disable";
                    description "Administrative state of the CA profile";
                }

                leaf description {
                    type types-sros:description;
                    description "Text description";
                }

                leaf cert-file {
                    type types-security:pki-file-name;
                    sros-ext:auto-restart-to-modify;
                    description "Certificate file name";
                }

                leaf crl-file {
                    type types-security:pki-file-name;
                    sros-ext:auto-restart-to-modify;
                    description "Certificate Revocation List (CRL) file name";
                }

                leaf revocation-check {
                    type enumeration {
                        enum "crl"                          { value 1; }
                        enum "crl-optional"                 { value 2; }
                    }
                    sros-ext:auto-restart-to-modify;
                    default "crl";
                    description "Method to verify the revocation status of certificates issued by the CA";
                }

                leaf-list apply-groups {
                    type leafref {
                        path "../../../../../groups/group/name";
                    }
                    max-elements 8;
                    ordered-by user;
                    sros-ext:auto-restart-to-modify;
                    description "Apply a configuration group at this level";
                }

                container ocsp {
                    sros-ext:auto-restart-to-modify;
                    description "Enter the ocsp context";

                    leaf responder-url {
                        type union {
                            type types-sros:http-optional-url-loose;
                        }
                        sros-ext:auto-restart-to-modify;
                        description "HTTP URL of the OCSP responder for the CA";
                    }

                    leaf service-name {
                        type types-services:service-name;
                        sros-ext:auto-restart-to-modify;
                        description "Service name for the OCSP URL";
                    }

                    leaf transmission-profile {
                        type leafref {
                            path "../../../../../transmission-profile/name";
                        }
                        sros-ext:auto-restart-to-modify;
                        description "The transmission profile for OCSP.";
                    }

                } // container ocsp

                container cmpv2 {
                    sros-ext:auto-restart-to-modify;
                    description "Enter the cmpv2 context";

                    leaf always-set-sender-for-ir {
                        type boolean;
                        sros-ext:auto-restart-to-modify;
                        default "false";
                        description "Subject name in CMPv2 header for all Initial Registration (IR) messages";
                    }

                    leaf same-recipient-nonce-for-poll-request {
                        type boolean;
                        sros-ext:auto-restart-to-modify;
                        default "false";
                        description "Same recipNonce as the last CMPv2 response for a poll request";
                    }

                    leaf response-signing-cert {
                        type types-security:pki-file-name;
                        sros-ext:auto-restart-to-modify;
                        description "File name of the certificate to verify the signature of received CMPv2 responses";
                    }

                    container accept-unprotected-message {
                        sros-ext:auto-restart-to-modify;
                        description "Enter the accept-unprotected-message context";

                        leaf error-message {
                            type boolean;
                            sros-ext:auto-restart-to-modify;
                            default "false";
                            description "Accept unprotected error messages";
                        }

                        leaf pkiconf-message {
                            type boolean;
                            sros-ext:auto-restart-to-modify;
                            default "false";
                            description "Accept unprotected PKI confirmation messages";
                        }

                    } // container accept-unprotected-message

                    container http {
                        sros-ext:auto-restart-to-modify;
                        description "Enter the http context";

                        leaf response-timeout {
                            type uint32 {
                                range "1..3600";
                            }
                            units "seconds";
                            sros-ext:auto-restart-to-modify;
                            default "30";
                            description "HTTP response timeout";
                        }

                        leaf version {
                            type enumeration {
                                enum "1.0"                          { value 1; }
                                enum "1.1"                          { value 2; }
                            }
                            sros-ext:auto-restart-to-modify;
                            default "1.1";
                            description "HTTP version for CMPv2 messages";
                        }

                    } // container http

                    container url {
                        sros-ext:auto-restart-to-modify;
                        description "Enter the url context";

                        leaf url-string {
                            type union {
                                type types-sros:http-optional-url-loose;
                            }
                            sros-ext:auto-restart-to-modify;
                            description "URL for CMPv2";
                        }

                        leaf service-name {
                            type types-services:service-name;
                            sros-ext:auto-restart-to-modify;
                            description "Service name for the CMPv2 URL";
                        }

                    } // container url

                    container key-list {
                        sros-ext:auto-restart-to-modify;
                        description "Enter the key-list context";

                        list key {
                            key "reference-number";
                            max-elements 128;
                            sros-ext:auto-restart-to-modify;
                            description "Enter the key list instance";

                            leaf reference-number {
                                type types-sros:display-string {
                                    length "1..64";
                                    pattern ".*\\S.*" {
                                        error-message "Reference number must not be all spaces";
                                    }
                                }
                                description "Unique identifier for the CA initial authentication key";
                            }

                            leaf password {
                                type types-sros:encrypted-leaf {
                                    length "1..115";
                                }
                                sros-ext:auto-restart-to-modify;
                                description "Shared secret for this CA initial authentication key";
                            }

                            leaf-list apply-groups {
                                type leafref {
                                    path "../../../../../../../../groups/group/name";
                                }
                                max-elements 8;
                                ordered-by user;
                                sros-ext:auto-restart-to-modify;
                                description "Apply a configuration group at this level";
                            }

                        } // list key

                    } // container key-list

                } // container cmpv2

                container auto-crl-update {
                    presence "Enables auto CRL update.";
                    sros-ext:auto-restart-to-modify;
                    description "Enter the auto-crl-update context";

                    leaf admin-state {
                        type types-sros:admin-state;
                        sros-ext:auto-restart-to-modify;
                        default "disable";
                        description "Administrative state of the automatic CRL update";
                    }

                    leaf periodic-update-interval {
                        type types-sros:time-duration {
                            range "3600..31622400";
                        }
                        units "seconds";
                        sros-ext:auto-restart-to-modify;
                        default "86400";
                        description "Interval between two consecutive CRL updates";
                    }

                    leaf pre-update-time {
                        type types-sros:time-duration {
                            range "0..31622400";
                        }
                        units "seconds";
                        sros-ext:auto-restart-to-modify;
                        default "3600";
                        description "Time prior to the next update time of the current CRL";
                    }

                    leaf retry-interval {
                        type types-sros:time-duration {
                            range "0..31622400";
                        }
                        units "seconds";
                        sros-ext:auto-restart-to-modify;
                        default "3600";
                        description "Interval before retrying to update CRL";
                    }

                    leaf schedule-type {
                        type enumeration {
                            enum "next-update-based"            { value 1; }
                            enum "periodic"                     { value 2; }
                        }
                        sros-ext:auto-restart-to-modify;
                        default "next-update-based";
                        description "Time scheduler type for an automated CRL update";
                    }

                    leaf-list apply-groups {
                        type leafref {
                            path "../../../../../../groups/group/name";
                        }
                        max-elements 8;
                        ordered-by user;
                        sros-ext:auto-restart-to-modify;
                        description "Apply a configuration group at this level";
                    }

                    container crl-urls {
                        sros-ext:auto-restart-to-modify;
                        description "Enter the crl-urls context";

                        list url-entry {
                            key "entry-id";
                            sros-ext:auto-restart-to-modify;
                            description "Enter the url-entry list instance";

                            leaf entry-id {
                                type uint32 {
                                    range "1..8";
                                }
                                description "URL on this system";
                            }

                            leaf transmission-profile {
                                type leafref {
                                    path "../../../../../../../transmission-profile/name";
                                }
                                sros-ext:auto-restart-to-modify;
                                description "File transmission profile to update CRL";
                            }

                            leaf url {
                                type union {
                                    type types-sros:http-url-path-loose;
                                }
                                sros-ext:auto-restart-to-modify;
                                description "Location of updated CRL";
                            }

                            leaf-list apply-groups {
                                type leafref {
                                    path "../../../../../../../../groups/group/name";
                                }
                                max-elements 8;
                                ordered-by user;
                                sros-ext:auto-restart-to-modify;
                                description "Apply a configuration group at this level";
                            }

                        } // list url-entry

                    } // container crl-urls

                } // container auto-crl-update

            } // list ca-profile

            list common-name-list {
                key "cn-list-name";
                max-elements 64;
                description "Enter the common-name-list list instance";

                leaf cn-list-name {
                    type types-sros:named-item;
                    description "Name for the common name list";
                }

                leaf-list apply-groups {
                    type leafref {
                        path "../../../../../groups/group/name";
                    }
                    max-elements 8;
                    ordered-by user;
                    description "Apply a configuration group at this level";
                }

                list common-name {
                    key "cn-index";
                    description "Enter the common-name list instance";

                    leaf cn-index {
                        type uint32 {
                            range "1..128";
                        }
                        description "Common name index";
                    }

                    leaf cn-type {
                        type enumeration {
                            enum "ip-address"                   { value 1; }
                            enum "domain-name"                  { value 2; }
                        }
                        mandatory true;
                        description "Common name type";
                    }

                    leaf cn-value {
                        type types-sros:regular-expression-not-all-spaces;
                        mandatory true;
                        description "Common name value";
                    }

                    leaf-list apply-groups {
                        type leafref {
                            path "../../../../../../groups/group/name";
                        }
                        max-elements 8;
                        ordered-by user;
                        description "Apply a configuration group at this level";
                    }

                } // list common-name

            } // list common-name-list

        } // container pki

    } // grouping conf-system-security-pki

}
