submodule nokia-state-port-eth-dot1x {

    yang-version "1.1";

    belongs-to nokia-state { prefix "state"; }

    import ietf-yang-types                { prefix "yang"; }
    import nokia-sros-yang-extensions     { prefix "sros-ext"; }
    import nokia-types-port               { prefix "types-port"; }


    sros-ext:sros-major-release "rel20";

    organization "Nokia";

    contact
        "Nokia SR OS Support
         Web: <http://www.nokia.com>";

    description
        "Nokia YANG Data model with operational state for ethernet ports 802.1x authentication capabilities on SR OS based routers.

         Copyright 2016 Nokia. All rights reserved. Reproduction of this document
         is authorized on the condition that the foregoing copyright notice is included.

         This nokia-state-port-eth-dot1x YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";

    revision "2020-08-21";

    grouping state-port-eth-dot1x {
        container dot1x {
            description "Enter the dot1x context";

            leaf authenticator-pae-state {
                type enumeration {
                    enum "initialize"                   { value 1; }
                    enum "disconnected"                 { value 2; }
                    enum "connecting"                   { value 3; }
                    enum "authenticating"               { value 4; }
                    enum "authenticated"                { value 5; }
                    enum "aborting"                     { value 6; }
                    enum "held"                         { value 7; }
                    enum "force-authorized"             { value 8; }
                    enum "force-unauthorized"           { value 9; }
                }
                description
                    "Indicates the current value of the Authenticator PAE state
                     machine.";
            }

            leaf backend-authentication-state {
                type enumeration {
                    enum "request"                      { value 1; }
                    enum "response"                     { value 2; }
                    enum "success"                      { value 3; }
                    enum "fail"                         { value 4; }
                    enum "timeout"                      { value 5; }
                    enum "idle"                         { value 6; }
                    enum "initialize"                   { value 7; }
                }
                description
                    "Indicates the current state of the Backend Authentication
                     state machine.";
            }

            leaf port-status {
                type types-port:pae-controlled-port-status;
                description
                    "Indicates the current value of the controlled Port
                     status parameter for the Port.";
            }

            container macsec {
                description "Enter the macsec context";

                list sub-port {
                    key "sub-port-id";
                    description "Enter the sub-port list instance";

                    leaf sub-port-id {
                        type uint32 {
                            range "1..1023";
                        }
                        description "Specifies the sub-port ID on the port.";
                    }

                    container statistics {
                        description "Enter the statistics context";

                        container received {
                            description "Enter the received context";

                            leaf bad-tag-packets {
                                type yang:counter64;
                                units "packets";
                                description
                                    "Indicates the number of received packets discarded with an
                                     invalid SecTAG or a zero value Packet Number (PN) or an
                                     invalid Integrity Check Value (ICV).";
                            }

                            leaf unknown-sci-packets {
                                type yang:counter64;
                                units "packets";
                                description
                                    "Indicates the number of received packets discarded with
                                     unknown SCI information when the C bit in the SecTAG is
                                     set.";
                            }

                            leaf packets-without-tag {
                                type yang:counter64;
                                units "packets";
                                description
                                    "Indicates the number of received packets discarded without
                                     the MAC security tag (SecTAG).";
                            }

                            leaf overrun-packets {
                                type yang:counter64;
                                units "packets";
                                description
                                    "Indicates the number of packets discarded because the number
                                     of received packets exceeded the cryptographic performance
                                     capabilities.";
                            }

                        } // container received

                        container transmitted {
                            description "Enter the transmitted context";

                            leaf too-long-packets {
                                type yang:counter64;
                                units "packets";
                                description
                                    "Indicates the number of transmitted packets discarded because
                                     the packet length is greater than the Maximum Transmission Unit
                                     (MTU) of the Ethernet physical interface.";
                            }

                            leaf untagged-packets {
                                type yang:counter64;
                                units "packets";
                                description
                                    "Indicates the number of transmitted packets without the MAC
                                     security tag (SecTAG) when the value of 
                                     macsec/connectivity-association/replay-protection
                                     for the configured CA is set to 'false'.";
                            }

                        } // container transmitted

                    } // container statistics

                } // list sub-port

            } // container macsec

            container statistics {
                description "Enter the statistics context";

                container received {
                    description "Enter the received context";

                    leaf bad-eap-length-frames {
                        type yang:counter32;
                        description
                            "Indicates the number of EAPOL frames that have been received
                             by this Authenticator in which the Packet Body
                             Length field is invalid.";
                    }

                    leaf last-source-mac-address {
                        type yang:mac-address;
                        description
                            "Indicates the source MAC address carried in the
                             most recently received EAPOL frame.";
                    }

                    leaf last-version {
                        type uint32;
                        description
                            "Indicates the protocol version number carried in the
                             most recently received EAPOL frame.";
                    }

                    leaf logoff-frames {
                        type yang:counter32;
                        description
                            "Indicates the number of EAPOL Logoff frames that have
                             been received by this Authenticator.";
                    }

                    leaf response-frames {
                        type yang:counter32;
                        description
                            "Indicates the number of valid EAP Response frames
                             (other than Resp/Id frames) that have been
                             received by this Authenticator.";
                    }

                    leaf response-id-frames {
                        type yang:counter32;
                        description
                            "Indicates the number of EAP Resp/Id frames that have
                             been received by this Authenticator.";
                    }

                    leaf start-frames {
                        type yang:counter32;
                        description
                            "Indicates the number of EAPOL Start frames that have
                             been received by this Authenticator.";
                    }

                    leaf valid-frames {
                        type yang:counter32;
                        description
                            "Indicates the number of valid EAPOL frames of any type
                             that have been received by this Authenticator.";
                    }

                    leaf unknown-frames {
                        type yang:counter32;
                        description
                            "Indicates the number of EAPOL frames that have been
                             received by this Authenticator in which the
                             frame type is not recognized.";
                    }

                } // container received

                container transmitted {
                    description "Enter the transmitted context";

                    leaf request-frames {
                        type yang:counter32;
                        description
                            "Indicates the number of EAP Request frames
                             (other than Rq/Id frames) that have been
                             transmitted by this Authenticator.";
                    }

                    leaf request-id-frames {
                        type yang:counter32;
                        description
                            "Indicates the number of EAP Req/Id frames that have been
                             transmitted by this Authenticator.";
                    }

                    leaf total-frames {
                        type yang:counter32;
                        description
                            "Indicates the number of EAPOL frames of any type
                             that have been transmitted by this Authenticator.";
                    }

                } // container transmitted

            } // container statistics

        } // container dot1x

    } // grouping state-port-eth-dot1x

}
