module nokia-types-vrrp {

    yang-version "1.1";

    namespace "urn:nokia.com:sros:ns:yang:sr:types-vrrp";

    prefix "types-vrrp";

    import nokia-sros-yang-extensions     { prefix "sros-ext"; }


    sros-ext:sros-major-release "rel20";

    organization "Nokia";

    contact
        "Nokia SR OS Support
         Web: <http://www.nokia.com>";

    description
        "Common data-types data types used in the SR OS management system.

         Copyright 2016 Nokia. All rights reserved. Reproduction of this document
         is authorized on the condition that the foregoing copyright notice is included.

         This nokia-types-vrrp YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";

    revision "2020-06-02";

    typedef priority {
        type uint8 {
            range "1..254";
        }
    }

    typedef host-unreachable-event-oper-state {
        type enumeration {
            enum "cleared-no-arp"               { value 0; }
            enum "cleared-no-route"             { value 1; }
            enum "cleared-host-unreachable"     { value 2; }
            enum "cleared-no-reply"             { value 3; }
            enum "cleared-reply-received"       { value 4; }
            enum "set-no-arp"                   { value 5; }
            enum "set-no-route"                 { value 6; }
            enum "set-host-unreachable"         { value 7; }
            enum "set-no-reply"                 { value 8; }
            enum "set-reply-received"           { value 9; }
        }
        description
            "The textual convention is an enumerated integer that specifies the operational state
             of a Host Unreachable Priority Event. The event state corresponds
             to the ability to receive ICMP Echo Reply packets from the
             IP host address associated with the event";
    }

    typedef port-down-oper-state {
        type enumeration {
            enum "cleared"                      { value 0; }
            enum "set-non-existant"             { value 1; }
            enum "set"                          { value 2; }
        }
        description
            "The value of zero indicates operational state of 'cleared' and
             '1' indicates 'set-non-existant'. Otherwise the value indicates
             that one or more ports down were configured.";
    }

    typedef ip-sec-no-forwarding-oper-state {
        type enumeration {
            enum "cleared"                      { value 0; }
            enum "set-not-forwarding"           { value 1; }
        }
        description
            "The textual convention is an enumerated integer that specifies
             the operational state of a multi-chassis IPsec non-forwarding
             Priority Event.

             The event state corresponds to the state of the tunnel-group with
             which it is associated.";
    }

    typedef port-down-event-oper-state {
        type enumeration {
            enum "cleared"                      { value 0; }
            enum "set-not-provisioned"          { value 1; }
            enum "set-not-populated"            { value 2; }
            enum "set-down"                     { value 3; }
        }
        description
            "The textual convention is an enumerated integer that specifies
             the operational state of a Port Down Priority Event. The event
             state corresponds to the state of the port or the channel with
             which it is associated.";
    }

    typedef route-unknown-event-oper-state {
        type enumeration {
            enum "cleared-less-specific-found"  { value 0; }
            enum "cleared-found"                { value 1; }
            enum "set-non-existent"             { value 2; }
            enum "set-in-active"                { value 3; }
            enum "set-wrong-next-hop"           { value 4; }
            enum "set-wrong-protocol"           { value 5; }
            enum "set-less-specific-found"      { value 6; }
            enum "set-default-best-match"       { value 7; }
        }
        description
            "The textual convention is an enumerated integer that specifies
             the operational state of a Route Unknown Priority Event. The event
             state corresponds to the existence in the routing table of an active
             route to the IP route prefix corresponding to the event.";
    }

    typedef event-hold {
        type uint32 {
            range "1..86400";
        }
    }

    typedef event-hold-state {
        type union {
            type event-hold;
            type enumeration {
                enum "expired"                      { value 0; }
            }
        }
    }

}
