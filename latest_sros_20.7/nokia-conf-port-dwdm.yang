submodule nokia-conf-port-dwdm {

    yang-version "1.1";

    belongs-to nokia-conf { prefix "conf"; }

    import nokia-sros-yang-extensions     { prefix "sros-ext"; }
    import nokia-types-port               { prefix "types-port"; }

    include nokia-conf-groups;
    include nokia-conf-port-dwdm-coherent;

    sros-ext:sros-major-release "rel20";

    organization "Nokia";

    contact
        "Nokia SR OS Support
         Web: <http://www.nokia.com>";

    description
        "Nokia YANG Data model to configure dense wavelength division multiplexing ports on SR OS based routers.

         Copyright 2016 Nokia. All rights reserved. Reproduction of this document
         is authorized on the condition that the foregoing copyright notice is included.

         This nokia-conf-port-dwdm YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";

    revision "2019-07-28";

    grouping conf-port-dwdm {
        container dwdm {
            description "Enter the dwdm context";

            leaf channel {
                type types-port:optical-dwdm-channel;
                description "DWDM channel number";
            }

            leaf rxdtv-adjust {
                type boolean;
                description "Adjust feedback for received decision threshold voltage";
            }

            leaf-list apply-groups {
                type leafref {
                    path "../../../groups/group/name";
                }
                max-elements 8;
                ordered-by user;
                description "Apply a configuration group at this level";
            }

            container wavetracker {
                description "Enter the wavetracker context";

                leaf-list apply-groups {
                    type leafref {
                        path "../../../../groups/group/name";
                    }
                    max-elements 8;
                    ordered-by user;
                    description "Apply a configuration group at this level";
                }

                container encode {
                    presence "Enter the 'encode' context";
                    description "Enable the encode context";

                    leaf key1 {
                        type uint32 {
                            range "1..4095";
                        }
                        mandatory true;
                        description "Configure the first wavetracker key.";
                    }

                    leaf key2 {
                        type uint32 {
                            range "1..4095";
                        }
                        mandatory true;
                        description "Configure the second wavetracker key.";
                    }

                } // container encode

                container power-control {
                    presence "Enter the 'power-control' context";
                    description "Enable the power-control context";

                    leaf target-power {
                        type decimal64 {
                            range "-22..3";
                            fraction-digits 2;
                        }
                        units "decibels per milliwatt";
                        default "-20";
                        description "Configure desired average output power.";
                    }

                } // container power-control

                container report-alarm {
                    description "Enter the report-alarm context";

                    leaf encoder-failure {
                        type boolean;
                        default "true";
                        description "Enable/disable encoder-failure alarm.";
                    }

                    leaf encoder-degrade {
                        type boolean;
                        default "true";
                        description "Enable/disable encoder-degrade alarm.";
                    }

                    leaf power-control-failure {
                        type boolean;
                        default "true";
                        description "Enable/disable power-control-failure alarm.";
                    }

                    leaf power-control-degrade {
                        type boolean;
                        default "true";
                        description "Enable/disable power-control-degrade alarm.";
                    }

                    leaf power-control-high-limit {
                        type boolean;
                        default "true";
                        description "Enable/disable power-control-high-limit alarm.";
                    }

                    leaf power-control-low-limit {
                        type boolean;
                        default "true";
                        description "Enable/disable power-control-low-limit alarm.";
                    }

                    leaf missing-pluggable-voa {
                        type boolean;
                        default "true";
                        description "Enable/disable missing-pluggable-voa alarm.";
                    }

                } // container report-alarm

            } // container wavetracker

            uses conf-port-dwdm-coherent;
        } // container dwdm

    } // grouping conf-port-dwdm

}
