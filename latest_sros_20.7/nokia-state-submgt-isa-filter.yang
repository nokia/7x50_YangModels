submodule nokia-state-submgt-isa-filter {

    yang-version "1.1";

    belongs-to nokia-state { prefix "state"; }

    import ietf-yang-types                { prefix "yang"; }
    import nokia-sros-yang-extensions     { prefix "sros-ext"; }
    import nokia-types-sros               { prefix "types-sros"; }


    sros-ext:sros-major-release "rel20";

    organization "Nokia";

    contact
        "Nokia SR OS Support
         Web: <http://www.nokia.com>";

    description
        "Nokia YANG Data model with operational state for subscriber management isa filter on SR OS based routers.

         Copyright 2016 Nokia. All rights reserved. Reproduction of this document
         is authorized on the condition that the foregoing copyright notice is included.

         This nokia-state-submgt-isa-filter YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";

    revision "2019-04-16";

    grouping state-submgt-isa-filter {
        list isa-filter {
            key "name";
            description "Enter the isa-filter list instance";

            leaf name {
                type types-sros:named-item;
                description "ISA filter name";
            }

            container ipv4 {
                description "Enter the ipv4 context";

                list entry {
                    key "id";
                    description "Enter the entry list instance";

                    leaf id {
                        type uint16 {
                            range "1..1024";
                        }
                        description "ISA filter entry ID";
                    }

                    leaf ingress-hit-pkt {
                        type yang:zero-based-counter64;
                        description "This object indicates the number of times an ingress packet matched this entry";
                    }

                } // list entry

            } // container ipv4

            container ipv6 {
                description "Enter the ipv6 context";

                list entry {
                    key "id";
                    description "Enter the entry list instance";

                    leaf id {
                        type uint16 {
                            range "1..1024";
                        }
                        description "ISA filter entry ID";
                    }

                    leaf ingress-hit-pkt {
                        type yang:zero-based-counter64;
                        description "This object indicates the number of times an ingress packet matched this entry";
                    }

                } // list entry

            } // container ipv6

        } // list isa-filter

    } // grouping state-submgt-isa-filter

}
