submodule nokia-conf-mirror {

    yang-version "1.1";

    belongs-to nokia-conf { prefix "conf"; }

    import ietf-yang-types                { prefix "yang"; }
    import nokia-sros-yang-extensions     { prefix "sros-ext"; }
    import nokia-types-services           { prefix "types-services"; }
    import nokia-types-sros               { prefix "types-sros"; }
    import nokia-types-subscriber-mgmt    { prefix "types-submgt"; }

    include nokia-conf-filter;
    include nokia-conf-groups;
    include nokia-conf-qos;

    sros-ext:sros-major-release "rel20";

    organization "Nokia";

    contact
        "Nokia SR OS Support
         Web: <http://www.nokia.com>";

    description
        "Nokia YANG Data model to configure mirror services on SR OS based routers.

         Copyright 2016 Nokia. All rights reserved. Reproduction of this document
         is authorized on the condition that the foregoing copyright notice is included.

         This nokia-conf-mirror YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";

    revision "2020-07-10";

    grouping conf-mirror {
        container mirror {
            description "Enter the mirror context";

            leaf-list apply-groups {
                type leafref {
                    path "../../groups/group/name";
                }
                max-elements 8;
                ordered-by user;
                description "Apply a configuration group at this level";
            }

            list mirror-dest {
                key "service-name";
                max-elements 255;
                description "Enter the mirror-dest list instance";

                leaf service-name {
                    type types-services:service-name;
                    description "Service name";
                }

                leaf type {
                    type types-services:mirror-type;
                    sros-ext:immutable;
                    default "ether";
                    description "Mirror type information";
                }

                leaf fc {
                    type types-sros:fc-name;
                    default "be";
                    description "Forwarding class for destination traffic";
                }

                leaf slice-size {
                    type uint32 {
                        range "128..9216";
                    }
                    description "Maximum size of a mirrored frame that can be transmitted to the mirror destination";
                }

                leaf include-port-id {
                    type boolean;
                    default "false";
                    description "Include port ID of the system in the packet";
                }

                leaf sampling-rate {
                    type uint32 {
                        range "256..10000";
                    }
                    description "Sampling rate";
                }

                leaf service-id {
                    type types-services:external-service-id;
                    sros-ext:immutable;
                    description "Unique service ID; cannot be used by any other service, regardless of service type";
                }

                leaf description {
                    type types-sros:description;
                    description "Text description";
                }

                leaf admin-state {
                    type types-sros:admin-state;
                    default "disable";
                    description "Administrative state of the mirror destination service";
                }

                leaf-list apply-groups {
                    type leafref {
                        path "../../../groups/group/name";
                    }
                    max-elements 8;
                    ordered-by user;
                    description "Apply a configuration group at this level";
                }

                list endpoint {
                    key "name";
                    max-elements 2;
                    description "Enter the endpoint list instance";

                    leaf name {
                        type types-sros:named-item;
                        description "Service endpoint name";
                    }

                    leaf description {
                        type types-sros:description;
                        description "Text description";
                    }

                    leaf revert-time {
                        type types-services:revert-time;
                        default "immediate";
                        description "Time before reverting back to primary spoke SDP defined after failing in backup spoke SDP";
                    }

                    leaf-list apply-groups {
                        type leafref {
                            path "../../../../groups/group/name";
                        }
                        max-elements 8;
                        ordered-by user;
                        description "Apply a configuration group at this level";
                    }

                } // list endpoint

                list sap {
                    key "sap-id";
                    max-elements 1;
                    description "Enter the sap list instance";

                    leaf sap-id {
                        type types-sros:sap;
                        description "SAP identifier";
                    }

                    leaf endpoint {
                        type leafref {
                            path "../../endpoint/name";
                        }
                        description "Configure name of the service endpoint.";
                    }

                    leaf-list apply-groups {
                        type leafref {
                            path "../../../../groups/group/name";
                        }
                        max-elements 8;
                        ordered-by user;
                        description "Apply a configuration group at this level";
                    }

                    container egress {
                        description "Enter the egress context";

                        container qos {
                            description "Enter the qos context";

                            container sap-egress {
                                description "Enter the sap-egress context";

                                leaf policy-name {
                                    type leafref {
                                        path "../../../../../../../qos/sap-egress/sap-egress-policy-name";
                                    }
                                    description "Policy identifier";
                                }

                                container port-redirect-group {
                                    description "Enter the port-redirect-group context";

                                    leaf group-name {
                                        type leafref {
                                            path "../../../../../../../../qos/queue-group-templates/egress/queue-group/egress-queue-group-name";
                                        }
                                        description "Port redirect queue-group policy";
                                    }

                                    leaf instance {
                                        type types-services:qos-qgrp-instance-id;
                                        description "Port queue-group instance";
                                    }

                                } // container port-redirect-group

                            } // container sap-egress

                        } // container qos

                        container ip-mirror {
                            description "Enter the ip-mirror context";

                            container mac {
                                description "Enter the mac context";

                                leaf source {
                                    type types-sros:mac-unicast-address;
                                    description "Source MAC address.";
                                }

                                leaf destination {
                                    type yang:mac-address;
                                    description "Destination MAC address.";
                                }

                            } // container mac

                        } // container ip-mirror

                    } // container egress

                } // list sap

                container remote-source {
                    presence "Enter the 'remote-source' context";
                    description "Enable the remote-source context";

                    list far-end {
                        key "far-end-addr";
                        description "Enter the far-end list instance";

                        leaf far-end-addr {
                            type types-sros:ipv4-address;
                            description "Far end IP address";
                        }

                        leaf vc-id {
                            type uint32 {
                                range "1..max";
                            }
                            mandatory true;
                            description "Virtual circuit identifier associated with the remote source";
                        }

                        leaf icb {
                            type boolean;
                            default "false";
                            description "Remote source as an inter-chassis backup";
                        }

                        leaf-list apply-groups {
                            type leafref {
                                path "../../../../../groups/group/name";
                            }
                            max-elements 8;
                            ordered-by user;
                            description "Apply a configuration group at this level";
                        }

                        choice ingress-label {
                            default "label-signaling";
                            case label-signaling {

                                leaf label-signaling {
                                    type enumeration {
                                        enum "tldp"                         { value 2; }
                                    }
                                    default "tldp";
                                    description "Protocol to obtain the ingress labels";
                                }

                            }
                            case ing-vc-label {

                                leaf ing-vc-label {
                                    type uint32 {
                                        range "32..18431";
                                    }
                                    description "Ingress virtual circuit label";
                                }

                            }
                        }
                    } // list far-end

                    list spoke-sdp {
                        key "sdp-bind-id";
                        description "Enter the spoke-sdp list instance";

                        leaf sdp-bind-id {
                            type types-services:sdp-bind-id;
                            description "SDP Binding identifier.";
                        }

                        leaf admin-state {
                            type types-sros:admin-state;
                            default "enable";
                            description "Administrative state of this Service SDP binding";
                        }

                        leaf control-word {
                            when "not(../../../type = 'atm-sdu')";
                            type boolean;
                            description "Enable the CW bit in label message";
                        }

                        leaf-list apply-groups {
                            type leafref {
                                path "../../../../../groups/group/name";
                            }
                            max-elements 8;
                            ordered-by user;
                            description "Apply a configuration group at this level";
                        }

                        container ingress {
                            description "Enter the ingress context";

                            leaf vc-label {
                                type uint32 {
                                    range "32..18431";
                                }
                                description "Static MPLS VC label used by the far end device to send packets through this SDP";
                            }

                            container l2tpv3 {
                                description "Enter the l2tpv3 context";

                                container cookie {
                                    description "Enter the cookie context";

                                    leaf cookie1 {
                                        type types-services:cookie-value;
                                        description "Value of cookie-1 for the tunnel";
                                    }

                                    leaf cookie2 {
                                        type types-services:cookie-value;
                                        description "Value of cookie-1 for the tunnel";
                                    }

                                } // container cookie

                            } // container l2tpv3

                        } // container ingress

                        container egress {
                            description "Enter the egress context";

                            leaf vc-label {
                                type types-services:egress-vc-label;
                                description "Static MPLS VC label that is used to send packets to the far end device through this SDP";
                            }

                        } // container egress

                        container endpoint {
                            description "Enter the endpoint context";

                            leaf name {
                                type leafref {
                                    path "../../../../endpoint/name";
                                }
                                description "Name of endpoint where this SDP bind is attached";
                            }

                            leaf icb {
                                type boolean;
                                default "false";
                                description "Bind SDP as type Inter-Chassis Backup (ICB)";
                            }

                        } // container endpoint

                    } // list spoke-sdp

                } // container remote-source

                list spoke-sdp {
                    key "sdp-bind-id";
                    description "Enter the spoke-sdp list instance";

                    leaf sdp-bind-id {
                        type types-services:sdp-bind-id;
                        description "SDP Binding identifier.";
                    }

                    leaf admin-state {
                        type types-sros:admin-state;
                        default "enable";
                        description "Administrative state of this Service SDP binding";
                    }

                    leaf control-word {
                        when "not(../../type = 'atm-sdu')";
                        type boolean;
                        description "Set the CW bit in the label message";
                    }

                    leaf-list apply-groups {
                        type leafref {
                            path "../../../../groups/group/name";
                        }
                        max-elements 8;
                        ordered-by user;
                        description "Apply a configuration group at this level";
                    }

                    container ingress {
                        description "Enter the ingress context";

                        leaf vc-label {
                            type uint32 {
                                range "32..18431";
                            }
                            sros-ext:auto-restart-to-modify;
                            description "Static MPLS VC label used by the far end device to send packets through this SDP";
                        }

                    } // container ingress

                    container egress {
                        description "Enter the egress context";

                        leaf vc-label {
                            type types-services:egress-vc-label;
                            sros-ext:auto-restart-to-modify;
                            description "Static MPLS VC label that is used to send packets to the far end device through this SDP";
                        }

                        container l2tpv3 {
                            description "Enter the l2tpv3 context";

                            leaf cookie {
                                type types-services:cookie-value;
                                description "Cookie parameters";
                            }

                        } // container l2tpv3

                    } // container egress

                    container endpoint {
                        description "Enter the endpoint context";

                        leaf name {
                            type leafref {
                                path "../../../endpoint/name";
                            }
                            description "Name of endpoint where this SDP bind is attached";
                        }

                        leaf precedence {
                            type types-services:sdp-precedence;
                            default "4";
                            description "Precedence of this SDP bind when there are multiple SDP binds attached to one service endpoint";
                        }

                        leaf icb {
                            type boolean;
                            sros-ext:auto-restart-to-modify;
                            default "false";
                            description "Bind SDP as type Inter-Chassis Backup (ICB)";
                        }

                    } // container endpoint

                } // list spoke-sdp

                container encap {
                    description "Enter the encap context";

                    container layer-3-encap {
                        presence "Enter the 'layer-3-encap' context";
                        description "Enable the layer-3-encap context";

                        leaf header-type {
                            type enumeration {
                                enum "ip-udp-shim"                  { value 1; }
                                enum "ip-gre"                       { value 2; }
                                enum "ip-udp-shim-sampled"          { value 4; }
                            }
                            sros-ext:immutable;
                            mandatory true;
                            description "Header for the Layer 3 encapsulation";
                        }

                        leaf direction-bit {
                            type boolean;
                            default "false";
                            description "Highest bit in Interception ID of shim header to show direction of mirrored traffic flow";
                        }

                        leaf router-instance {
                            type string;
                            default "Base";
                            description "Router instance to use with routed encapsulation";
                        }

                        leaf-list apply-groups {
                            type leafref {
                                path "../../../../../groups/group/name";
                            }
                            max-elements 8;
                            ordered-by user;
                            description "Apply a configuration group at this level";
                        }

                        container gateway {
                            presence "Enter the 'gateway' context";
                            description "Enable the gateway context";

                            leaf-list apply-groups {
                                type leafref {
                                    path "../../../../../../groups/group/name";
                                }
                                max-elements 8;
                                ordered-by user;
                                description "Apply a configuration group at this level";
                            }

                            container ip-address {
                                description "Enter the ip-address context";

                                leaf source {
                                    type types-sros:ipv4-unicast-address;
                                    description "IPv4 source address for the gateway";
                                }

                                leaf destination {
                                    type types-sros:ipv4-unicast-address;
                                    description "IPv4 destination address for the gateway";
                                }

                            } // container ip-address

                            container udp-port {
                                description "Enter the udp-port context";

                                leaf source {
                                    type types-sros:tcp-udp-port;
                                    default "0";
                                    description "UDP source port with this gateway";
                                }

                                leaf destination {
                                    type types-sros:tcp-udp-port;
                                    default "0";
                                    description "UDP destination port to use with this gateway";
                                }

                            } // container udp-port

                        } // container gateway

                    } // container layer-3-encap

                } // container encap

                list pcap {
                    key "session-name";
                    max-elements 1;
                    description "Enter the pcap list instance";

                    leaf session-name {
                        type types-sros:named-item;
                        description "Packet Capture (PCAP) session name";
                    }

                    leaf file-url {
                        type types-sros:ts-url;
                        description "URL and file name for packet capture transfer";
                    }

                    leaf-list apply-groups {
                        type leafref {
                            path "../../../../groups/group/name";
                        }
                        max-elements 8;
                        ordered-by user;
                        description "Apply a configuration group at this level";
                    }

                } // list pcap

            } // list mirror-dest

            list mirror-source {
                key "service-name";
                description "Enter the mirror-source list instance";

                leaf service-name {
                    type types-services:service-name;
                    description "Service name";
                }

                leaf admin-state {
                    type types-sros:admin-state;
                    default "enable";
                    description "Enable/disable mirror service.";
                }

                leaf-list apply-groups {
                    type leafref {
                        path "../../../groups/group/name";
                    }
                    max-elements 8;
                    ordered-by user;
                    description "Apply a configuration group at this level";
                }

                list port {
                    key "port-id";
                    description "Enter the port list instance";

                    leaf port-id {
                        type types-services:mirror-source-port-lag-key;
                        description "Port identifier.";
                    }

                    leaf ingress {
                        type boolean;
                        default "false";
                        description "Whether ingress packets will be mirrored or not.";
                    }

                    leaf egress {
                        type boolean;
                        default "false";
                        description "Whether egress packets will be mirrored or not.";
                    }

                    leaf-list apply-groups {
                        type leafref {
                            path "../../../../groups/group/name";
                        }
                        max-elements 8;
                        ordered-by user;
                        description "Apply a configuration group at this level";
                    }

                } // list port

                list sap {
                    key "sap-id";
                    description "Enter the sap list instance";

                    leaf sap-id {
                        type types-sros:sap;
                        description "SAP identifier.";
                    }

                    leaf ingress {
                        type boolean;
                        default "false";
                        description "Whether ingress packets will be mirrored or not.";
                    }

                    leaf egress {
                        type boolean;
                        default "false";
                        description "Whether egress packets will be mirrored or not.";
                    }

                    leaf-list apply-groups {
                        type leafref {
                            path "../../../../groups/group/name";
                        }
                        max-elements 8;
                        ordered-by user;
                        description "Apply a configuration group at this level";
                    }

                } // list sap

                list ip-filter {
                    key "filter-name";
                    description "Enter the ip-filter list instance";

                    leaf filter-name {
                        type leafref {
                            path "../../../../filter/ip-filter/filter-name";
                        }
                        description "IP Filter name";
                    }

                    leaf-list apply-groups {
                        type leafref {
                            path "../../../../groups/group/name";
                        }
                        max-elements 8;
                        ordered-by user;
                        description "Apply a configuration group at this level";
                    }

                    list entry {
                        key "entry-id";
                        min-elements 1;
                        description "Add a list entry for entry";

                        leaf entry-id {
                            type uint32 {
                                range "1..2097151";
                            }
                            description "IP Filter entry identifier";
                        }

                    } // list entry

                } // list ip-filter

                list ipv6-filter {
                    key "filter-name";
                    description "Enter the ipv6-filter list instance";

                    leaf filter-name {
                        type leafref {
                            path "../../../../filter/ipv6-filter/filter-name";
                        }
                        description "IPv6 Filter name";
                    }

                    leaf-list apply-groups {
                        type leafref {
                            path "../../../../groups/group/name";
                        }
                        max-elements 8;
                        ordered-by user;
                        description "Apply a configuration group at this level";
                    }

                    list entry {
                        key "entry-id";
                        min-elements 1;
                        description "Add a list entry for entry";

                        leaf entry-id {
                            type uint32 {
                                range "1..2097151";
                            }
                            description "IPv6 Filter entry identifier";
                        }

                    } // list entry

                } // list ipv6-filter

                list mac-filter {
                    key "filter-name";
                    description "Enter the mac-filter list instance";

                    leaf filter-name {
                        type leafref {
                            path "../../../../filter/mac-filter/filter-name";
                        }
                        description "MAC Filter name";
                    }

                    leaf-list apply-groups {
                        type leafref {
                            path "../../../../groups/group/name";
                        }
                        max-elements 8;
                        ordered-by user;
                        description "Apply a configuration group at this level";
                    }

                    list entry {
                        key "entry-id";
                        min-elements 1;
                        description "Add a list entry for entry";

                        leaf entry-id {
                            type uint32 {
                                range "1..2097151";
                            }
                            description "MAC Filter entry identifier";
                        }

                    } // list entry

                } // list mac-filter

                list subscriber {
                    key "subscriber-id";
                    description "Enter the subscriber list instance";

                    leaf subscriber-id {
                        type types-submgt:subscriber-id;
                        description "Subscriber Identifier";
                    }

                    leaf-list fc {
                        type enumeration {
                            enum "be"                           { value 0; }
                            enum "l2"                           { value 1; }
                            enum "af"                           { value 2; }
                            enum "l1"                           { value 3; }
                            enum "h2"                           { value 4; }
                            enum "ef"                           { value 5; }
                            enum "h1"                           { value 6; }
                            enum "nc"                           { value 7; }
                        }
                        max-elements 8;
                        description "The forwarding classes traffic which should be mirrored";
                    }

                    leaf ingress {
                        type boolean;
                        default "false";
                        description "Whether ingress packets will be mirrored or not.";
                    }

                    leaf egress {
                        type boolean;
                        default "false";
                        description "Whether egress packets will be mirrored or not.";
                    }

                    leaf host-type {
                        type enumeration {
                            enum "ipoe"                         { value 2; }
                            enum "ppp"                          { value 3; }
                        }
                        description "The host type to be mirrored.";
                    }

                    leaf ip-family {
                        type enumeration {
                            enum "ipv4"                         { value 2; }
                            enum "ipv6"                         { value 3; }
                        }
                        description "The family of IP flows to be monitored for an IPoE type of host.";
                    }

                    leaf-list apply-groups {
                        type leafref {
                            path "../../../../groups/group/name";
                        }
                        max-elements 8;
                        ordered-by user;
                        description "Apply a configuration group at this level";
                    }

                    choice host-identification {
                        case sap-id {

                            leaf sap-id {
                                type types-sros:sap;
                                description "Subscriber SAP identifier";
                            }

                            leaf mac-address {
                                type yang:mac-address;
                                description "The MAC address to be used to match the packets for the subscriber on the mirror source.";
                            }

                            leaf ip-address {
                                type types-sros:ipv4-address;
                                description "The IP address of the remote source or the far-end ESR which is allowed to be a source of packets.";
                            }

                        }
                        case sla-profile {

                            leaf sla-profile {
                                type types-sros:named-item;
                                description "The SLA profile Name";
                            }

                        }
                    }
                } // list subscriber

            } // list mirror-source

        } // container mirror

    } // grouping conf-mirror

}
