submodule nokia-state-svc-sdp {

    yang-version "1.1";

    belongs-to nokia-state { prefix "state"; }

    import nokia-sros-yang-extensions     { prefix "sros-ext"; }
    import nokia-types-services           { prefix "types-services"; }
    import nokia-types-sros               { prefix "types-sros"; }


    sros-ext:sros-major-release "rel20";

    organization "Nokia";

    contact
        "Nokia SR OS Support
         Web: <http://www.nokia.com>";

    description
        "Nokia YANG Data model with operational state for services on SR OS based routers.

         Copyright 2016 Nokia. All rights reserved. Reproduction of this document
         is authorized on the condition that the foregoing copyright notice is included.

         This nokia-state-svc-sdp YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";

    revision "2020-05-19";

    grouping state-svc-sdp {
        list sdp {
            key "sdp-id";
            description "Enter the sdp list instance";

            leaf sdp-id {
                type types-services:sdp-id;
                description "Service Distribution Point (SDP) identifier";
            }

            leaf sdp-oper-state {
                type enumeration {
                    enum "up"                           { value 1; }
                    enum "down"                         { value 6; }
                }
                description "This object indicates the operating state of this SDP.";
            }

            leaf sdp-oper-path-mtu {
                type int32;
                description "This object indicates the operation path MTU.";
            }

            leaf sdp-oper-flags {
                type bits {
                    bit sdp-admin-down                 { position 0; }
                    bit signaling-session-down         { position 1; }
                    bit transport-tunnel-down          { position 2; }
                    bit keep-alive-failure             { position 3; }
                    bit invalid-egress-interface       { position 4; }
                    bit no-system-ip-address           { position 5; }
                    bit transport-tunnel-unstable      { position 6; }
                    bit not-on-binding-port            { position 7; }
                }
                description "This object indicates the operating status of this SDP.";
            }

            leaf mvpls-mgmt-service {
                type uint32 {
                    range "0..2148007980";
                }
                description
                    "This object indicates the service Id where the STP instance is
                     running that is managing this SDP.";
            }

            leaf mvpls-mgmt-sdp-bind-id {
                type types-services:state-sdp-bind-id-or-zero;
                description
                    "This object indicates the SDP bind in the mVPLS instance
                     specified in sdpMvplsMgmtService is controlling this SDP.";
            }

            leaf sdp-oper-bandwidth {
                type uint32;
                description "This object indicates the operational Bandwidth available for this SDP.";
            }

            leaf sdp-available-bandwidth {
                type uint32;
                description
                    "This object indicates the Bandwidth still free for booking by
                     the SDP bindings on the SDP.";
            }

            leaf sdp-creation-origin {
                type types-sros:creation-origin;
                description "Creation origin of this SDP.";
            }

            leaf lsp-revert-time-countdown {
                type int32 {
                    range "-1|0..600";
                }
                description
                    "This object indicates the timer countdown before reverting back
                     from LDP on this SDP.";
            }

            leaf ldp-lsp-id {
                type uint32;
                description "This object indicates the LDP LSP Id.";
            }

            leaf egress-ifs-net-domain-consistent {
                type enumeration {
                    enum "not-applicable"               { value 1; }
                    enum "consistent"                   { value 2; }
                    enum "inconsistent"                 { value 3; }
                }
                description
                    "This object indicates whether all the egress network interfaces
                     that can carry traffic on this SDP are associated with the
                     network-domain configured on this SDP.";
            }

            leaf bgp-tunnel-lsp-id {
                type uint32;
                description "This object indicates the Id for the BGP tunnel LSP.";
            }

            leaf active-lsp-type {
                type enumeration {
                    enum "not-applicable"               { value 0; }
                    enum "rsvp"                         { value 1; }
                    enum "ldp"                          { value 2; }
                    enum "bgp"                          { value 3; }
                    enum "none"                         { value 4; }
                    enum "mpls-tp"                      { value 5; }
                    enum "sr-isis"                      { value 6; }
                    enum "sr-ospf"                      { value 7; }
                    enum "sr-te-lsp"                    { value 8; }
                    enum "fpe"                          { value 9; }
                }
                description "This object indicates the type of LSP that is currently active on this SDP.";
            }

            leaf control-pw-is-active {
                type boolean;
                description
                    "This object indicates whether control pseudo-wire is considered
                     active  on the Backbone Edge Bridge (BEB).";
            }

            leaf fpe-lsp-id {
                type uint32;
                description "Identifier of the forward-path-extension LSP when the SDP is created using 'fpe'.";
            }

            leaf oper-tunnel-far-end-inet-address {
                type types-sros:ip-address;
                description "IP address of the remote end of the transport tunnel for this SDP.";
            }

            container keep-alive {
                description "Enter the keep-alive context";

                leaf oper-state {
                    type enumeration {
                        enum "alive"                        { value 1; }
                        enum "no-response"                  { value 2; }
                        enum "sender-id-invalid"            { value 3; }
                        enum "responder-id-error"           { value 4; }
                        enum "disabled"                     { value 5; }
                    }
                    description "This object indicates the current status of the keep-alive protocol.";
                }

                leaf hello-request-messages {
                    type uint32;
                    description
                        "This object indicates the number of SDP Echo Request messages
                         transmitted since the keep-alive was administratively enabled
                         or the counter was cleared.";
                }

                leaf hello-response-messages {
                    type uint32;
                    description
                        "This object indicates the number of SDP Echo Response messages
                         since the keep-alive was administratively enabled or the
                         counter was cleared.";
                }

                leaf late-hello-response-messages {
                    type uint32;
                    description
                        "This object indicates the number of SDP Echo Response messages
                         received after the corresponding request timeout timer expired.";
                }

            } // container keep-alive

        } // list sdp

    } // grouping state-svc-sdp

}
