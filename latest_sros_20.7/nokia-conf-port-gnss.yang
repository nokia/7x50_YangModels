submodule nokia-conf-port-gnss {

    yang-version "1.1";

    belongs-to nokia-conf { prefix "conf"; }

    import nokia-sros-yang-extensions     { prefix "sros-ext"; }

    include nokia-conf-groups;

    sros-ext:sros-major-release "rel20";

    organization "Nokia";

    contact
        "Nokia SR OS Support
         Web: <http://www.nokia.com>";

    description
        "Nokia YANG Data model to configure Global Navigation Satellite System (GNSS) CPM ports on SR OS based routers.

         Copyright 2016 Nokia. All rights reserved. Reproduction of this document
         is authorized on the condition that the foregoing copyright notice is included.

         This nokia-conf-port-gnss YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";

    revision "2020-05-22";

    grouping conf-port-gnss {
        container gnss {
            description "Enter the gnss context";

            leaf antenna-cable-delay {
                type uint32 {
                    range "0..32767";
                }
                units "nanoseconds";
                default "0";
                description "The expected signal delay resulting from the length of the antenna cable";
            }

            leaf elevation-mask-angle {
                type uint32 {
                    range "0..89";
                }
                units "degrees angle";
                default "10";
                description "The minimum elevation angle below which the GNSS receiver will not use a satellite";
            }

            leaf-list apply-groups {
                type leafref {
                    path "../../../groups/group/name";
                }
                max-elements 8;
                ordered-by user;
                description "Apply a configuration group at this level";
            }

            container constellation {
                description "Enter the constellation context";

                leaf gps {
                    type boolean;
                    default "true";
                    description "Configure the gnss receiver to process the 'gps' constellation type";
                }

                leaf glonass {
                    type boolean;
                    default "false";
                    description "Configure the gnss receiver to process the 'glonass' constellation type";
                }

            } // container constellation

        } // container gnss

    } // grouping conf-port-gnss

}
