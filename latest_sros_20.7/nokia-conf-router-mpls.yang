submodule nokia-conf-router-mpls {

    yang-version "1.1";

    belongs-to nokia-conf { prefix "conf"; }

    import ietf-yang-types                { prefix "yang"; }
    import nokia-sros-yang-extensions     { prefix "sros-ext"; }
    import nokia-types-mpls               { prefix "types-mpls"; }
    import nokia-types-sros               { prefix "types-sros"; }

    include nokia-conf-bfd;
    include nokia-conf-groups;
    include nokia-conf-log;
    include nokia-conf-policy-options;
    include nokia-conf-router;
    include nokia-conf-routing-options;

    sros-ext:sros-major-release "rel20";

    organization "Nokia";

    contact
        "Nokia SR OS Support
         Web: <http://www.nokia.com>";

    description
        "Nokia YANG Data model to configure mpls protocol on SR OS based routers.

         Copyright 2016 Nokia. All rights reserved. Reproduction of this document
         is authorized on the condition that the foregoing copyright notice is included.

         This nokia-conf-router-mpls YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";

    revision "2019-07-08";

    grouping conf-router-mpls {
        container mpls {
            presence "Enter the 'mpls' context";
            description "Enable the mpls context";

            leaf admin-group-frr {
                type boolean;
                default "false";
                description "Use admin group constraints for FRR path computation";
            }

            leaf admin-state {
                type types-sros:admin-state;
                default "disable";
                description "Administrative state of the MPLS instance";
            }

            leaf bypass-resignal-timer {
                type uint32 {
                    range "1..10080";
                }
                units "minutes";
                description "Resignal timer for bypass";
            }

            leaf cspf-on-loose-hop {
                type boolean;
                default "false";
                description "Calculate CSPF until next loose hop on LSR";
            }

            leaf dynamic-bypass {
                type boolean;
                default "true";
                description "Create dynamic bypass LSPs in FRR";
            }

            leaf exponential-backoff-retry {
                type boolean;
                default "false";
                description "Use exponential back-off timer when retrying an LSP";
            }

            leaf frr-object {
                type boolean;
                default "true";
                description "Signal with fast reroute object";
            }

            leaf hold-timer {
                type uint32 {
                    range "0..1000";
                }
                units "seconds";
                default "1";
                description "Hold timer value";
            }

            leaf least-fill-min-thd {
                type types-sros:percent;
                default "5";
                description "Percentage of the least fill minimum threshold value";
            }

            leaf least-fill-reoptim-thd {
                type types-sros:percent;
                default "10";
                description "Percentage of the least fill reoptimization threshold value";
            }

            leaf logger-event-bundling {
                type boolean;
                sros-ext:auto-restart-to-modify;
                default "false";
                description "Merge and bundle MPLS traps";
            }

            leaf lsp-init-retry-timeout {
                type uint32 {
                    range "10..600";
                }
                units "seconds";
                default "30";
                description "LSP initial retry timeout";
            }

            leaf max-bypass-associations {
                type uint32 {
                    range "100..131072";
                }
                default "1000";
                description "Maximum number of LSPs to be associated with a bypass tunnel";
            }

            leaf max-bypass-plr-associations {
                type uint32 {
                    range "1..16";
                }
                default "16";
                description "The maximum number separate dynamic bypass to create for each Point of Local Repair (PLR).";
            }

            leaf mbb-prefer-current-hops {
                type boolean;
                default "false";
                description "Select preference to use the current hops for Make-Before-Break (MBB)";
            }

            leaf p2mp-resignal-timer {
                type uint32 {
                    range "60..10080";
                }
                units "minutes";
                description "Resignal timer for P2MP LSPs";
            }

            leaf p2mp-s2l-fast-retry {
                type uint32 {
                    range "1..10";
                }
                units "seconds";
                description "Fast retry timer for P2MP S2L paths";
            }

            leaf p2p-active-path-fast-retry {
                type uint32 {
                    range "1..10";
                }
                units "seconds";
                description "Fast retry timer for P2P active paths";
            }

            leaf resignal-timer {
                type uint32 {
                    range "30..10080";
                }
                units "minutes";
                description "Resignal timer for RSVP LSPs";
            }

            leaf retry-on-igp-overload {
                type boolean;
                default "false";
                description "Tear down LSPs when IGP is in overload state";
            }

            leaf secondary-fast-retry-timer {
                type uint32 {
                    range "1..10";
                }
                units "seconds";
                description "Fast retry timer for secondary paths";
            }

            leaf shortcut-local-ttl-propagate {
                type boolean;
                default "true";
                description "Propagate TTL over LSP shortcut for local packets";
            }

            leaf shortcut-transit-ttl-propagate {
                type boolean;
                default "true";
                description "Propagate TTL over LSP shortcut for local packets for transit packets";
            }

            leaf srlg-frr {
                type enumeration {
                    enum "loose"                        { value 1; }
                    enum "strict"                       { value 2; }
                }
                description "Use of Shared Risk Link Group (SRLG) constraint for FRR path computation";
            }

            leaf static-lsp-fast-retry {
                type uint32 {
                    range "1..30";
                }
                units "seconds";
                default "30";
                description "Fast retry timer for static LSPs";
            }

            leaf user-srlg-db {
                type boolean;
                default "false";
                description "Enable/disable use of user SRLG database.";
            }

            leaf-list apply-groups {
                type leafref {
                    path "../../../groups/group/name";
                }
                max-elements 8;
                ordered-by user;
                description "Apply a configuration group at this level";
            }

            container lsp-self-ping {
                description "Enter the lsp-self-ping context";

                leaf interval {
                    type uint32 {
                        range "1..10";
                    }
                    default "1";
                    description "MPLS periodic LSP Self Ping interval";
                }

                leaf rsvp-te {
                    type boolean;
                    default "false";
                    description "Activate LSP Self Ping on RSVP-TE LSPs";
                }

                leaf timeout {
                    type uint32 {
                        range "3..3600";
                    }
                    default "300";
                    description "MPLS LSP Self Ping timeout value";
                }

                leaf timeout-action {
                    type enumeration {
                        enum "retry"                        { value 1; }
                        enum "switch"                       { value 2; }
                    }
                    default "retry";
                    description "Configure mpls lsp self ping timeout-action.";
                }

            } // container lsp-self-ping

            container auto-bandwidth-multipliers {
                description "Enter the auto-bandwidth-multipliers context";

                leaf sample-multiplier {
                    type uint32 {
                        range "1..511";
                    }
                    default "1";
                    description "Collection intervals in a sample interval";
                }

                leaf adjust-multiplier {
                    type uint32 {
                        range "1..16383";
                    }
                    default "288";
                    description "Collection intervals in a sample interval";
                }

            } // container auto-bandwidth-multipliers

            container entropy-label {
                description "Enter the entropy-label context";

                leaf rsvp-te {
                    type boolean;
                    description "Apply entropy labels to RSVP-TE LSPs";
                }

                leaf sr-te {
                    type boolean;
                    description "Apply entropy labels to SR-TE LSPs";
                }

            } // container entropy-label

            container pce-report {
                description "Enter the pce-report context";

                leaf sr-te {
                    type boolean;
                    default "false";
                    description "Allow PCE reporting for all TE LSPs of SR-TE type";
                }

                leaf rsvp-te {
                    type boolean;
                    default "false";
                    description "Allow PCE reporting for all TE LSPs of RSVP-TE type";
                }

            } // container pce-report

            container srlg-database {
                description "Enter the srlg-database context";

                list router-id {
                    key "router-address";
                    description "Enter the router-id list instance";

                    leaf router-address {
                        type types-sros:ipv4-address;
                        description "Specifies a unique identifier of the router in the Autonomous System.";
                    }

                    leaf admin-state {
                        type types-sros:admin-state;
                        default "disable";
                        description "Administrative state of the interface";
                    }

                    leaf-list apply-groups {
                        type leafref {
                            path "../../../../../groups/group/name";
                        }
                        max-elements 8;
                        ordered-by user;
                        description "Apply a configuration group at this level";
                    }

                    list interface {
                        key "interface-address srlg-group";
                        description "Add a list entry for interface";

                        leaf interface-address {
                            type types-sros:ipv4-address;
                            description "Indicates the IP address of the interface.";
                        }

                        leaf srlg-group {
                            type leafref {
                                path "../../../../../../routing-options/if-attribute/srlg-group/name";
                            }
                            description "SRLG group name";
                        }

                    } // list interface

                } // list router-id

            } // container srlg-database

            list interface {
                key "interface-name";
                description "Enter the interface list instance";

                leaf interface-name {
                    type leafref {
                        path "../../../interface/interface-name";
                    }
                    description "Router interface name";
                }

                leaf admin-state {
                    type types-sros:admin-state;
                    default "enable";
                    description "Administrative state of MPLS";
                }

                leaf te-metric {
                    type uint32 {
                        range "1..16777215";
                    }
                    description "TE metric for the interface";
                }

                leaf-list admin-group {
                    type leafref {
                        path "../../../../routing-options/if-attribute/admin-group/group-name";
                    }
                    max-elements 32;
                    description "Name of the admin group membership of the MPLS interface";
                }

                leaf-list apply-groups {
                    type leafref {
                        path "../../../../groups/group/name";
                    }
                    max-elements 8;
                    ordered-by user;
                    description "Apply a configuration group at this level";
                }

                list srlg-group {
                    key "name";
                    max-elements 64;
                    description "Add a list entry for srlg-group";

                    leaf name {
                        type leafref {
                            path "../../../../../routing-options/if-attribute/srlg-group/name";
                        }
                        description "Shared Risk Link Group (SRLG) name";
                    }

                } // list srlg-group

                list label-map {
                    key "in-label";
                    description "Enter the label-map list instance";

                    leaf in-label {
                        type types-sros:mpls-label;
                        description "Match the incoming MPLS label";
                    }

                    leaf admin-state {
                        type types-sros:admin-state;
                        sros-ext:auto-restart-to-modify;
                        default "disable";
                        description "Administrative state of the label map";
                    }

                    leaf-list apply-groups {
                        type leafref {
                            path "../../../../../groups/group/name";
                        }
                        max-elements 8;
                        ordered-by user;
                        sros-ext:auto-restart-to-modify;
                        description "Apply a configuration group at this level";
                    }

                    choice label-map-choice {
                        case pop {

                            leaf pop {
                                type empty;
                                sros-ext:immutable;
                                sros-ext:auto-restart-to-modify;
                                description "Pop (remove) the incoming label and forward packet based on service header";
                            }

                        }
                        case swap {

                            container swap {
                                presence "Enter the 'swap' context";
                                sros-ext:auto-restart-to-modify;
                                description "Enable the swap context";

                                leaf out-label {
                                    type union {
                                        type uint32 {
                                            range "16..1048575";
                                        }
                                        type enumeration {
                                            enum "implicit-null-label"          { value 3; }
                                        }
                                    }
                                    sros-ext:auto-restart-to-modify;
                                    mandatory true;
                                    description "Push specific label onto the top of the outgoing packet's label stack";
                                }

                                leaf next-hop {
                                    type types-sros:ipv4-unicast-address;
                                    sros-ext:auto-restart-to-modify;
                                    mandatory true;
                                    description "IP address for the next hop";
                                }

                                leaf-list apply-groups {
                                    type leafref {
                                        path "../../../../../../groups/group/name";
                                    }
                                    max-elements 8;
                                    ordered-by user;
                                    sros-ext:auto-restart-to-modify;
                                    description "Apply a configuration group at this level";
                                }

                            } // container swap

                        }
                    }
                } // list label-map

            } // list interface

            list class-forwarding-policy {
                key "policy-name";
                max-elements 15;
                description "Enter the class-forwarding-policy list instance";

                leaf policy-name {
                    type types-sros:named-item;
                    description "Name of class forwarding policy";
                }

                leaf default-set {
                    type uint32 {
                        range "1..6";
                    }
                    default "1";
                    description "Default forwarding set ID";
                }

                leaf-list apply-groups {
                    type leafref {
                        path "../../../../groups/group/name";
                    }
                    max-elements 8;
                    ordered-by user;
                    description "Apply a configuration group at this level";
                }

                list fc {
                    key "fc-name";
                    description "Enter the fc list instance";

                    leaf fc-name {
                        type types-sros:fc-name;
                        description "Forwarding class name for LSP";
                    }

                    leaf forwarding-set {
                        type uint32 {
                            range "1..6";
                        }
                        default "1";
                        description "Forwarding set ID for forwarding classes";
                    }

                    leaf-list apply-groups {
                        type leafref {
                            path "../../../../../groups/group/name";
                        }
                        max-elements 8;
                        ordered-by user;
                        description "Apply a configuration group at this level";
                    }

                } // list fc

            } // list class-forwarding-policy

            list path {
                key "path-name";
                max-elements 65535;
                description "Enter the path list instance";

                leaf path-name {
                    type types-sros:named-item-64;
                    description "Name for this LSP path";
                }

                leaf admin-state {
                    type types-sros:admin-state;
                    sros-ext:auto-restart-to-modify;
                    default "disable";
                    description "Administrative state of this tunnel";
                }

                leaf-list apply-groups {
                    type leafref {
                        path "../../../../groups/group/name";
                    }
                    max-elements 8;
                    ordered-by user;
                    sros-ext:auto-restart-to-modify;
                    description "Apply a configuration group at this level";
                }

                list hop {
                    key "hop-index";
                    max-elements 255;
                    sros-ext:auto-restart-to-modify;
                    description "Enter the hop list instance";

                    leaf hop-index {
                        type int32 {
                            range "1..1024";
                        }
                        description "Index to identify a particular hop";
                    }

                    leaf-list apply-groups {
                        type leafref {
                            path "../../../../../groups/group/name";
                        }
                        max-elements 8;
                        ordered-by user;
                        sros-ext:auto-restart-to-modify;
                        description "Apply a configuration group at this level";
                    }

                    choice hop-info {
                        mandatory true;
                        case hop-ip-address {

                            leaf ip-address {
                                type types-sros:ip-address;
                                sros-ext:immutable;
                                sros-ext:auto-restart-to-modify;
                                description "IPv4 address of this hop";
                            }

                            leaf type {
                                type enumeration {
                                    enum "strict"                       { value 1; }
                                    enum "loose"                        { value 2; }
                                }
                                sros-ext:auto-restart-to-modify;
                                description "Tunnel hop type";
                            }

                        }
                        case hop-sid {

                            leaf sid-label {
                                type uint32 {
                                    range "32..1048575";
                                }
                                sros-ext:auto-restart-to-modify;
                                description "MPLS label for this tunnel hop";
                            }

                        }
                    }
                } // list hop

            } // list path

            list lsp-template {
                key "template-name";
                max-elements 4096;
                description "Enter the lsp-template list instance";

                leaf template-name {
                    type types-sros:named-item;
                    description "Name of the LSP template to automatically create and signal multiple LSP instances";
                }

                leaf type {
                    type enumeration {
                        enum "p2mp-rsvp"                    { value 1; }
                        enum "p2p-rsvp-one-hop"             { value 2; }
                        enum "p2p-rsvp-mesh"                { value 3; }
                        enum "p2p-sr-te-one-hop"            { value 4; }
                        enum "p2p-sr-te-mesh"               { value 5; }
                        enum "p2p-sr-te-pce-init"           { value 6; }
                    }
                    sros-ext:immutable;
                    sros-ext:auto-restart-to-modify;
                    mandatory true;
                    description "Configure type of the LSP template.";
                }

                leaf admin-state {
                    type types-sros:admin-state;
                    default "disable";
                    description "Administrative state of LSP template";
                }

                leaf backup-class-type {
                    when "not(../type) or ../type = 'p2p-rsvp-one-hop' or ../type = 'p2p-rsvp-mesh'";
                    type types-mpls:class-type;
                    sros-ext:auto-restart-to-modify;
                    default "0";
                    description "Configure backup-class-type for this LSP template.";
                }

                leaf bandwidth {
                    when "not(../type) or ../type = 'p2mp-rsvp' or ../type = 'p2p-rsvp-one-hop' or ../type = 'p2p-rsvp-mesh'";
                    type types-mpls:lsp-bandwidth;
                    default "0";
                    description "Specify bandwidth in mbps for LSP instances created using this LSP template.";
                }

                leaf bgp-shortcut {
                    when "not(../type) or ../type = 'p2p-rsvp-one-hop' or ../type = 'p2p-rsvp-mesh' or ../type = 'p2p-sr-te-one-hop' or ../type = 'p2p-sr-te-mesh' or ../type = 'p2p-sr-te-pce-init'";
                    type boolean;
                    sros-ext:auto-restart-to-modify;
                    description "Enable/disable use of RSVP LSP for IPv4 BGP routes.";
                }

                leaf bgp-transport-tunnel {
                    when "not(../type) or ../type = 'p2p-rsvp-one-hop' or ../type = 'p2p-rsvp-mesh' or ../type = 'p2p-sr-te-one-hop' or ../type = 'p2p-sr-te-mesh' or ../type = 'p2p-sr-te-pce-init'";
                    type boolean;
                    sros-ext:auto-restart-to-modify;
                    default "true";
                    description "Include/exclude use of RSVP LSP as transport LSP for labeled IPv4 BGP routes.";
                }

                leaf default-path {
                    when "not(../type) or ../type = 'p2mp-rsvp' or ../type = 'p2p-rsvp-one-hop' or ../type = 'p2p-rsvp-mesh' or ../type = 'p2p-sr-te-one-hop' or ../type = 'p2p-sr-te-mesh' or ../type = 'p2p-sr-te-pce-init'";
                    type leafref {
                        path "../../path/path-name";
                    }
                    sros-ext:immutable;
                    sros-ext:auto-restart-to-modify;
                    description "Specify default path to be used for signaling LSP instances created using this LSP template.";
                }

                leaf from {
                    when "not(../type) or ../type = 'p2p-rsvp-mesh' or ../type = 'p2p-sr-te-mesh'";
                    type types-sros:ip-address;
                    sros-ext:auto-restart-to-modify;
                    description "IP address of the ingress router for the LSP template.";
                }

                leaf hop-limit {
                    when "not(../type) or ../type = 'p2mp-rsvp' or ../type = 'p2p-rsvp-one-hop' or ../type = 'p2p-rsvp-mesh' or ../type = 'p2p-sr-te-one-hop' or ../type = 'p2p-sr-te-mesh'";
                    type uint16 {
                        range "2..255";
                    }
                    sros-ext:auto-restart-to-modify;
                    description "Configure maximum number of hops that can be traversed by LSP instances created using this LSP template.";
                }

                leaf ldp-over-rsvp {
                    when "not(../type) or ../type = 'p2p-rsvp-one-hop' or ../type = 'p2p-rsvp-mesh'";
                    type boolean;
                    sros-ext:auto-restart-to-modify;
                    default "true";
                    description "Configure if this LSP will be included in LDP over RSVP.";
                }

                leaf metric {
                    when "not(../type) or ../type = 'p2p-rsvp-one-hop' or ../type = 'p2p-rsvp-mesh' or ../type = 'p2p-sr-te-one-hop' or ../type = 'p2p-sr-te-mesh' or ../type = 'p2p-sr-te-pce-init'";
                    type uint32 {
                        range "0..16777215";
                    }
                    sros-ext:auto-restart-to-modify;
                    default "0";
                    description "Configure LSP template metric.";
                }

                leaf vprn-auto-bind {
                    when "not(../type) or ../type = 'p2p-rsvp-one-hop' or ../type = 'p2p-rsvp-mesh' or ../type = 'p2p-sr-te-one-hop' or ../type = 'p2p-sr-te-mesh' or ../type = 'p2p-sr-te-pce-init'";
                    type boolean;
                    sros-ext:auto-restart-to-modify;
                    default "true";
                    description "Configure if this LSP will be included in auto-bind for VPRN services.";
                }

                leaf pce-report {
                    when "not(../type) or ../type = 'p2p-rsvp-one-hop' or ../type = 'p2p-rsvp-mesh' or ../type = 'p2p-sr-te-one-hop' or ../type = 'p2p-sr-te-mesh' or ../type = 'p2p-sr-te-pce-init'";
                    type types-sros:bool-with-inherit;
                    sros-ext:auto-restart-to-modify;
                    description "Specifies whether to override the global configuration of reporting to PCE.";
                }

                leaf entropy-label {
                    when "not(../type) or ../type = 'p2p-rsvp-one-hop' or ../type = 'p2p-rsvp-mesh' or ../type = 'p2p-sr-te-one-hop' or ../type = 'p2p-sr-te-mesh' or ../type = 'p2p-sr-te-pce-init'";
                    type types-sros:bool-with-inherit;
                    sros-ext:auto-restart-to-modify;
                    description "Configure Entropy Label for LSP Template.";
                }

                leaf adaptive {
                    when "not(../type) or ../type = 'p2mp-rsvp' or ../type = 'p2p-rsvp-one-hop' or ../type = 'p2p-rsvp-mesh'";
                    type boolean;
                    sros-ext:auto-restart-to-modify;
                    default "true";
                    description "Enable/disable make-before-break functionality.";
                }

                leaf adspec {
                    when "not(../type) or ../type = 'p2p-rsvp-one-hop' or ../type = 'p2p-rsvp-mesh'";
                    type boolean;
                    sros-ext:auto-restart-to-modify;
                    default "false";
                    description "Enable/disable inclusion of ADSPEC objects in RSVP messages.";
                }

                leaf class-type {
                    when "not(../type) or ../type = 'p2p-rsvp-one-hop' or ../type = 'p2p-rsvp-mesh'";
                    type types-mpls:class-type;
                    sros-ext:auto-restart-to-modify;
                    default "0";
                    description "Configure class-type.";
                }

                leaf least-fill {
                    when "not(../type) or ../type = 'p2p-rsvp-one-hop' or ../type = 'p2p-rsvp-mesh'";
                    type boolean;
                    sros-ext:auto-restart-to-modify;
                    default "false";
                    description "Configure use of least-fill path selection method.";
                }

                leaf load-balancing-weight {
                    when "not(../type) or ../type = 'p2p-rsvp-one-hop' or ../type = 'p2p-rsvp-mesh' or ../type = 'p2p-sr-te-one-hop' or ../type = 'p2p-sr-te-mesh' or ../type = 'p2p-sr-te-pce-init'";
                    type uint32 {
                        range "1..max";
                    }
                    sros-ext:auto-restart-to-modify;
                    description "Configure load balancing weight.";
                }

                leaf main-ct-retry-limit {
                    when "not(../type) or ../type = 'p2p-rsvp-one-hop' or ../type = 'p2p-rsvp-mesh'";
                    type uint32 {
                        range "1..10000";
                    }
                    sros-ext:auto-restart-to-modify;
                    description "Max number of attempts before switching to backup class type.";
                }

                leaf propagate-admin-group {
                    when "not(../type) or ../type = 'p2mp-rsvp' or ../type = 'p2p-rsvp-one-hop' or ../type = 'p2p-rsvp-mesh'";
                    type boolean;
                    sros-ext:auto-restart-to-modify;
                    default "false";
                    description "Enable/disable admin groups via session attribute object.";
                }

                leaf retry-limit {
                    when "not(../type) or ../type = 'p2mp-rsvp' or ../type = 'p2p-rsvp-one-hop' or ../type = 'p2p-rsvp-mesh' or ../type = 'p2p-sr-te-one-hop' or ../type = 'p2p-sr-te-mesh'";
                    type uint32 {
                        range "1..10000";
                    }
                    sros-ext:auto-restart-to-modify;
                    description "Max number of attempts made to reestablish the LSP after it has failed.";
                }

                leaf retry-timer {
                    when "not(../type) or ../type = 'p2mp-rsvp' or ../type = 'p2p-rsvp-one-hop' or ../type = 'p2p-rsvp-mesh' or ../type = 'p2p-sr-te-one-hop' or ../type = 'p2p-sr-te-mesh'";
                    type uint32 {
                        range "1..600";
                    }
                    units "seconds";
                    sros-ext:auto-restart-to-modify;
                    default "30";
                    description "Time between attempts to reestablish the LSP after it has failed.";
                }

                leaf record {
                    when "not(../type) or ../type = 'p2mp-rsvp' or ../type = 'p2p-rsvp-one-hop' or ../type = 'p2p-rsvp-mesh'";
                    type boolean;
                    sros-ext:auto-restart-to-modify;
                    default "true";
                    description "Enable/disable recording of all hops.";
                }

                leaf record-label {
                    when "not(../type) or ../type = 'p2mp-rsvp' or ../type = 'p2p-rsvp-one-hop' or ../type = 'p2p-rsvp-mesh'";
                    type boolean;
                    sros-ext:auto-restart-to-modify;
                    default "true";
                    description "Enable/disable recording of labels at each node or instance.";
                }

                leaf template-id {
                    when "not(../type) or ../type = 'p2p-sr-te-pce-init'";
                    type union {
                        type uint32 {
                            range "1..max";
                        }
                        type enumeration {
                            enum "default"                      { value 0; }
                        }
                    }
                    sros-ext:immutable;
                    sros-ext:auto-restart-to-modify;
                    description "The value indicates lsp template-id. Configure this if LSP Template is of type p2p-sr-te-pce-init.";
                }

                leaf path-computation-method {
                    when "not(../type) or ../type = 'p2mp-rsvp' or ../type = 'p2p-rsvp-one-hop' or ../type = 'p2p-rsvp-mesh' or ../type = 'p2p-sr-te-one-hop' or ../type = 'p2p-sr-te-mesh'";
                    type enumeration {
                        enum "local-cspf"                   { value 2; }
                    }
                    sros-ext:auto-restart-to-modify;
                    description "Configure path computation method";
                }

                leaf family {
                    when "not(../type) or ../type = 'p2p-sr-te-one-hop' or ../type = 'p2p-sr-te-mesh'";
                    type enumeration {
                        enum "ipv4"                         { value 1; }
                        enum "ipv6"                         { value 2; }
                    }
                    sros-ext:auto-restart-to-modify;
                    default "ipv4";
                    description "Address family that specifies template use in SR-TE LSP";
                }

                leaf metric-type {
                    when "not(../type) or ../type = 'p2mp-rsvp' or ../type = 'p2p-rsvp-one-hop' or ../type = 'p2p-rsvp-mesh' or ../type = 'p2p-sr-te-one-hop' or ../type = 'p2p-sr-te-mesh'";
                    type enumeration {
                        enum "igp"                          { value 1; }
                        enum "te"                           { value 2; }
                    }
                    sros-ext:auto-restart-to-modify;
                    default "igp";
                    description "Configure metric type used for LSP path computation.";
                }

                leaf local-sr-protection {
                    when "not(../type) or ../type = 'p2p-sr-te-one-hop' or ../type = 'p2p-sr-te-mesh'";
                    type enumeration {
                        enum "none"                         { value 1; }
                        enum "preferred"                    { value 2; }
                        enum "mandatory"                    { value 3; }
                    }
                    sros-ext:auto-restart-to-modify;
                    default "preferred";
                    description "Configure local SR protection preference for LSP path computation.";
                }

                leaf label-stack-reduction {
                    when "not(../type) or ../type = 'p2p-sr-te-one-hop' or ../type = 'p2p-sr-te-mesh'";
                    type boolean;
                    sros-ext:auto-restart-to-modify;
                    default "false";
                    description "Enable/disable label compression for LSP path.";
                }

                leaf lsp-self-ping {
                    when "not(../type) or ../type = 'p2p-rsvp-one-hop' or ../type = 'p2p-rsvp-mesh'";
                    type types-sros:bool-with-inherit;
                    sros-ext:auto-restart-to-modify;
                    description "LSP Self Ping activation status on RSVP-TE LSP template";
                }

                leaf-list include-admin-group {
                    when "not(../type) or ../type = 'p2mp-rsvp' or ../type = 'p2p-rsvp-one-hop' or ../type = 'p2p-rsvp-mesh' or ../type = 'p2p-sr-te-one-hop' or ../type = 'p2p-sr-te-mesh'";
                    type leafref {
                        path "../../../../routing-options/if-attribute/admin-group/group-name";
                    }
                    max-elements 32;
                    sros-ext:auto-restart-to-modify;
                    description "Admin group name included when LSP is set up";
                }

                leaf-list exclude-admin-group {
                    when "not(../type) or ../type = 'p2mp-rsvp' or ../type = 'p2p-rsvp-one-hop' or ../type = 'p2p-rsvp-mesh' or ../type = 'p2p-sr-te-one-hop' or ../type = 'p2p-sr-te-mesh'";
                    type leafref {
                        path "../../../../routing-options/if-attribute/admin-group/group-name";
                    }
                    max-elements 32;
                    sros-ext:auto-restart-to-modify;
                    description "Admin group name excluded when LSP is set up";
                }

                leaf-list apply-groups {
                    type leafref {
                        path "../../../../groups/group/name";
                    }
                    max-elements 8;
                    ordered-by user;
                    sros-ext:auto-restart-to-modify;
                    description "Apply a configuration group at this level";
                }

                container class-forwarding {
                    when "not(../type) or ../type = 'p2p-rsvp-one-hop' or ../type = 'p2p-rsvp-mesh' or ../type = 'p2p-sr-te-one-hop' or ../type = 'p2p-sr-te-mesh' or ../type = 'p2p-sr-te-pce-init'";
                    presence "Enter the 'class-forwarding' context";
                    sros-ext:auto-restart-to-modify;
                    description "Enable the class-forwarding context";

                    choice cbf-choice {
                        default "default-lsp-and-fc";
                        case default-lsp-and-fc {

                            leaf default-lsp {
                                status obsolete;
                                type boolean;
                                sros-ext:auto-restart-to-modify;
                                default "false";
                                description "Use the default LSP configuration for specified LSP or LSP template";
                            }

                            leaf-list fc {
                                status obsolete;
                                type enumeration {
                                    enum "be"                           { value 0; }
                                    enum "l2"                           { value 1; }
                                    enum "af"                           { value 2; }
                                    enum "l1"                           { value 3; }
                                    enum "h2"                           { value 4; }
                                    enum "ef"                           { value 5; }
                                    enum "h1"                           { value 6; }
                                    enum "nc"                           { value 7; }
                                }
                                max-elements 8;
                                sros-ext:auto-restart-to-modify;
                                description "One or more forwarding classes for LSP instances";
                            }

                        }
                        case forwarding-set {

                            container forwarding-set {
                                sros-ext:auto-restart-to-modify;
                                description "Enter the forwarding-set context";

                                leaf policy {
                                    type leafref {
                                        path "../../../../class-forwarding-policy/policy-name";
                                    }
                                    sros-ext:auto-restart-to-modify;
                                    description "Name for the class based forwarding policy for LSP instances";
                                }

                                leaf set {
                                    type uint32 {
                                        range "1..6";
                                    }
                                    sros-ext:auto-restart-to-modify;
                                    description "Forwarding set ID";
                                }

                            } // container forwarding-set

                        }
                    }
                } // container class-forwarding

                container cspf {
                    status obsolete;
                    when "not(../type) or ../type = 'p2mp-rsvp' or ../type = 'p2p-rsvp-one-hop' or ../type = 'p2p-rsvp-mesh' or ../type = 'p2p-sr-te-one-hop' or ../type = 'p2p-sr-te-mesh' or ../type = 'p2p-sr-te-pce-init'";
                    sros-ext:auto-restart-to-modify;
                    description "Enter the cspf context";

                    leaf admin-state {
                        status obsolete;
                        type types-sros:admin-state;
                        sros-ext:auto-restart-to-modify;
                        default "disable";
                        description "Administrative state of the CSPF support for LSP";
                    }

                    leaf use-te-metric {
                        status obsolete;
                        when "not(../../type = 'p2p-sr-te-pce-init')";
                        type boolean;
                        sros-ext:auto-restart-to-modify;
                        default "false";
                        description "TE metric for the LSP path computation by CSPF";
                    }

                } // container cspf

                container priority {
                    when "not(../type) or ../type = 'p2p-rsvp-one-hop' or ../type = 'p2p-rsvp-mesh'";
                    sros-ext:auto-restart-to-modify;
                    description "Enter the priority context";

                    leaf setup-priority {
                        type types-mpls:priority;
                        sros-ext:auto-restart-to-modify;
                        default "7";
                        description "Setup priority when insufficient bandwidth is available to set up LSP";
                    }

                    leaf hold-priority {
                        type types-mpls:priority;
                        sros-ext:auto-restart-to-modify;
                        default "0";
                        description "Hold priority when insufficient bandwidth is available to set up LSP";
                    }

                } // container priority

                container fast-reroute {
                    when "not(../type) or ../type = 'p2mp-rsvp' or ../type = 'p2p-rsvp-one-hop' or ../type = 'p2p-rsvp-mesh'";
                    presence "Enter the 'fast-reroute' context";
                    sros-ext:auto-restart-to-modify;
                    description "Enable the fast-reroute context";

                    leaf hop-limit {
                        type uint32 {
                            range "0..255";
                        }
                        default "16";
                        description "Total number of hops a detour or backup LSP can take before merging back onto the main LSP path";
                    }

                    leaf propagate-admin-group {
                        type boolean;
                        default "false";
                        description "Enable signaling of the primary LSP path admin-group constraints in the FRR object at ingress";
                    }

                    leaf frr-method {
                        type types-mpls:frr-method-type;
                        sros-ext:auto-restart-to-modify;
                        default "facility";
                        description "Fast Reroute method for the LSPs that are dynamically created using this LSP template";
                    }

                    leaf node-protect {
                        type boolean;
                        default "false";
                        description "Enable node and link protection for the specified LSP";
                    }

                } // container fast-reroute

                container igp-shortcut {
                    when "not(../type) or ../type = 'p2p-rsvp-one-hop' or ../type = 'p2p-rsvp-mesh' or ../type = 'p2p-sr-te-one-hop' or ../type = 'p2p-sr-te-mesh' or ../type = 'p2p-sr-te-pce-init'";
                    sros-ext:auto-restart-to-modify;
                    description "Enter the igp-shortcut context";

                    leaf admin-state {
                        type types-sros:admin-state;
                        sros-ext:auto-restart-to-modify;
                        default "enable";
                        description "Administrative state of the RSVP LSP to be used as a shortcut while resolving IGP routes";
                    }

                    choice igp-choice {
                        case lfa-type {

                            leaf lfa-type {
                                type enumeration {
                                    enum "lfa-protect"                  { value 1; }
                                    enum "lfa-only"                     { value 2; }
                                }
                                sros-ext:auto-restart-to-modify;
                                description "Specific RSVP LSP by IS-IS and OSPF routing protocols to assign as shortcut or as forwarding adjacency";
                            }

                        }
                        case relative-metric {

                            leaf relative-metric {
                                type int32 {
                                    range "-10..10";
                                }
                                sros-ext:auto-restart-to-modify;
                                description "Shortest IGP cost between the endpoints of the LSP plus the configured offset";
                            }

                        }
                    }
                } // container igp-shortcut

                container max-sr-labels {
                    when "not(../type) or ../type = 'p2p-sr-te-mesh' or ../type = 'p2p-sr-te-one-hop' or ../type = 'p2p-sr-te-pce-init'";
                    sros-ext:auto-restart-to-modify;
                    description "Enter the max-sr-labels context";

                    leaf label-stack-size {
                        type uint32 {
                            range "1..11";
                        }
                        sros-ext:auto-restart-to-modify;
                        description "Size for the maximum segment routing label stack";
                    }

                    leaf additional-frr-labels {
                        type uint32 {
                            range "0..4";
                        }
                        sros-ext:auto-restart-to-modify;
                        default "1";
                        description "Maximum number of additional overhead labels";
                    }

                } // container max-sr-labels

                list admin-tag {
                    when "not(../type) or ../type = 'p2p-sr-te-mesh' or ../type = 'p2p-sr-te-one-hop' or ../type = 'p2p-rsvp-mesh' or ../type = 'p2p-rsvp-one-hop' or ../type = 'p2p-sr-te-pce-init'";
                    key "name";
                    max-elements 4;
                    sros-ext:auto-restart-to-modify;
                    description "Add a list entry for admin-tag";

                    leaf name {
                        type leafref {
                            path "../../../../../routing-options/admin-tags/admin-tag/tag";
                        }
                        description "Name of the admin tags";
                    }

                } // list admin-tag

                container auto-bandwidth {
                    when "not(../type) or ../type = 'p2p-rsvp-mesh' or ../type = 'p2p-rsvp-one-hop'";
                    presence "Enter the 'auto-bandwidth' context";
                    sros-ext:auto-restart-to-modify;
                    description "Enable the auto-bandwidth context";

                    leaf max-bandwidth {
                        type types-mpls:lsp-bandwidth;
                        sros-ext:auto-restart-to-modify;
                        default "100000";
                        description "Maximum bandwidth of auto-bandwidth to request for the LSP";
                    }

                    leaf min-bandwidth {
                        type types-mpls:lsp-bandwidth;
                        sros-ext:auto-restart-to-modify;
                        default "0";
                        description "Minimum bandwidth of auto-bandwidth to request for the LSP";
                    }

                    leaf monitor-bandwidth {
                        type boolean;
                        sros-ext:auto-restart-to-modify;
                        default "false";
                        description "Collect and display auto-bandwidth measurements for the LSP";
                    }

                    leaf-list apply-groups {
                        type leafref {
                            path "../../../../../groups/group/name";
                        }
                        max-elements 8;
                        ordered-by user;
                        sros-ext:auto-restart-to-modify;
                        description "Apply a configuration group at this level";
                    }

                    list fc {
                        key "fc-name";
                        max-elements 8;
                        sros-ext:auto-restart-to-modify;
                        description "Enter the fc list instance";

                        leaf fc-name {
                            type types-sros:fc-name;
                            description "Forwarding class name for LSP";
                        }

                        leaf sampling-weight {
                            type types-sros:percent;
                            sros-ext:auto-restart-to-modify;
                            default "100";
                            description "Forwarding class weight for LSP";
                        }

                        leaf-list apply-groups {
                            type leafref {
                                path "../../../../../../groups/group/name";
                            }
                            max-elements 8;
                            ordered-by user;
                            sros-ext:auto-restart-to-modify;
                            description "Apply a configuration group at this level";
                        }

                    } // list fc

                    container adjust-down {
                        sros-ext:auto-restart-to-modify;
                        description "Enter the adjust-down context";

                        leaf percent {
                            type types-sros:percent;
                            sros-ext:auto-restart-to-modify;
                            default "5";
                            description "Minimum difference in percent between LSP bandwidth reservation and the maximum average data rate";
                        }

                        leaf bw {
                            type types-mpls:lsp-bandwidth;
                            sros-ext:auto-restart-to-modify;
                            default "0";
                            description "Minimum difference in absolute bandwidth between LSP bandwidth reservation and max average data rate";
                        }

                    } // container adjust-down

                    container adjust-up {
                        sros-ext:auto-restart-to-modify;
                        description "Enter the adjust-up context";

                        leaf percent {
                            type types-sros:percent;
                            sros-ext:auto-restart-to-modify;
                            default "5";
                            description "Minimum difference in percent between LSP bandwidth reservation and the maximum average data rate";
                        }

                        leaf bw {
                            type types-mpls:lsp-bandwidth;
                            sros-ext:auto-restart-to-modify;
                            default "0";
                            description "Minimum difference in absolute bandwidth between LSP bandwidth reservation and max average data rate";
                        }

                    } // container adjust-up

                    container multipliers {
                        sros-ext:auto-restart-to-modify;
                        description "Enter the multipliers context";

                        leaf sample-multiplier {
                            type uint32 {
                                range "1..511";
                            }
                            sros-ext:auto-restart-to-modify;
                            description "Multiplier for collection intervals in a sample interval";
                        }

                        leaf adjust-multiplier {
                            type uint32 {
                                range "1..16383";
                            }
                            sros-ext:auto-restart-to-modify;
                            description "Number of collection intervals in the adjust interval";
                        }

                    } // container multipliers

                    container overflow-limit {
                        presence "Enter the 'overflow-limit' context";
                        sros-ext:auto-restart-to-modify;
                        description "Enable the overflow-limit context";

                        leaf threshold {
                            type types-sros:percent;
                            sros-ext:auto-restart-to-modify;
                            default "0";
                            description "Minimum difference in percent between the LSP bandwidth and the sampled data rate";
                        }

                        leaf bw {
                            type types-mpls:lsp-bandwidth {
                                range "1..6400000";
                            }
                            sros-ext:auto-restart-to-modify;
                            description "Minimum difference in absolute bandwidth between the LSP bandwidth and the sampled data rate";
                        }

                        leaf number {
                            type uint32 {
                                range "1..10";
                            }
                            sros-ext:auto-restart-to-modify;
                            mandatory true;
                            description "Number of overflow samples to trigger an overflow auto-bandwidth adjustment attempt";
                        }

                    } // container overflow-limit

                    container underflow-limit {
                        presence "Enter the 'underflow-limit' context";
                        sros-ext:auto-restart-to-modify;
                        description "Enable the underflow-limit context";

                        leaf threshold {
                            type types-sros:percent;
                            sros-ext:auto-restart-to-modify;
                            default "0";
                            description "Minimum difference in percent between the LSP bandwidth and the sampled data rate";
                        }

                        leaf bw {
                            type types-mpls:lsp-bandwidth {
                                range "1..6400000";
                            }
                            sros-ext:auto-restart-to-modify;
                            description "Minimum difference in absolute bandwidth between the LSP bandwidth and the sampled data rate";
                        }

                        leaf number {
                            type uint32 {
                                range "1..10";
                            }
                            sros-ext:auto-restart-to-modify;
                            mandatory true;
                            description "Number of overflow samples to trigger an overflow auto-bandwidth adjustment attempt";
                        }

                    } // container underflow-limit

                } // container auto-bandwidth

                container egress-statistics {
                    when "not(../type) or ../type = 'p2mp-rsvp' or ../type = 'p2p-rsvp-one-hop' or ../type = 'p2p-rsvp-mesh' or ../type = 'p2p-sr-te-mesh' or ../type = 'p2p-sr-te-one-hop' or ../type = 'p2p-sr-te-pce-init'";
                    presence "Enter the 'egress-statistics' context";
                    sros-ext:auto-restart-to-modify;
                    description "Enable the egress-statistics context";

                    leaf collect-stats {
                        when "not(../../type) or ../../type = 'p2mp-rsvp' or ../../type = 'p2p-rsvp-one-hop' or ../../type = 'p2p-rsvp-mesh'";
                        type boolean;
                        sros-ext:auto-restart-to-modify;
                        default "false";
                        description "Collect statistics";
                    }

                    leaf accounting-policy {
                        when "not(../../type) or ../../type = 'p2mp-rsvp' or ../../type = 'p2p-rsvp-one-hop' or ../../type = 'p2p-rsvp-mesh'";
                        type leafref {
                            path "../../../../../log/accounting-policy/policy-id";
                        }
                        sros-ext:auto-restart-to-modify;
                        description "Accounting policy ID";
                    }

                } // container egress-statistics

                container bfd {
                    when "not(../type) or ../type = 'p2p-rsvp-one-hop' or ../type = 'p2p-rsvp-mesh' or ../type = 'p2p-sr-te-mesh' or ../type = 'p2p-sr-te-one-hop' or ../type = 'p2p-sr-te-pce-init'";
                    sros-ext:auto-restart-to-modify;
                    description "Enter the bfd context";

                    leaf bfd-liveness {
                        type boolean;
                        default "false";
                        description "Enable BFD on the RSVP LSP or S-BFD on the SR-TE LSP";
                    }

                    leaf bfd-template {
                        type leafref {
                            path "../../../../../bfd/bfd-template/name";
                        }
                        description "BFD template";
                    }

                    leaf lsp-ping-interval {
                        when "not(../../type) or ../../type = 'p2p-rsvp-one-hop' or ../../type = 'p2p-rsvp-mesh'";
                        type union {
                            type uint32 {
                                range "60..300";
                            }
                            type enumeration {
                                enum "none"                         { value 0; }
                            }
                        }
                        units "seconds";
                        default "60";
                        description "Interval for periodic LSP ping for BFD bootstrapping";
                    }

                    leaf failure-action {
                        type enumeration {
                            enum "none"                         { value 0; }
                            enum "down"                         { value 1; }
                            enum "failover-or-down"             { value 2; }
                        }
                        default "none";
                        description "Indicates the action to be taken when LSP BFD session fails";
                    }

                    leaf wait-for-up-timer {
                        when "not(../../type) or ../../type = 'p2p-sr-te-one-hop' or ../../type = 'p2p-sr-te-mesh' or ../../type = 'p2p-sr-te-pce-init'";
                        type uint32 {
                            range "1..60";
                        }
                        units "seconds";
                        sros-ext:auto-restart-to-modify;
                        default "4";
                        description "Time to wait for BFD to become operationally available";
                    }

                } // container bfd

            } // list lsp-template

            list lsp {
                key "lsp-name";
                description "Enter the lsp list instance";

                leaf lsp-name {
                    type types-sros:named-item-64;
                    description "Labeled Switch path name";
                }

                leaf type {
                    type enumeration {
                        enum "p2p-rsvp"                     { value 2; }
                        enum "p2p-static-mpls"              { value 3; }
                        enum "p2p-rsvp-bypass"              { value 4; }
                        enum "p2mp-rsvp"                    { value 5; }
                        enum "p2mp-rsvp-auto"               { value 6; }
                        enum "p2p-rsvp-mesh"                { value 8; }
                        enum "p2p-rsvp-one-hop"             { value 9; }
                        enum "p2p-sr-te"                    { value 10; }
                        enum "p2p-sr-te-mesh"               { value 11; }
                        enum "p2p-sr-te-one-hop"            { value 12; }
                        enum "p2p-sr-te-pce-init"           { value 13; }
                    }
                    sros-ext:immutable;
                    mandatory true;
                    description "LSP for bypass protection, point to multipoint, segment routing or MPLS-TP static LSP";
                }

                leaf admin-state {
                    type types-sros:admin-state;
                    default "disable";
                    description "Administrative state of the LSP";
                }

                leaf exclude-node {
                    when "not(../type) or ../type = 'p2p-rsvp-bypass'";
                    type types-sros:ip-address;
                    description "Exclude Routers object to be included in the bypass path message";
                }

                leaf from {
                    when "not(../type) or ../type = 'p2p-rsvp' or ../type = 'p2p-rsvp-bypass' or ../type = 'p2mp-rsvp' or ../type = 'p2p-sr-te'";
                    type types-sros:ip-address;
                    sros-ext:auto-restart-to-modify;
                    description "Source IP address of this LSP";
                }

                leaf to {
                    when "not(../type) or ../type = 'p2p-rsvp' or ../type = 'p2p-rsvp-bypass' or ../type = 'p2p-sr-te'";
                    type types-sros:ip-address;
                    sros-ext:auto-restart-to-modify;
                    description "Destination IP address or the egress router for the LSP";
                }

                leaf hop-limit {
                    when "not(../type) or ../type = 'p2p-rsvp' or ../type = 'p2p-rsvp-bypass' or ../type = 'p2mp-rsvp' or ../type = 'p2p-sr-te'";
                    type uint32 {
                        range "2..255";
                    }
                    default "255";
                    description "Maximum number of hops that an LSP can traverse including ingress and egress routers";
                }

                leaf p2mp-id {
                    when "not(../type) or ../type = 'p2mp-rsvp'";
                    type uint32 {
                        range "1..65535";
                    }
                    description "Unique identifier as Point-to-Multipoint (P2MP) identifier";
                }

                leaf pce-control {
                    when "not(../type) or ../type = 'p2p-rsvp' or ../type = 'p2p-sr-te'";
                    type boolean;
                    default "false";
                    description "Control of path (delegation) to Path Computation Engine (PCE) to be used";
                }

                leaf revert-timer {
                    when "not(../type) or ../type = 'p2p-rsvp' or ../type = 'p2p-sr-te'";
                    type uint32 {
                        range "1..4320";
                    }
                    units "minutes";
                    description "Revert timer for this LSP";
                }

                leaf rsvp-resv-style {
                    when "not(../type) or ../type = 'p2p-rsvp' or ../type = 'p2p-rsvp-bypass' or ../type = 'p2mp-rsvp'";
                    type enumeration {
                        enum "se"                           { value 1; }
                        enum "ff"                           { value 2; }
                    }
                    default "se";
                    description "Reservation style for RSVP";
                }

                leaf bgp-shortcut {
                    when "not(../type) or ../type = 'p2p-rsvp' or ../type = 'p2p-sr-te'";
                    type boolean;
                    description "Include LSP for BGP routes";
                }

                leaf bgp-transport-tunnel {
                    when "not(../type) or ../type = 'p2p-rsvp' or ../type = 'p2p-sr-te'";
                    type boolean;
                    description "Include LSP as transport LSP for labeled BGP routes";
                }

                leaf ldp-over-rsvp {
                    when "not(../type) or ../type = 'p2p-rsvp'";
                    type boolean;
                    description "Include this LSP in LDP over RSVP";
                }

                leaf metric {
                    when "not(../type) or ../type = 'p2p-rsvp' or ../type = 'p2p-sr-te'";
                    type uint32 {
                        range "0..16777215";
                    }
                    description "LSP metric that forces to a constant value";
                }

                leaf vprn-auto-bind {
                    when "not(../type) or ../type = 'p2p-rsvp' or ../type = 'p2p-sr-te'";
                    type boolean;
                    description "Include this LSP in auto-bind for VPRN services";
                }

                leaf pce-report {
                    when "not(../type) or ../type = 'p2p-rsvp' or ../type = 'p2p-sr-te'";
                    type types-sros:bool-with-inherit;
                    description "Global configuration of reporting to PCE to override";
                }

                leaf entropy-label {
                    when "not(../type) or ../type = 'p2p-rsvp' or ../type = 'p2p-sr-te'";
                    type types-sros:bool-with-inherit;
                    description "Entropy label";
                }

                leaf adaptive {
                    when "not(../type) or ../type = 'p2p-rsvp' or ../type = 'p2p-rsvp-bypass' or ../type = 'p2mp-rsvp'";
                    type boolean;
                    default "true";
                    description "Enable/disable make-before-break functionality.";
                }

                leaf adspec {
                    when "not(../type) or ../type = 'p2p-rsvp' or ../type = 'p2p-rsvp-bypass'";
                    type boolean;
                    default "false";
                    description "Enable/disable inclusion of ADSPEC object in RSVP messages.";
                }

                leaf class-type {
                    when "not(../type) or ../type = 'p2p-rsvp'";
                    type types-mpls:class-type;
                    default "0";
                    description "Configure class type.";
                }

                leaf least-fill {
                    when "not(../type) or ../type = 'p2p-rsvp'";
                    type boolean;
                    default "false";
                    description "Configure use of least-fill path selection method.";
                }

                leaf load-balancing-weight {
                    when "not(../type) or ../type = 'p2p-rsvp' or ../type = 'p2p-sr-te'";
                    type uint32 {
                        range "1..max";
                    }
                    description "Configure load balancing weight.";
                }

                leaf main-ct-retry-limit {
                    when "not(../type) or ../type = 'p2p-rsvp'";
                    type uint32 {
                        range "1..10000";
                    }
                    description "Max number of attempts before switching to backup class type.";
                }

                leaf propagate-admin-group {
                    when "not(../type) or ../type = 'p2p-rsvp' or ../type = 'p2p-rsvp-bypass' or ../type = 'p2mp-rsvp'";
                    type boolean;
                    default "false";
                    description "Enable/disable admin groups via session attribute object.";
                }

                leaf retry-limit {
                    when "not(../type) or ../type = 'p2p-rsvp' or ../type = 'p2p-rsvp-bypass' or ../type = 'p2mp-rsvp' or ../type = 'p2p-sr-te'";
                    type uint32 {
                        range "1..10000";
                    }
                    description "Max number of attempts made to reestablish the LSP after it has failed.";
                }

                leaf retry-timer {
                    when "not(../type) or ../type = 'p2p-rsvp' or ../type = 'p2p-rsvp-bypass' or ../type = 'p2mp-rsvp' or ../type = 'p2p-sr-te'";
                    type uint32 {
                        range "1..600";
                    }
                    units "seconds";
                    default "30";
                    description "Time between attempts to reestablish the LSP after it has failed.";
                }

                leaf path-computation-method {
                    when "not(../type) or ../type = 'p2p-rsvp' or ../type = 'p2p-rsvp-bypass' or ../type = 'p2mp-rsvp' or ../type = 'p2p-sr-te'";
                    type enumeration {
                        enum "local-cspf"                   { value 2; }
                        enum "pce"                          { value 3; }
                    }
                    description "Configure path computation method";
                }

                leaf metric-type {
                    when "not(../type) or ../type = 'p2p-rsvp' or ../type = 'p2p-rsvp-bypass' or ../type = 'p2mp-rsvp' or ../type = 'p2p-sr-te'";
                    type enumeration {
                        enum "igp"                          { value 1; }
                        enum "te"                           { value 2; }
                    }
                    default "igp";
                    description "Configure metric type used for LSP path computation.";
                }

                leaf local-sr-protection {
                    when "not(../type) or ../type = 'p2p-sr-te'";
                    type enumeration {
                        enum "none"                         { value 1; }
                        enum "preferred"                    { value 2; }
                        enum "mandatory"                    { value 3; }
                    }
                    default "preferred";
                    description "Configure local SR protection preference for LSP path computation.";
                }

                leaf label-stack-reduction {
                    when "not(../type) or ../type = 'p2p-sr-te'";
                    type boolean;
                    default "false";
                    description "Enable/disable label compression for LSP path.";
                }

                leaf lsp-self-ping {
                    when "not(../type) or ../type = 'p2p-rsvp'";
                    type types-sros:bool-with-inherit;
                    description "LSP Self Ping activation status on the RSVP-TE LSP";
                }

                leaf-list include-admin-group {
                    when "not(../type) or ../type = 'p2p-rsvp' or ../type = 'p2p-rsvp-bypass' or ../type = 'p2mp-rsvp' or ../type = 'p2p-sr-te'";
                    type leafref {
                        path "../../../../routing-options/if-attribute/admin-group/group-name";
                    }
                    max-elements 32;
                    description "Admin group name included when LSP is set up";
                }

                leaf-list exclude-admin-group {
                    when "not(../type) or ../type = 'p2p-rsvp' or ../type = 'p2p-rsvp-bypass' or ../type = 'p2mp-rsvp' or ../type = 'p2p-sr-te'";
                    type leafref {
                        path "../../../../routing-options/if-attribute/admin-group/group-name";
                    }
                    max-elements 32;
                    description "Name of admin group excluded when LSP is set up";
                }

                leaf-list apply-groups {
                    type leafref {
                        path "../../../../groups/group/name";
                    }
                    max-elements 8;
                    ordered-by user;
                    description "Apply a configuration group at this level";
                }

                leaf pce-computation {
                    status obsolete;
                    when "not(../type) or ../type = 'p2p-rsvp' or ../type = 'p2p-sr-te'";
                    type boolean;
                    default "false";
                    description "LSP path computation request sent to local CSPF or to PCE";
                }

                container class-forwarding {
                    when "not(../type) or ../type = 'p2p-rsvp' or ../type = 'p2p-sr-te'";
                    presence "Enter the 'class-forwarding' context";
                    description "Enable the class-forwarding context";

                    choice cbf-choice {
                        default "default-lsp-and-fc";
                        case default-lsp-and-fc {

                            leaf default-lsp {
                                status obsolete;
                                type boolean;
                                default "false";
                                description "Use the default LSP configuration for specified LSP or LSP template";
                            }

                            leaf-list fc {
                                status obsolete;
                                type enumeration {
                                    enum "be"                           { value 0; }
                                    enum "l2"                           { value 1; }
                                    enum "af"                           { value 2; }
                                    enum "l1"                           { value 3; }
                                    enum "h2"                           { value 4; }
                                    enum "ef"                           { value 5; }
                                    enum "h1"                           { value 6; }
                                    enum "nc"                           { value 7; }
                                }
                                max-elements 8;
                                description "One or more forwarding classes for LSP instances";
                            }

                        }
                        case forwarding-set {

                            container forwarding-set {
                                description "Enter the forwarding-set context";

                                leaf policy {
                                    type leafref {
                                        path "../../../../class-forwarding-policy/policy-name";
                                    }
                                    description "Name for the class based forwarding policy for LSP instances";
                                }

                                leaf set {
                                    type uint32 {
                                        range "1..6";
                                    }
                                    description "Forwarding set ID";
                                }

                            } // container forwarding-set

                        }
                    }
                } // container class-forwarding

                container cspf {
                    status obsolete;
                    when "not(../type) or ../type = 'p2p-rsvp' or ../type = 'p2p-rsvp-bypass' or ../type = 'p2mp-rsvp' or ../type = 'p2p-sr-te'";
                    presence "Enter the 'cspf' context";
                    description "Enable the cspf context";

                    leaf use-te-metric {
                        status obsolete;
                        type boolean;
                        default "false";
                        description "TE metric to the LSP path computation by CSPF";
                    }

                } // container cspf

                container igp-shortcut {
                    when "not(../type) or ../type = 'p2p-rsvp' or ../type = 'p2p-sr-te'";
                    description "Enter the igp-shortcut context";

                    leaf admin-state {
                        type types-sros:admin-state;
                        description "Administrative state of the LSP to be used as a shortcut while resolving IGP routes";
                    }

                    choice igp-choice {
                        case lfa-type {

                            leaf lfa-type {
                                type enumeration {
                                    enum "lfa-protect"                  { value 1; }
                                    enum "lfa-only"                     { value 2; }
                                }
                                description "Specific RSVP LSP by IS-IS and OSPF routing protocols to assign as shortcut or as forwarding adjacency";
                            }

                        }
                        case relative-metric {

                            leaf relative-metric {
                                type int32 {
                                    range "-10..10";
                                }
                                description "Shortest IGP cost between the endpoints of the LSP plus the configured offset";
                            }

                        }
                    }
                } // container igp-shortcut

                container fast-reroute {
                    when "not(../type) or ../type = 'p2p-rsvp' or ../type = 'p2mp-rsvp'";
                    presence "Enter the 'fast-reroute' context";
                    description "Enable the fast-reroute context";

                    leaf hop-limit {
                        type uint32 {
                            range "0..255";
                        }
                        default "16";
                        description "Total number of hops a detour or backup LSP can take before merging back onto the main LSP path";
                    }

                    leaf propagate-admin-group {
                        type boolean;
                        default "false";
                        description "Enable signaling of the primary LSP path admin-group constraints in the FRR object at ingress";
                    }

                    leaf frr-method {
                        type types-mpls:frr-method-type;
                        description "Fast Reroute method";
                    }

                    leaf node-protect {
                        type boolean;
                        description "Enable node and link protection for the specified LSP";
                    }

                } // container fast-reroute

                container max-sr-labels {
                    when "not(../type) or ../type = 'p2p-sr-te'";
                    description "Enter the max-sr-labels context";

                    leaf label-stack-size {
                        type uint32 {
                            range "1..11";
                        }
                        description "Maximum Label Stack size";
                    }

                    leaf additional-frr-labels {
                        type uint32 {
                            range "0..4";
                        }
                        default "1";
                        description "Value for the maximum additional overhead labels";
                    }

                } // container max-sr-labels

                list admin-tag {
                    when "not(../type) or ../type = 'p2p-rsvp' or ../type = 'p2p-sr-te'";
                    key "name";
                    max-elements 4;
                    description "Add a list entry for admin-tag";

                    leaf name {
                        type leafref {
                            path "../../../../../routing-options/admin-tags/admin-tag/tag";
                        }
                        description "Name of the admin tags";
                    }

                } // list admin-tag

                container auto-bandwidth {
                    when "not(../type) or ../type = 'p2p-rsvp'";
                    presence "Enter the 'auto-bandwidth' context";
                    description "Enable the auto-bandwidth context";

                    leaf max-bandwidth {
                        type types-mpls:lsp-bandwidth;
                        default "100000";
                        description "Maximum bandwidth of auto-bandwidth to request for the LSP";
                    }

                    leaf min-bandwidth {
                        type types-mpls:lsp-bandwidth;
                        default "0";
                        description "Minimum bandwidth of auto-bandwidth to request for the LSP";
                    }

                    leaf monitor-bandwidth {
                        type boolean;
                        default "false";
                        description "Collect and display auto-bandwidth measurements for the LSP";
                    }

                    leaf-list apply-groups {
                        type leafref {
                            path "../../../../../groups/group/name";
                        }
                        max-elements 8;
                        ordered-by user;
                        description "Apply a configuration group at this level";
                    }

                    list fc {
                        key "fc-name";
                        max-elements 8;
                        description "Enter the fc list instance";

                        leaf fc-name {
                            type types-sros:fc-name;
                            description "Forwarding class name for LSP";
                        }

                        leaf sampling-weight {
                            type types-sros:percent;
                            default "100";
                            description "Forwarding class weight for LSP";
                        }

                        leaf-list apply-groups {
                            type leafref {
                                path "../../../../../../groups/group/name";
                            }
                            max-elements 8;
                            ordered-by user;
                            description "Apply a configuration group at this level";
                        }

                    } // list fc

                    container adjust-down {
                        description "Enter the adjust-down context";

                        leaf percent {
                            type types-sros:percent;
                            default "5";
                            description "Minimum difference in percent between LSP bandwidth reservation and the maximum average data rate";
                        }

                        leaf bw {
                            type types-mpls:lsp-bandwidth;
                            default "0";
                            description "Minimum difference in absolute bandwidth between LSP bandwidth reservation and max average data rate";
                        }

                    } // container adjust-down

                    container adjust-up {
                        description "Enter the adjust-up context";

                        leaf percent {
                            type types-sros:percent;
                            default "5";
                            description "Minimum difference in percent between LSP bandwidth reservation and the maximum average data rate";
                        }

                        leaf bw {
                            type types-mpls:lsp-bandwidth;
                            default "0";
                            description "Minimum difference in absolute bandwidth between LSP bandwidth reservation and max average data rate";
                        }

                    } // container adjust-up

                    container multipliers {
                        description "Enter the multipliers context";

                        leaf sample-multiplier {
                            type uint32 {
                                range "1..511";
                            }
                            description "Multiplier for collection intervals in a sample interval";
                        }

                        leaf adjust-multiplier {
                            type uint32 {
                                range "1..16383";
                            }
                            description "Number of collection intervals in the adjust interval";
                        }

                    } // container multipliers

                    container overflow-limit {
                        presence "Enter the 'overflow-limit' context";
                        description "Enable the overflow-limit context";

                        leaf threshold {
                            type types-sros:percent;
                            default "0";
                            description "Minimum difference in percent between the LSP bandwidth and the sampled data rate";
                        }

                        leaf bw {
                            type types-mpls:lsp-bandwidth {
                                range "1..6400000";
                            }
                            description "Minimum difference in absolute bandwidth between the LSP bandwidth and the sampled data rate";
                        }

                        leaf number {
                            type uint32 {
                                range "1..10";
                            }
                            mandatory true;
                            description "Number of overflow samples to trigger an overflow auto-bandwidth adjustment attempt";
                        }

                    } // container overflow-limit

                    container underflow-limit {
                        presence "Enter the 'underflow-limit' context";
                        description "Enable the underflow-limit context";

                        leaf threshold {
                            type types-sros:percent;
                            default "0";
                            description "Minimum difference in percent between the LSP bandwidth and the sampled data rate";
                        }

                        leaf bw {
                            type types-mpls:lsp-bandwidth {
                                range "1..6400000";
                            }
                            description "Minimum difference in absolute bandwidth between the LSP bandwidth and the sampled data rate";
                        }

                        leaf number {
                            type uint32 {
                                range "1..10";
                            }
                            mandatory true;
                            description "Number of overflow samples to trigger an overflow auto-bandwidth adjustment attempt";
                        }

                    } // container underflow-limit

                    container use-last-adj-bw {
                        presence "Enter the 'use-last-adj-bw' context";
                        description "Enable the use-last-adj-bw context";

                        leaf secondary-retry-limit {
                            type types-mpls:retry-limit;
                            default "5";
                            description "Specify the max number of retry attempts that will be made to signal the secondary path with the last adjusted bandwidth.";
                        }

                    } // container use-last-adj-bw

                } // container auto-bandwidth

                container egress-statistics {
                    when "../type = 'p2p-rsvp' or ../type = 'p2mp-rsvp' or not(../type) or ../type = 'p2p-sr-te'";
                    presence "Enter the 'egress-statistics' context";
                    description "Enable the egress-statistics context";

                    leaf collect-stats {
                        when "not(../../type) or ../../type = 'p2p-rsvp' or ../../type = 'p2mp-rsvp'";
                        type boolean;
                        default "false";
                        description "Collect statistics";
                    }

                    leaf accounting-policy {
                        when "not(../../type) or ../../type = 'p2p-rsvp' or ../../type = 'p2mp-rsvp'";
                        type leafref {
                            path "../../../../../log/accounting-policy/policy-id";
                        }
                        description "Accounting policy ID";
                    }

                    leaf admin-state {
                        when "not(../../type) or ../../type = 'p2p-rsvp' or ../../type = 'p2mp-rsvp' or ../../type = 'p2p-sr-te'";
                        type types-sros:admin-state;
                        default "disable";
                        description "Administrative state of ingress statistics for LSP";
                    }

                    leaf-list apply-groups {
                        type leafref {
                            path "../../../../../groups/group/name";
                        }
                        max-elements 8;
                        ordered-by user;
                        description "Apply a configuration group at this level";
                    }

                } // container egress-statistics

                container bfd {
                    when "not(../type) or ../type = 'p2p-rsvp' or ../type = 'p2p-sr-te'";
                    description "Enter the bfd context";

                    leaf bfd-liveness {
                        type boolean;
                        default "false";
                        description "Enable BFD on the RSVP LSP or S-BFD on the SR-TE LSP";
                    }

                    leaf bfd-template {
                        type leafref {
                            path "../../../../../bfd/bfd-template/name";
                        }
                        description "BFD template";
                    }

                    leaf lsp-ping-interval {
                        when "not(../../type) or ../../type = 'p2p-rsvp'";
                        type union {
                            type uint32 {
                                range "60..300";
                            }
                            type enumeration {
                                enum "none"                         { value 0; }
                            }
                        }
                        units "seconds";
                        default "60";
                        description "Interval for periodic LSP ping for BFD bootstrapping";
                    }

                    leaf failure-action {
                        type enumeration {
                            enum "none"                         { value 0; }
                            enum "down"                         { value 1; }
                            enum "failover"                     { value 2; }
                            enum "failover-or-down"             { value 3; }
                        }
                        default "none";
                        description "Action when LSP BFD fails on the RSVP SR-TE LSP";
                    }

                    leaf wait-for-up-timer {
                        when "not(../../type) or ../../type = 'p2p-sr-te' or ../../type = 'p2p-rsvp'";
                        type uint32 {
                            range "1..60";
                        }
                        units "seconds";
                        default "4";
                        description "Time to wait for BFD to become operationally available";
                    }

                } // container bfd

                list path-profile {
                    when "not(../type) or ../type = 'p2p-rsvp' or ../type = 'p2p-sr-te'";
                    key "profile-id";
                    max-elements 5;
                    description "Enter the path-profile list instance";

                    leaf profile-id {
                        type uint32 {
                            range "1..max";
                        }
                        description "Profile ID for the specified LSP";
                    }

                    leaf path-group {
                        type uint32;
                        default "0";
                        description "Profile ID for the specified LSP";
                    }

                    leaf-list apply-groups {
                        type leafref {
                            path "../../../../../groups/group/name";
                        }
                        max-elements 8;
                        ordered-by user;
                        description "Apply a configuration group at this level";
                    }

                } // list path-profile

                list primary {
                    when "not(../type) or ../type = 'p2p-rsvp' or ../type = 'p2p-rsvp-bypass' or ../type = 'p2p-sr-te'";
                    key "path-name";
                    max-elements 1;
                    description "Enter the primary list instance";

                    leaf path-name {
                        type leafref {
                            path "../../../path/path-name";
                        }
                        description "Path name";
                    }

                    leaf admin-state {
                        type types-sros:admin-state;
                        default "enable";
                        description "Administrative state of LSP path";
                    }

                    leaf adaptive {
                        when "not(../../type) or ../../type = 'p2p-rsvp' or ../../type = 'p2p-rsvp-bypass' or ../../type = 'p2mp-rsvp'";
                        type boolean;
                        description "Enable/disable make-before-break functionality.";
                    }

                    leaf bandwidth {
                        when "not(../../type) or ../../type = 'p2p-rsvp' or ../../type = 'p2mp-rsvp' or ../../type = 'p2p-sr-te'";
                        type types-mpls:lsp-bandwidth;
                        default "0";
                        description "Amount of bandwidth to be reserved.";
                    }

                    leaf hop-limit {
                        when "not(../../type) or ../../type = 'p2p-rsvp' or ../../type = 'p2p-rsvp-bypass' or ../../type = 'p2mp-rsvp' or ../../type = 'p2p-sr-te'";
                        type uint32 {
                            range "2..255";
                        }
                        description "The maximum number of hops that an LSP will traverse including the ingress and egress LSRs.";
                    }

                    leaf record {
                        when "not(../../type) or ../../type = 'p2p-rsvp' or ../../type = 'p2p-rsvp-bypass' or ../../type = 'p2mp-rsvp'";
                        type boolean;
                        default "true";
                        description "Enable/disable recording of all hops.";
                    }

                    leaf record-label {
                        when "not(../../type) or ../../type = 'p2p-rsvp' or ../../type = 'p2p-rsvp-bypass' or ../../type = 'p2mp-rsvp'";
                        type boolean;
                        default "true";
                        description "Enable/disable recording of labels at each node or instance.";
                    }

                    leaf class-type {
                        when "not(../../type) or ../../type = 'p2p-rsvp'";
                        type types-mpls:class-type;
                        description "Class-type";
                    }

                    leaf backup-class-type {
                        when "not(../../type) or ../../type = 'p2p-rsvp'";
                        type types-mpls:class-type;
                        description "Class-type for the LSP or LSP path";
                    }

                    leaf-list apply-groups {
                        type leafref {
                            path "../../../../../groups/group/name";
                        }
                        max-elements 8;
                        ordered-by user;
                        description "Apply a configuration group at this level";
                    }

                    container priority {
                        when "not(../../type) or ../../type = 'p2p-rsvp' or ../../type = 'p2p-sr-te'";
                        description "Enter the priority context";

                        leaf setup-priority {
                            type types-mpls:priority;
                            default "7";
                            description "Setup priority when insufficient bandwidth is available to set up LSP";
                        }

                        leaf hold-priority {
                            type types-mpls:priority;
                            default "0";
                            description "Hold priority when insufficient bandwidth is available to set up LSP";
                        }

                    } // container priority

                    container include-admin-group {
                        when "not(../../type) or ../../type = 'p2p-rsvp' or ../../type = 'p2p-rsvp-bypass' or ../../type = 'p2p-sr-te'";
                        presence "Enter the 'include-admin-group' context";
                        description "Enable the include-admin-group context";

                        leaf-list group {
                            type leafref {
                                path "../../../../../../routing-options/if-attribute/admin-group/group-name";
                            }
                            min-elements 1;
                            max-elements 32;
                            description "Groups that are included when LSP path is setup";
                        }

                    } // container include-admin-group

                    container exclude-admin-group {
                        when "not(../../type) or ../../type = 'p2p-rsvp' or ../../type = 'p2p-rsvp-bypass' or ../../type = 'p2p-sr-te'";
                        presence "Enter the 'exclude-admin-group' context";
                        description "Enable the exclude-admin-group context";

                        leaf-list group {
                            type leafref {
                                path "../../../../../../routing-options/if-attribute/admin-group/group-name";
                            }
                            min-elements 1;
                            max-elements 32;
                            description "Groups to exclude when the LSP path is setup";
                        }

                    } // container exclude-admin-group

                    container bfd {
                        when "not(../../type) or ../../type = 'p2p-rsvp' or ../../type = 'p2p-sr-te'";
                        description "Enter the bfd context";

                        leaf bfd-liveness {
                            type boolean;
                            default "false";
                            description "Enable BFD on the RSVP LSP or S-BFD on the SR-TE LSP";
                        }

                        leaf bfd-template {
                            type leafref {
                                path "../../../../../../bfd/bfd-template/name";
                            }
                            description "BFD template";
                        }

                        leaf lsp-ping-interval {
                            when "not(../../../type) or ../../../type = 'p2p-rsvp'";
                            type union {
                                type uint32 {
                                    range "60..300";
                                }
                                type enumeration {
                                    enum "none"                         { value 0; }
                                }
                            }
                            units "seconds";
                            default "60";
                            description "Interval for periodic LSP ping for BFD bootstrapping";
                        }

                        leaf wait-for-up-timer {
                            when "not(../../../type) or ../../../type = 'p2p-sr-te' or ../../../type = 'p2p-rsvp'";
                            type uint32 {
                                range "1..60";
                            }
                            units "seconds";
                            default "4";
                            description "Time to wait for BFD to become operationally available";
                        }

                    } // container bfd

                } // list primary

                list secondary {
                    when "not(../type) or ../type = 'p2p-rsvp' or ../type = 'p2p-sr-te'";
                    key "path-name";
                    max-elements 8;
                    description "Enter the secondary list instance";

                    leaf path-name {
                        type leafref {
                            path "../../../path/path-name";
                        }
                        description "Path name";
                    }

                    leaf admin-state {
                        type types-sros:admin-state;
                        default "enable";
                        description "Administrative state of LSP path";
                    }

                    leaf adaptive {
                        when "not(../../type) or ../../type = 'p2p-rsvp' or ../../type = 'p2p-rsvp-bypass' or ../../type = 'p2mp-rsvp'";
                        type boolean;
                        description "Enable/disable make-before-break functionality.";
                    }

                    leaf bandwidth {
                        when "not(../../type) or ../../type = 'p2p-rsvp' or ../../type = 'p2mp-rsvp' or ../../type = 'p2p-sr-te'";
                        type types-mpls:lsp-bandwidth;
                        default "0";
                        description "Amount of bandwidth to be reserved.";
                    }

                    leaf hop-limit {
                        when "not(../../type) or ../../type = 'p2p-rsvp' or ../../type = 'p2p-rsvp-bypass' or ../../type = 'p2mp-rsvp' or ../../type = 'p2p-sr-te'";
                        type uint32 {
                            range "2..255";
                        }
                        description "The maximum number of hops that an LSP will traverse including the ingress and egress LSRs.";
                    }

                    leaf record {
                        when "not(../../type) or ../../type = 'p2p-rsvp' or ../../type = 'p2p-rsvp-bypass' or ../../type = 'p2mp-rsvp'";
                        type boolean;
                        default "true";
                        description "Enable/disable recording of all hops.";
                    }

                    leaf record-label {
                        when "not(../../type) or ../../type = 'p2p-rsvp' or ../../type = 'p2p-rsvp-bypass' or ../../type = 'p2mp-rsvp'";
                        type boolean;
                        default "true";
                        description "Enable/disable recording of labels at each node or instance.";
                    }

                    leaf class-type {
                        when "not(../../type) or ../../type = 'p2p-rsvp'";
                        type types-mpls:class-type;
                        description "Class-type";
                    }

                    leaf path-preference {
                        when "not(../../type) or ../../type = 'p2p-rsvp' or ../../type = 'p2p-sr-te'";
                        type int32 {
                            range "1..255";
                        }
                        default "255";
                        description "Path preference for the secondary standby path";
                    }

                    leaf srlg {
                        when "not(../../type) or ../../type = 'p2p-rsvp' or ../../type = 'p2p-sr-te'";
                        type boolean;
                        default "false";
                        description "Use SRLG constraint in secondary path computation for an LSP at the head-end LER";
                    }

                    leaf standby {
                        when "not(../../type) or ../../type = 'p2p-rsvp' or ../../type = 'p2p-sr-te'";
                        type boolean;
                        default "false";
                        description "Maintain secondary path LSP indefinitely in hot standby state";
                    }

                    leaf-list apply-groups {
                        type leafref {
                            path "../../../../../groups/group/name";
                        }
                        max-elements 8;
                        ordered-by user;
                        description "Apply a configuration group at this level";
                    }

                    container priority {
                        when "not(../../type) or ../../type = 'p2p-rsvp' or ../../type = 'p2p-sr-te'";
                        description "Enter the priority context";

                        leaf setup-priority {
                            type types-mpls:priority;
                            default "7";
                            description "Setup priority when insufficient bandwidth is available to set up LSP";
                        }

                        leaf hold-priority {
                            type types-mpls:priority;
                            default "0";
                            description "Hold priority when insufficient bandwidth is available to set up LSP";
                        }

                    } // container priority

                    container include-admin-group {
                        when "not(../../type) or ../../type = 'p2p-rsvp' or ../../type = 'p2p-sr-te'";
                        presence "Enter the 'include-admin-group' context";
                        description "Enable the include-admin-group context";

                        leaf-list group {
                            type leafref {
                                path "../../../../../../routing-options/if-attribute/admin-group/group-name";
                            }
                            min-elements 1;
                            max-elements 32;
                            description "Groups that are included when LSP path is setup";
                        }

                    } // container include-admin-group

                    container exclude-admin-group {
                        when "not(../../type) or ../../type = 'p2p-rsvp' or ../../type = 'p2p-sr-te'";
                        presence "Enter the 'exclude-admin-group' context";
                        description "Enable the exclude-admin-group context";

                        leaf-list group {
                            type leafref {
                                path "../../../../../../routing-options/if-attribute/admin-group/group-name";
                            }
                            min-elements 1;
                            max-elements 32;
                            description "Groups to exclude when the LSP path is setup";
                        }

                    } // container exclude-admin-group

                    container bfd {
                        when "not(../../type) or ../../type = 'p2p-rsvp' or ../../type = 'p2p-sr-te'";
                        description "Enter the bfd context";

                        leaf bfd-liveness {
                            type boolean;
                            default "false";
                            description "Enable BFD on the RSVP LSP or S-BFD on the SR-TE LSP";
                        }

                        leaf bfd-template {
                            type leafref {
                                path "../../../../../../bfd/bfd-template/name";
                            }
                            description "BFD template";
                        }

                        leaf lsp-ping-interval {
                            when "not(../../../type) or ../../../type = 'p2p-rsvp'";
                            type union {
                                type uint32 {
                                    range "60..300";
                                }
                                type enumeration {
                                    enum "none"                         { value 0; }
                                }
                            }
                            units "seconds";
                            default "60";
                            description "Interval for periodic LSP ping for BFD bootstrapping";
                        }

                        leaf wait-for-up-timer {
                            when "not(../../../type) or ../../../type = 'p2p-sr-te' or ../../../type = 'p2p-rsvp'";
                            type uint32 {
                                range "1..60";
                            }
                            units "seconds";
                            default "4";
                            description "Time to wait for BFD to become operationally available";
                        }

                    } // container bfd

                } // list secondary

                list primary-p2mp-instance {
                    when "not(../type) or ../type = 'p2mp-rsvp'";
                    key "instance-name";
                    max-elements 1;
                    description "Enter the primary-p2mp-instance list instance";

                    leaf instance-name {
                        type types-sros:named-item;
                        description "The unique name which identifies this P2MP LSP for this virtual router.";
                    }

                    leaf admin-state {
                        type types-sros:admin-state;
                        default "enable";
                        description "Administrative state of LSP path";
                    }

                    leaf adaptive {
                        when "not(../../type) or ../../type = 'p2p-rsvp' or ../../type = 'p2p-rsvp-bypass' or ../../type = 'p2mp-rsvp'";
                        type boolean;
                        description "Enable/disable make-before-break functionality.";
                    }

                    leaf bandwidth {
                        when "not(../../type) or ../../type = 'p2p-rsvp' or ../../type = 'p2mp-rsvp' or ../../type = 'p2p-sr-te'";
                        type types-mpls:lsp-bandwidth;
                        default "0";
                        description "Amount of bandwidth to be reserved.";
                    }

                    leaf hop-limit {
                        when "not(../../type) or ../../type = 'p2p-rsvp' or ../../type = 'p2p-rsvp-bypass' or ../../type = 'p2mp-rsvp' or ../../type = 'p2p-sr-te'";
                        type uint32 {
                            range "2..255";
                        }
                        description "The maximum number of hops that an LSP will traverse including the ingress and egress LSRs.";
                    }

                    leaf record {
                        when "not(../../type) or ../../type = 'p2p-rsvp' or ../../type = 'p2p-rsvp-bypass' or ../../type = 'p2mp-rsvp'";
                        type boolean;
                        default "true";
                        description "Enable/disable recording of all hops.";
                    }

                    leaf record-label {
                        when "not(../../type) or ../../type = 'p2p-rsvp' or ../../type = 'p2p-rsvp-bypass' or ../../type = 'p2mp-rsvp'";
                        type boolean;
                        default "true";
                        description "Enable/disable recording of labels at each node or instance.";
                    }

                    leaf-list apply-groups {
                        type leafref {
                            path "../../../../../groups/group/name";
                        }
                        max-elements 8;
                        ordered-by user;
                        description "Apply a configuration group at this level";
                    }

                    container include-admin-group {
                        when "not(../../type) or ../../type = 'p2mp-rsvp'";
                        presence "Enter the 'include-admin-group' context";
                        description "Enable the include-admin-group context";

                        leaf-list group {
                            type leafref {
                                path "../../../../../../routing-options/if-attribute/admin-group/group-name";
                            }
                            min-elements 1;
                            max-elements 32;
                            description "Groups that are included when LSP path is setup";
                        }

                    } // container include-admin-group

                    container exclude-admin-group {
                        when "not(../../type) or ../../type = 'p2mp-rsvp'";
                        presence "Enter the 'exclude-admin-group' context";
                        description "Enable the exclude-admin-group context";

                        leaf-list group {
                            type leafref {
                                path "../../../../../../routing-options/if-attribute/admin-group/group-name";
                            }
                            min-elements 1;
                            max-elements 32;
                            description "Groups to exclude when the LSP path is setup";
                        }

                    } // container exclude-admin-group

                    list s2l-path {
                        when "not(../../type) or ../../type = 'p2mp-rsvp'";
                        key "path-name to";
                        max-elements 650;
                        description "Enter the s2l-path list instance";

                        leaf path-name {
                            type leafref {
                                path "../../../../path/path-name";
                            }
                            description "A label switch path (P2MP LSP) name.";
                        }

                        leaf to {
                            type types-sros:ip-address;
                            description "The IP address of the destination address of the S2L sub LSP.";
                        }

                        leaf admin-state {
                            type types-sros:admin-state;
                            default "enable";
                            description "Administrative state of the S2L sub-LSP for a P2MP LSP";
                        }

                        leaf-list apply-groups {
                            type leafref {
                                path "../../../../../../groups/group/name";
                            }
                            max-elements 8;
                            ordered-by user;
                            description "Apply a configuration group at this level";
                        }

                    } // list s2l-path

                } // list primary-p2mp-instance

            } // list lsp

            list auto-lsp {
                key "template-name";
                max-elements 500;
                description "Enter the auto-lsp list instance";

                leaf template-name {
                    type leafref {
                        path "../../lsp-template/template-name";
                    }
                    description "Name of the LSP template used to automatically create and signal multiple LSP instances";
                }

                leaf-list apply-groups {
                    type leafref {
                        path "../../../../groups/group/name";
                    }
                    max-elements 8;
                    ordered-by user;
                    description "Apply a configuration group at this level";
                }

                choice auto-lsp-choice {
                    case one-hop {

                        leaf one-hop {
                            type boolean;
                            default "false";
                            description "Enable the automatic signaling of one-hop point-to-point LSPs";
                        }

                    }
                    case policy {

                        leaf-list policy {
                            type leafref {
                                path "../../../../policy-options/policy-statement/name";
                            }
                            max-elements 5;
                            ordered-by user;
                            description "Specify policies to bind to this LSP template to enable automatic creation of mesh point to point (P2P) LSPs.";
                        }

                    }
                }
            } // list auto-lsp

            list static-lsp {
                key "lsp-name";
                max-elements 1000;
                description "Enter the static-lsp list instance";

                leaf lsp-name {
                    type types-sros:named-item-64;
                    description "Labeled Switch path name";
                }

                leaf metric {
                    type uint32 {
                        range "1..16777215";
                    }
                    sros-ext:auto-restart-to-modify;
                    description "MPLS static LSP metric to select an LSP";
                }

                leaf admin-state {
                    type types-sros:admin-state;
                    sros-ext:auto-restart-to-modify;
                    default "disable";
                    description "Administrative state of the static LSP";
                }

                leaf to {
                    type types-sros:ipv4-unicast-address;
                    sros-ext:auto-restart-to-modify;
                    description "Destination IP address or the egress router for the LSP";
                }

                leaf-list apply-groups {
                    type leafref {
                        path "../../../../groups/group/name";
                    }
                    max-elements 8;
                    ordered-by user;
                    sros-ext:auto-restart-to-modify;
                    description "Apply a configuration group at this level";
                }

                container push {
                    presence "Enter the 'push' context";
                    sros-ext:auto-restart-to-modify;
                    description "Enable the push context";

                    leaf out-label {
                        type union {
                            type uint32 {
                                range "16..1048575";
                            }
                            type enumeration {
                                enum "implicit-null-label"          { value 3; }
                            }
                        }
                        sros-ext:auto-restart-to-modify;
                        mandatory true;
                        description "Push specific label onto the top of the outgoing packet's label stack";
                    }

                    leaf next-hop {
                        type types-sros:ipv4-unicast-address;
                        sros-ext:auto-restart-to-modify;
                        mandatory true;
                        description "IP address for the next hop";
                    }

                    leaf-list apply-groups {
                        type leafref {
                            path "../../../../../groups/group/name";
                        }
                        max-elements 8;
                        ordered-by user;
                        sros-ext:auto-restart-to-modify;
                        description "Apply a configuration group at this level";
                    }

                } // container push

            } // list static-lsp

            container forwarding-policies {
                presence "Enter the 'forwarding-policies' context";
                description "Enable the forwarding-policies context";

                leaf admin-state {
                    type types-sros:admin-state;
                    default "disable";
                    description "Administrative state of MPLS forwarding policies";
                }

                leaf reserved-label-block {
                    type leafref {
                        path "../../../mpls-labels/reserved-label-block/label-block-name";
                    }
                    sros-ext:auto-restart-to-modify;
                    description "Reserved label block";
                }

                leaf-list apply-groups {
                    type leafref {
                        path "../../../../groups/group/name";
                    }
                    max-elements 8;
                    ordered-by user;
                    description "Apply a configuration group at this level";
                }

                list forwarding-policy {
                    key "policy-name";
                    max-elements 65536;
                    description "Enter the forwarding-policy list instance";

                    leaf policy-name {
                        type types-sros:named-item-64;
                        description "Forwarding policy name";
                    }

                    leaf admin-state {
                        type types-sros:admin-state;
                        default "disable";
                        description "Administrative state of the forwarding policy";
                    }

                    leaf binding-label {
                        type types-sros:mpls-label-or-zero;
                        sros-ext:auto-restart-to-modify;
                        description "Binding label";
                    }

                    leaf endpoint {
                        type types-sros:ip-unicast-address;
                        sros-ext:auto-restart-to-modify;
                        description "Configure endpoint address.";
                    }

                    leaf revert-timer {
                        type uint32 {
                            range "1..600";
                        }
                        units "seconds";
                        description "Revert timer";
                    }

                    leaf preference {
                        type uint32 {
                            range "1..255";
                        }
                        sros-ext:auto-restart-to-modify;
                        default "255";
                        description "Preference number";
                    }

                    leaf metric {
                        type uint32 {
                            range "1..16777215";
                        }
                        description "Configure metric.";
                    }

                    leaf tunnel-table-pref {
                        type uint32 {
                            range "1..255";
                        }
                        default "255";
                        description "Configure tunnel table preference.";
                    }

                    leaf-list apply-groups {
                        type leafref {
                            path "../../../../../groups/group/name";
                        }
                        max-elements 8;
                        ordered-by user;
                        description "Apply a configuration group at this level";
                    }

                    list next-hop-group {
                        key "index";
                        max-elements 32;
                        description "Enter the next-hop-group list instance";

                        leaf index {
                            type uint32 {
                                range "1..32";
                            }
                            description "Index for next hop group";
                        }

                        leaf admin-state {
                            type types-sros:admin-state;
                            default "disable";
                            description "Administrative state of next hop group";
                        }

                        leaf resolution-type {
                            type enumeration {
                                enum "direct"                       { value 1; }
                                enum "indirect"                     { value 2; }
                            }
                            sros-ext:immutable;
                            mandatory true;
                            description "Resolution type for next hop group";
                        }

                        leaf load-balancing-weight {
                            type uint32 {
                                range "1..max";
                            }
                            description "Configure load balancing weight.";
                        }

                        leaf-list apply-groups {
                            type leafref {
                                path "../../../../../../groups/group/name";
                            }
                            max-elements 8;
                            ordered-by user;
                            description "Apply a configuration group at this level";
                        }

                        container primary-next-hop {
                            presence "Enter the 'primary-next-hop' context";
                            description "Enable the primary-next-hop context";

                            leaf next-hop {
                                type types-sros:ip-unicast-address;
                                description "Next hop address";
                            }

                            leaf-list apply-groups {
                                type leafref {
                                    path "../../../../../../../groups/group/name";
                                }
                                max-elements 8;
                                ordered-by user;
                                description "Apply a configuration group at this level";
                            }

                            list pushed-labels {
                                key "index";
                                max-elements 10;
                                description "Enter the pushed-labels list instance";

                                leaf index {
                                    type uint32 {
                                        range "1..10";
                                    }
                                    description "Index for push-label.";
                                }

                                leaf label {
                                    type uint32 {
                                        range "1..1048575";
                                    }
                                    mandatory true;
                                    description "Push label value.";
                                }

                                leaf-list apply-groups {
                                    type leafref {
                                        path "../../../../../../../../groups/group/name";
                                    }
                                    max-elements 8;
                                    ordered-by user;
                                    description "Apply a configuration group at this level";
                                }

                            } // list pushed-labels

                        } // container primary-next-hop

                        container backup-next-hop {
                            presence "Enter the 'backup-next-hop' context";
                            description "Enable the backup-next-hop context";

                            leaf next-hop {
                                type types-sros:ip-unicast-address;
                                description "Next hop address";
                            }

                            leaf-list apply-groups {
                                type leafref {
                                    path "../../../../../../../groups/group/name";
                                }
                                max-elements 8;
                                ordered-by user;
                                description "Apply a configuration group at this level";
                            }

                            list pushed-labels {
                                key "index";
                                max-elements 10;
                                description "Enter the pushed-labels list instance";

                                leaf index {
                                    type uint32 {
                                        range "1..10";
                                    }
                                    description "Index for push-label.";
                                }

                                leaf label {
                                    type uint32 {
                                        range "1..1048575";
                                    }
                                    mandatory true;
                                    description "Push label value.";
                                }

                                leaf-list apply-groups {
                                    type leafref {
                                        path "../../../../../../../../groups/group/name";
                                    }
                                    max-elements 8;
                                    ordered-by user;
                                    description "Apply a configuration group at this level";
                                }

                            } // list pushed-labels

                        } // container backup-next-hop

                    } // list next-hop-group

                    container ingress-statistics {
                        presence "Enter the 'ingress-statistics' context";
                        description "Enable the ingress-statistics context";

                        leaf admin-state {
                            type types-sros:admin-state;
                            default "disable";
                            description "Administrative state of egress or ingress statistics";
                        }

                        leaf-list apply-groups {
                            type leafref {
                                path "../../../../../../groups/group/name";
                            }
                            max-elements 8;
                            ordered-by user;
                            description "Apply a configuration group at this level";
                        }

                    } // container ingress-statistics

                    container egress-statistics {
                        presence "Enter the 'egress-statistics' context";
                        description "Enable the egress-statistics context";

                        leaf admin-state {
                            type types-sros:admin-state;
                            default "disable";
                            description "Administrative state of egress or ingress statistics";
                        }

                        leaf-list apply-groups {
                            type leafref {
                                path "../../../../../../groups/group/name";
                            }
                            max-elements 8;
                            ordered-by user;
                            description "Apply a configuration group at this level";
                        }

                    } // container egress-statistics

                } // list forwarding-policy

            } // container forwarding-policies

            container pce-init-lsp {
                presence "Enter the 'pce-init-lsp' context";
                description "Enable the pce-init-lsp context";

                leaf-list apply-groups {
                    type leafref {
                        path "../../../../groups/group/name";
                    }
                    max-elements 8;
                    ordered-by user;
                    description "Apply a configuration group at this level";
                }

                container sr-te {
                    presence "Enter the 'sr-te' context";
                    description "Enable the sr-te context";

                    leaf admin-state {
                        type types-sros:admin-state;
                        default "disable";
                        description "Administrative state of SR-TE PCE-initiated LSP support";
                    }

                } // container sr-te

            } // container pce-init-lsp

            container ingress-statistics {
                description "Enter the ingress-statistics context";

                list lsp {
                    key "sender lsp-name";
                    description "Enter the lsp list instance";

                    leaf sender {
                        type types-sros:ip-unicast-address;
                        description "Sender address";
                    }

                    leaf lsp-name {
                        type types-sros:named-item-64;
                        description "Administrative name for Labeled Switch Path.";
                    }

                    leaf collect-stats {
                        type boolean;
                        default "false";
                        description "Collect statistics";
                    }

                    leaf accounting-policy {
                        type leafref {
                            path "../../../../../log/accounting-policy/policy-id";
                        }
                        description "Accounting policy ID";
                    }

                    leaf admin-state {
                        type types-sros:admin-state;
                        default "disable";
                        description "Administrative state of ingress statistics for LSP";
                    }

                    leaf-list apply-groups {
                        type leafref {
                            path "../../../../../groups/group/name";
                        }
                        max-elements 8;
                        ordered-by user;
                        description "Apply a configuration group at this level";
                    }

                } // list lsp

                list p2mp-template-lsp {
                    key "sender rsvp-session-name";
                    description "Enter the p2mp-template-lsp list instance";

                    leaf sender {
                        type types-sros:ip-unicast-address;
                        description "Sender address";
                    }

                    leaf rsvp-session-name {
                        type types-sros:named-item-64;
                        description "RSVP session name";
                    }

                    leaf collect-stats {
                        type boolean;
                        default "false";
                        description "Collect statistics";
                    }

                    leaf accounting-policy {
                        type leafref {
                            path "../../../../../log/accounting-policy/policy-id";
                        }
                        description "Accounting policy ID";
                    }

                    leaf admin-state {
                        type types-sros:admin-state;
                        default "disable";
                        description "Administrative state of ingress statistics for LSP";
                    }

                    leaf max-stats {
                        type uint32 {
                            range "1..8191";
                        }
                        default "8191";
                        description "Maximum number of statistic indices";
                    }

                    leaf-list apply-groups {
                        type leafref {
                            path "../../../../../groups/group/name";
                        }
                        max-elements 8;
                        ordered-by user;
                        description "Apply a configuration group at this level";
                    }

                } // list p2mp-template-lsp

                list p2p-template-lsp {
                    key "sender rsvp-session-name";
                    description "Enter the p2p-template-lsp list instance";

                    leaf sender {
                        type types-sros:ip-unicast-address;
                        description "Sender address";
                    }

                    leaf rsvp-session-name {
                        type types-sros:named-item-64;
                        description "RSVP session name";
                    }

                    leaf collect-stats {
                        type boolean;
                        default "false";
                        description "Collect statistics";
                    }

                    leaf accounting-policy {
                        type leafref {
                            path "../../../../../log/accounting-policy/policy-id";
                        }
                        description "Accounting policy ID";
                    }

                    leaf admin-state {
                        type types-sros:admin-state;
                        default "disable";
                        description "Administrative state of ingress statistics for LSP";
                    }

                    leaf max-stats {
                        type uint32 {
                            range "1..8191";
                        }
                        default "8191";
                        description "Maximum number of statistic indices";
                    }

                    leaf-list apply-groups {
                        type leafref {
                            path "../../../../../groups/group/name";
                        }
                        max-elements 8;
                        ordered-by user;
                        description "Apply a configuration group at this level";
                    }

                } // list p2p-template-lsp

            } // container ingress-statistics

            container aux-stats {
                presence "Enter the 'aux-stats' context";
                description "Enable the aux-stats context";

                leaf sr {
                    type boolean;
                    default "false";
                    description "Count Segment Routing (SR) traffic in the auxiliary MPLS statistics table";
                }

            } // container aux-stats

            container sr-te-resignal {
                description "Enter the sr-te-resignal context";

                leaf resignal-timer {
                    type uint32 {
                        range "30..10080";
                    }
                    units "minutes";
                    description "The resignal timer for SR-TE LSPs.";
                }

                leaf resignal-on-igp-event {
                    type boolean;
                    default "false";
                    description "Enable/disable re-optimization of SR-TE LSPs triggered by IGP events.";
                }

            } // container sr-te-resignal

        } // container mpls

    } // grouping conf-router-mpls

}
