module nokia-types-igmp {

    yang-version "1.1";

    namespace "urn:nokia.com:sros:ns:yang:sr:types-igmp";

    prefix "types-igmp";

    import nokia-sros-yang-extensions     { prefix "sros-ext"; }

    sros-ext:sros-major-release "rel24";
    organization "Nokia";
    contact
        "Nokia SR OS Support
         Web: <http://www.nokia.com>";
    description
        "Common IGMP data types used in the SR OS management system.

         Copyright 2016 Nokia. All rights reserved. Reproduction of this document
         is authorized on the condition that the foregoing copyright notice is included.

         This nokia-types-igmp YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";
    revision "2022-02-11";

    typedef learn-type {
        type enumeration {
            enum static {
                value 1;
                description "This group entry was statically configured.";
            }
            enum dynamic {
                value 2;
                description "This group entry was learned by the protocol.";
            }
            enum bgp-smet {
                value 3;
                description "This group entry was learned from a bgp SMET route.";
            }
            enum bgp-sync {
                value 4;
                description "This group entry was learned from a bgp JOIN SYNC route.";
            }
        }
        description "How this group entry was learned.";
    }

    typedef filter-mode {
        type enumeration {
            enum include {
                value 1;
                description "In include mode, reception of packets sent to the specified multicast address is requested only from those IP source addresses listed in the source-list parameter";
            }
            enum exclude {
                value 2;
                description "In exclude mode, reception of packets sent to the given multicast address is requested from all IP source addresses except those listed in the source-list parameter.";
            }
        }
        description "The type of group membership.";
    }

    typedef mld-version {
        type enumeration {
            enum 1                              { value 1; }
            enum 2                              { value 2; }
        }
        description "The MLD protocol version.";
    }

    typedef igmp-version {
        type enumeration {
            enum 1                              { value 1; }
            enum 2                              { value 2; }
            enum 3                              { value 3; }
        }
        description "The IGMP protocol version.";
    }

    typedef forwarding-state {
        type enumeration {
            enum forward                        { value 1; }
            enum block                          { value 2; }
        }
        description "Forwarding state.";
    }

    typedef trace-igmp-pkt-type {
        type enumeration {
            enum all {
                value 0;
                description "All IGMP packets";
            }
            enum query {
                value 1;
                description "IGMP Query packets";
            }
            enum v1-report {
                value 2;
                description "IGMP version 1 Report packets";
            }
            enum v2-report {
                value 3;
                description "IGMP version 2 Report packets";
            }
            enum v2-leave {
                value 4;
                description "IGMP version 2 Leave packets";
            }
            enum v3-report {
                value 5;
                description "IGMP version 3 Report packets";
            }
        }
    }

    typedef trace-mld-pkt-type {
        type enumeration {
            enum all {
                value 0;
                description "All MLD packets";
            }
            enum query {
                value 1;
                description "MLD Query packets";
            }
            enum v1-report {
                value 2;
                description "MLD version 1 Report packets";
            }
            enum v2-report {
                value 3;
                description "MLD version 2 Report packets";
            }
        }
    }

    typedef trace-igmp-mld-pkt-detail {
        type enumeration {
            enum low                            { value 0; }
            enum medium                         { value 1; }
            enum high                           { value 2; }
        }
    }

}
