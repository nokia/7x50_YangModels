submodule nokia-conf-system-security-aaa {

    yang-version "1.1";

    belongs-to nokia-conf { prefix "conf"; }

    import nokia-sros-yang-extensions     { prefix "sros-ext"; }
    import nokia-types-qos                { prefix "types-qos"; }
    import nokia-types-security           { prefix "types-security"; }
    import nokia-types-sros               { prefix "types-sros"; }
    import nokia-types-system             { prefix "types-system"; }

    include nokia-conf-groups;
    include nokia-conf-service;
    include nokia-conf-svc-vprn;
    include nokia-conf-system;
    include nokia-conf-system-security;
    include nokia-conf-system-security-tls;

    sros-ext:sros-major-release "rel24";
    organization "Nokia";
    contact
        "Nokia SR OS Support
         Web: <http://www.nokia.com>";
    description
        "Nokia YANG Data model to configure system security aaa parameters. on SR OS based routers.

         Copyright 2016 Nokia. All rights reserved. Reproduction of this document
         is authorized on the condition that the foregoing copyright notice is included.

         This nokia-conf-system-security-aaa YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";
    revision "2024-10-11";

    grouping conf-system-security-aaa {
        container aaa {
            description "Enter the aaa context";

            leaf health-check {
                type union {
                    type int32 {
                        range "6..1500";
                    }
                    type enumeration {
                        enum none                           { value 0; }
                    }
                }
                units "seconds";
                default "30";
                description "Polling interval of RADIUS, TACACS+, and LDAP servers";
            }

            leaf-list apply-groups {
                type leafref {
                    path "../../../../groups/group/name";
                }
                max-elements 8;
                ordered-by user;
                description "Apply a configuration group at this level";
            }

            leaf-list apply-groups-exclude {
                type leafref {
                    path "../../../../groups/group/name";
                }
                max-elements 8;
                ordered-by user;
                description "Exclude a configuration group at this level";
            }

            container remote-servers {
                description "Enter the remote-servers context";

                leaf-list apply-groups {
                    type leafref {
                        path "../../../../../groups/group/name";
                    }
                    max-elements 8;
                    ordered-by user;
                    description "Apply a configuration group at this level";
                }

                leaf-list apply-groups-exclude {
                    type leafref {
                        path "../../../../../groups/group/name";
                    }
                    max-elements 8;
                    ordered-by user;
                    description "Exclude a configuration group at this level";
                }

                container radius {
                    description "Enter the radius context";

                    leaf admin-state {
                        type types-sros:admin-state;
                        default "enable";
                        description "Administrative state of the authentication server";
                    }

                    leaf accounting {
                        type boolean;
                        default "false";
                        description "Enable RADIUS command accounting";
                    }

                    leaf accounting-port {
                        type uint32 {
                            range "1..65535";
                        }
                        default "1813";
                        description "Port number on RADIUS server for accounting requests";
                    }

                    leaf authorization {
                        type boolean;
                        default "false";
                        description "Enable RADIUS authorization";
                    }

                    leaf interactive-authentication {
                        type boolean;
                        default "false";
                        description "Enable RADIUS interactive authentication";
                    }

                    leaf server-retry {
                        type uint32 {
                            range "1..10";
                        }
                        default "3";
                        description "Number of attempts to retry contacting RADIUS server";
                    }

                    leaf server-timeout {
                        type uint32 {
                            range "1..90";
                        }
                        units "seconds";
                        default "3";
                        description "Time to wait for a response from the RADIUS server";
                    }

                    leaf port {
                        type uint32 {
                            range "1..65535";
                        }
                        default "1812";
                        description "UDP port number on which to contact RADIUS server";
                    }

                    leaf use-default-template {
                        type boolean;
                        default "false";
                        description "Apply the RADIUS default user template to RADIUS user";
                    }

                    leaf access-algorithm {
                        type enumeration {
                            enum direct                         { value 1; }
                            enum round-robin                    { value 2; }
                        }
                        default "direct";
                        description "Algorithm used to access the set of RADIUS servers";
                    }

                    leaf route-preference {
                        type types-security:aaa-route-preference;
                        default "both";
                        description "Route preference to reach the AAA server";
                    }

                    leaf-list apply-groups {
                        type leafref {
                            path "../../../../../../groups/group/name";
                        }
                        max-elements 8;
                        ordered-by user;
                        description "Apply a configuration group at this level";
                    }

                    leaf-list apply-groups-exclude {
                        type leafref {
                            path "../../../../../../groups/group/name";
                        }
                        max-elements 8;
                        ordered-by user;
                        description "Exclude a configuration group at this level";
                    }

                    list server {
                        key "index";
                        max-elements 5;
                        description "Enter the server list instance";

                        leaf index {
                            type uint32 {
                                range "1..5";
                            }
                            description "RADIUS server ID";
                        }

                        leaf address {
                            type types-sros:ip-unicast-address;
                            mandatory true;
                            description "IP address of the RADIUS server";
                        }

                        leaf authenticator {
                            type enumeration {
                                enum md5                            { value 1; }
                                enum sm3                            { value 2; }
                            }
                            default "md5";
                            description "Authenticator hash algorithm for the RADIUS server";
                        }

                        leaf secret {
                            type types-sros:encrypted-leaf {
                                length "1..115";
                            }
                            description "Secret key to access the RADIUS server";
                        }

                        leaf tls-client-profile {
                            type leafref {
                                path "../../../../../tls/client-tls-profile/client-profile-name";
                            }
                            description "TLS client profile for the RADIUS server";
                        }

                        leaf-list apply-groups {
                            type leafref {
                                path "../../../../../../../groups/group/name";
                            }
                            max-elements 8;
                            ordered-by user;
                            description "Apply a configuration group at this level";
                        }

                        leaf-list apply-groups-exclude {
                            type leafref {
                                path "../../../../../../../groups/group/name";
                            }
                            max-elements 8;
                            ordered-by user;
                            description "Exclude a configuration group at this level";
                        }

                    } // list server

                } // container radius

                container ldap {
                    description "Enter the ldap context";

                    leaf admin-state {
                        type types-sros:admin-state;
                        default "enable";
                        description "Administrative state of the LDAP operation protocol";
                    }

                    leaf public-key-authentication {
                        type boolean;
                        default "false";
                        description "Allow SSH public key authentication from LDAP server";
                    }

                    leaf server-retry {
                        type uint32 {
                            range "1..10";
                        }
                        default "3";
                        description "Number of attempts to retry contacting the LDAP server";
                    }

                    leaf server-timeout {
                        type types-sros:time-duration {
                            range "1..90";
                        }
                        units "seconds";
                        default "3";
                        description "Timeout for a response from the LDAP server";
                    }

                    leaf use-default-template {
                        type boolean;
                        default "true";
                        description "Apply the default template to LDAP";
                    }

                    leaf route-preference {
                        type types-security:aaa-route-preference;
                        default "both";
                        description "Route preference to reach the AAA server";
                    }

                    leaf-list apply-groups {
                        type leafref {
                            path "../../../../../../groups/group/name";
                        }
                        max-elements 8;
                        ordered-by user;
                        description "Apply a configuration group at this level";
                    }

                    leaf-list apply-groups-exclude {
                        type leafref {
                            path "../../../../../../groups/group/name";
                        }
                        max-elements 8;
                        ordered-by user;
                        description "Exclude a configuration group at this level";
                    }

                    list server {
                        key "index";
                        max-elements 5;
                        description "Enter the server list instance";

                        leaf index {
                            type uint32 {
                                range "1..5";
                            }
                            description "LDAP server ID";
                        }

                        leaf admin-state {
                            type types-sros:admin-state;
                            default "disable";
                            description "Administrative state of the LDAP server";
                        }

                        leaf server-name {
                            type types-sros:named-item;
                            description "LDAP server name";
                        }

                        leaf tls-profile {
                            type leafref {
                                path "../../../../../tls/client-tls-profile/client-profile-name";
                            }
                            description "TLS client profile used to encrypt the LDAP connection";
                        }

                        leaf-list apply-groups {
                            type leafref {
                                path "../../../../../../../groups/group/name";
                            }
                            max-elements 8;
                            ordered-by user;
                            description "Apply a configuration group at this level";
                        }

                        leaf-list apply-groups-exclude {
                            type leafref {
                                path "../../../../../../../groups/group/name";
                            }
                            max-elements 8;
                            ordered-by user;
                            description "Exclude a configuration group at this level";
                        }

                        list address {
                            key "ip-address";
                            max-elements 1;
                            description "Enter the address list instance";

                            leaf ip-address {
                                type types-sros:ip-unicast-address;
                                description "LDAP server address";
                            }

                            leaf port {
                                type int32 {
                                    range "1..65535";
                                }
                                default "389";
                                description "Port number on which to contact the LDAP server";
                            }

                            leaf-list apply-groups {
                                type leafref {
                                    path "../../../../../../../../groups/group/name";
                                }
                                max-elements 8;
                                ordered-by user;
                                description "Apply a configuration group at this level";
                            }

                            leaf-list apply-groups-exclude {
                                type leafref {
                                    path "../../../../../../../../groups/group/name";
                                }
                                max-elements 8;
                                ordered-by user;
                                description "Exclude a configuration group at this level";
                            }

                        } // list address

                        container bind-authentication {
                            description "Enter the bind-authentication context";

                            leaf root-dn {
                                type types-sros:string-not-all-spaces {
                                    length "1..512";
                                }
                                description "Root domain used for authentication with LDAP server";
                            }

                            leaf password {
                                type types-sros:encrypted-leaf {
                                    length "1..199";
                                }
                                description "Password used for authentication with the LDAP server";
                            }

                        } // container bind-authentication

                        container search {
                            description "Enter the search context";

                            leaf base-dn {
                                type types-sros:string-not-all-spaces {
                                    length "1..512";
                                }
                                description "LDAP server search base domain name";
                            }

                        } // container search

                    } // list server

                } // container ldap

                container tacplus {
                    description "Enter the tacplus context";

                    leaf interactive-authentication {
                        type boolean;
                        default "false";
                        description "Allows TACACS+ interactive authentication";
                    }

                    leaf admin-state {
                        type types-sros:admin-state;
                        default "enable";
                        description "Administrative state of the TACACS+ protocol";
                    }

                    leaf server-timeout {
                        type types-sros:time-duration {
                            range "1..90";
                        }
                        units "seconds";
                        default "3";
                        description "Time to wait for a response from the TACACS+ server";
                    }

                    leaf use-default-template {
                        type boolean;
                        default "true";
                        description "Apply TACACS+ default user-template to TACACS+ user";
                    }

                    leaf route-preference {
                        type types-security:aaa-route-preference;
                        default "both";
                        description "Route preference to reach the AAA server";
                    }

                    leaf-list apply-groups {
                        type leafref {
                            path "../../../../../../groups/group/name";
                        }
                        max-elements 8;
                        ordered-by user;
                        description "Apply a configuration group at this level";
                    }

                    leaf-list apply-groups-exclude {
                        type leafref {
                            path "../../../../../../groups/group/name";
                        }
                        max-elements 8;
                        ordered-by user;
                        description "Exclude a configuration group at this level";
                    }

                    container accounting {
                        presence "Enable the accounting context";
                        description "Enable the accounting context";

                        leaf record-type {
                            type enumeration {
                                enum start-stop                     { value 1; }
                                enum stop-only                      { value 2; }
                            }
                            default "stop-only";
                            description "Type of accounting record packet sent to TACACS+ server";
                        }

                    } // container accounting

                    container authorization {
                        presence "Enable the authorization context";
                        description "Enable the authorization context";

                        leaf use-priv-lvl {
                            type boolean;
                            default "false";
                            description "Allow privilege level mapping";
                        }

                        container request-format {
                            description "Enter the request-format context";

                            leaf-list access-operation-cmd {
                                type enumeration {
                                    enum delete                         { value 1; }
                                }
                                max-elements 1;
                                description "Access operations sent in authorization requests";
                            }

                        } // container request-format

                    } // container authorization

                    container admin-control {
                        description "Enter the admin-control context";

                        leaf tacplus-map-to-priv-lvl {
                            type int32 {
                                range "0..15";
                            }
                            description "Interactive authentication from node to TACACS+ server";
                        }

                    } // container admin-control

                    container priv-lvl-map {
                        description "Enter the priv-lvl-map context";

                        leaf-list apply-groups {
                            type leafref {
                                path "../../../../../../../groups/group/name";
                            }
                            max-elements 8;
                            ordered-by user;
                            description "Apply a configuration group at this level";
                        }

                        leaf-list apply-groups-exclude {
                            type leafref {
                                path "../../../../../../../groups/group/name";
                            }
                            max-elements 8;
                            ordered-by user;
                            description "Exclude a configuration group at this level";
                        }

                        list priv-lvl {
                            key "level";
                            description "Enter the priv-lvl list instance";

                            leaf level {
                                type uint32 {
                                    range "0..15";
                                }
                                description "Privilege level for the mapping";
                            }

                            leaf user-profile-name {
                                type leafref {
                                    path "../../../../../local-profiles/profile/user-profile-name";
                                }
                                mandatory true;
                                description "User profile for the mapping";
                            }

                            leaf-list apply-groups {
                                type leafref {
                                    path "../../../../../../../../groups/group/name";
                                }
                                max-elements 8;
                                ordered-by user;
                                description "Apply a configuration group at this level";
                            }

                            leaf-list apply-groups-exclude {
                                type leafref {
                                    path "../../../../../../../../groups/group/name";
                                }
                                max-elements 8;
                                ordered-by user;
                                description "Exclude a configuration group at this level";
                            }

                        } // list priv-lvl

                    } // container priv-lvl-map

                    container service-request {
                        description "Enter the service-request context";

                        leaf nokia-grpc-rpc-authorization {
                            type boolean;
                            default "false";
                            description "Request nokia-grpc-rpc-authorization service VSAs";
                        }

                        leaf nokia-netconf-base-op-authorization {
                            type boolean;
                            default "false";
                            description "Request nokia-netconf-base-op-authorization service VSAs";
                        }

                        leaf nokia-user {
                            type boolean;
                            default "false";
                            description "Request nokia-user service VSAs";
                        }

                    } // container service-request

                    list server {
                        key "index";
                        max-elements 5;
                        description "Enter the server list instance";

                        leaf index {
                            type uint32 {
                                range "1..5";
                            }
                            description "TACACS+ server ID";
                        }

                        leaf address {
                            type types-sros:ip-unicast-address;
                            mandatory true;
                            description "IP address of the TACACS+ server";
                        }

                        leaf port {
                            type types-qos:tcp-udp-match-port;
                            default "49";
                            description "TCP port ID on which to contact TACACS+ server";
                        }

                        leaf secret {
                            type types-sros:encrypted-leaf {
                                length "1..199";
                            }
                            mandatory true;
                            description "Secret key to access the TACACS+ server";
                        }

                        leaf-list apply-groups {
                            type leafref {
                                path "../../../../../../../groups/group/name";
                            }
                            max-elements 8;
                            ordered-by user;
                            description "Apply a configuration group at this level";
                        }

                        leaf-list apply-groups-exclude {
                            type leafref {
                                path "../../../../../../../groups/group/name";
                            }
                            max-elements 8;
                            ordered-by user;
                            description "Exclude a configuration group at this level";
                        }

                    } // list server

                } // container tacplus

                container vprn-server {
                    description "Enter the vprn-server context";

                    leaf inband {
                        type leafref {
                            path "../../../../../../service/vprn/service-name";
                        }
                        description "VPRN service used for AAA by in-band sessions";
                    }

                    leaf outband {
                        type leafref {
                            path "../../../../../../service/vprn/service-name";
                        }
                        description "VPRN service used for AAA by out-of-band sessions";
                    }

                    leaf vprn {
                        type leafref {
                            path "../../../../../../service/vprn/service-name";
                        }
                        description "VPRN used for AAA in VPRNs without a AAA server";
                    }

                    leaf-list apply-groups {
                        type leafref {
                            path "../../../../../../groups/group/name";
                        }
                        max-elements 8;
                        ordered-by user;
                        description "Apply a configuration group at this level";
                    }

                    leaf-list apply-groups-exclude {
                        type leafref {
                            path "../../../../../../groups/group/name";
                        }
                        max-elements 8;
                        ordered-by user;
                        description "Exclude a configuration group at this level";
                    }

                } // container vprn-server

            } // container remote-servers

            container local-profiles {
                description "Enter the local-profiles context";

                leaf-list apply-groups {
                    type leafref {
                        path "../../../../../groups/group/name";
                    }
                    max-elements 8;
                    ordered-by user;
                    description "Apply a configuration group at this level";
                }

                leaf-list apply-groups-exclude {
                    type leafref {
                        path "../../../../../groups/group/name";
                    }
                    max-elements 8;
                    ordered-by user;
                    description "Exclude a configuration group at this level";
                }

                list profile {
                    key "user-profile-name";
                    max-elements 128;
                    description "Enter the profile list instance";

                    leaf user-profile-name {
                        type types-sros:named-item {
                            pattern "[^ ]*" {
                                error-message "The name cannot contain spaces.";
                            }
                        }
                        description "User profile name";
                    }

                    leaf cli-session-group {
                        type leafref {
                            path "../../../cli-session-group/cli-session-group-name";
                        }
                        description "CLI session group to which the profile belongs";
                    }

                    leaf combined-max-sessions {
                        type types-system:session-limit;
                        description "Maximum number of concurrent SSH and Telnet sessions";
                    }

                    leaf ssh-max-sessions {
                        type types-system:session-limit;
                        description "Maximum number of concurrent SSH sessions";
                    }

                    leaf telnet-max-sessions {
                        type types-system:session-limit;
                        description "Maximum number of concurrent Telnet sessions";
                    }

                    leaf li {
                        type boolean;
                        default "false";
                        description "Allow lawful intercept profile ID";
                    }

                    leaf default-action {
                        type enumeration {
                            enum deny-all                       { value 1; }
                            enum permit-all                     { value 2; }
                            enum none                           { value 3; }
                            enum read-only-all                  { value 4; }
                        }
                        default "none";
                        description "Action for non-matching entry";
                    }

                    leaf-list apply-groups {
                        type leafref {
                            path "../../../../../../groups/group/name";
                        }
                        max-elements 8;
                        ordered-by user;
                        description "Apply a configuration group at this level";
                    }

                    leaf-list apply-groups-exclude {
                        type leafref {
                            path "../../../../../../groups/group/name";
                        }
                        max-elements 8;
                        ordered-by user;
                        description "Exclude a configuration group at this level";
                    }

                    list entry {
                        key "entry-id";
                        description "Enter the entry list instance";

                        leaf entry-id {
                            type uint32 {
                                range "1..9999";
                            }
                            description "User profile entry ID";
                        }

                        leaf description {
                            type types-sros:description;
                            description "Text description";
                        }

                        leaf match {
                            type types-sros:display-string;
                            description "Command to match the entry";
                        }

                        leaf action {
                            type enumeration {
                                enum deny                           { value 1; }
                                enum permit                         { value 2; }
                                enum none                           { value 3; }
                                enum read-only                      { value 4; }
                            }
                            default "none";
                            description "Action when a user command matches the entry";
                        }

                        leaf-list apply-groups {
                            type leafref {
                                path "../../../../../../../groups/group/name";
                            }
                            max-elements 8;
                            ordered-by user;
                            description "Apply a configuration group at this level";
                        }

                        leaf-list apply-groups-exclude {
                            type leafref {
                                path "../../../../../../../groups/group/name";
                            }
                            max-elements 8;
                            ordered-by user;
                            description "Exclude a configuration group at this level";
                        }

                    } // list entry

                    container grpc {
                        description "Enter the grpc context";

                        container rpc-authorization {
                            description "Enter the rpc-authorization context";

                            leaf gnmi-capabilities {
                                type types-system:permit-deny;
                                description "gNMI Capabilities RPC authorization";
                            }

                            leaf gnmi-get {
                                type types-system:permit-deny;
                                description "gNMI Get RPC authorization";
                            }

                            leaf gnmi-set {
                                type types-system:permit-deny;
                                description "gNMI Set RPC authorization";
                            }

                            leaf gnmi-subscribe {
                                type types-system:permit-deny;
                                description "gNMI Subscribe RPC authorization";
                            }

                            leaf gnoi-cert-mgmt-rotate {
                                type types-system:permit-deny;
                                default "deny";
                                description "gNOI Rotate RPC authorization";
                            }

                            leaf gnoi-cert-mgmt-install {
                                type types-system:permit-deny;
                                default "deny";
                                description "gNOI Install RPC authorization";
                            }

                            leaf gnoi-cert-mgmt-getcert {
                                type types-system:permit-deny;
                                default "deny";
                                description "gNOI GetCertificates RPC authorization";
                            }

                            leaf gnoi-cert-mgmt-revoke {
                                type types-system:permit-deny;
                                default "deny";
                                description "gNOI RevokeCertificates RPC authorization";
                            }

                            leaf gnoi-cert-mgmt-cangenerate {
                                type types-system:permit-deny;
                                default "deny";
                                description "gNOI CanGenerateCSR RPC authorization";
                            }

                            leaf gnoi-file-get {
                                type types-system:permit-deny;
                                description "gNOI File Get RPC authorization";
                            }

                            leaf gnoi-file-transfertoremote {
                                type types-system:permit-deny;
                                description "gNOI File TransferToRemote RPC authorization";
                            }

                            leaf gnoi-file-put {
                                type types-system:permit-deny;
                                description "gNOI File Put RPC authorization";
                            }

                            leaf gnoi-file-stat {
                                type types-system:permit-deny;
                                description "gNOI File Stat RPC authorization";
                            }

                            leaf gnoi-file-remove {
                                type types-system:permit-deny;
                                description "gNOI File Remove RPC authorization";
                            }

                            leaf gnoi-system-ping {
                                type types-system:permit-deny;
                                description "gNOI System Ping RPC authorization";
                            }

                            leaf gnoi-system-traceroute {
                                type types-system:permit-deny;
                                description "gNOI System Traceroute RPC authorization";
                            }

                            leaf gnoi-system-time {
                                type types-system:permit-deny;
                                description "gNOI System Time RPC authorization";
                            }

                            leaf gnoi-system-setpackage {
                                type types-system:permit-deny;
                                default "deny";
                                description "gNOI System SetPackage RPC authorization";
                            }

                            leaf gnoi-system-switchcontrolprocessor {
                                type types-system:permit-deny;
                                default "deny";
                                description "gNOI System SwitchControlProcessor RPC authorization";
                            }

                            leaf gnoi-system-reboot {
                                type types-system:permit-deny;
                                default "deny";
                                description "gNOI System Reboot RPC authorization";
                            }

                            leaf gnoi-system-rebootstatus {
                                type types-system:permit-deny;
                                default "deny";
                                description "gNOI System RebootStatus RPC authorization";
                            }

                            leaf gnoi-system-cancelreboot {
                                type types-system:permit-deny;
                                default "deny";
                                description "gNOI System CancelReboot RPC authorization";
                            }

                            leaf md-cli-session {
                                type types-system:permit-deny;
                                description "gNOI MdCli Session RPC authorization";
                            }

                            leaf rib-api-getversion {
                                type types-system:permit-deny;
                                description "RibApi GetVersion RPC authorization";
                            }

                            leaf rib-api-modify {
                                type types-system:permit-deny;
                                description "RibApi Modify RPC authorization";
                            }

                        } // container rpc-authorization

                    } // container grpc

                    container netconf {
                        description "Enter the netconf context";

                        container base-op-authorization {
                            description "Enter the base-op-authorization context";

                            leaf action {
                                type boolean;
                                default "false";
                                description "Allow the NETCONF <action> RPC";
                            }

                            leaf cancel-commit {
                                type boolean;
                                default "false";
                                description "Allow the NETCONF <cancel-commit> RPC";
                            }

                            leaf close-session {
                                type boolean;
                                default "false";
                                description "Allow the NETCONF <close-session> RPC";
                            }

                            leaf commit {
                                type boolean;
                                default "false";
                                description "Allow the NETCONF <commit> RPC";
                            }

                            leaf copy-config {
                                type boolean;
                                default "false";
                                description "Allow the NETCONF <copy-config> RPC";
                            }

                            leaf create-subscription {
                                type boolean;
                                default "false";
                                description "Allow the NETCONF <create-subscription> RPC";
                            }

                            leaf delete-config {
                                type boolean;
                                default "false";
                                description "Allow the NETCONF <delete-config> RPC";
                            }

                            leaf discard-changes {
                                type boolean;
                                default "false";
                                description "Allow the NETCONF <discard-changes> RPC";
                            }

                            leaf edit-config {
                                type boolean;
                                default "false";
                                description "Allow the NETCONF <edit-config> RPC";
                            }

                            leaf get {
                                type boolean;
                                default "false";
                                description "Allow the NETCONF <get> RPC";
                            }

                            leaf get-config {
                                type boolean;
                                default "false";
                                description "Allow the NETCONF <get-config> RPC";
                            }

                            leaf get-data {
                                type boolean;
                                default "false";
                                description "Allow the NETCONF <get-data> RPC";
                            }

                            leaf get-schema {
                                type boolean;
                                default "false";
                                description "Allow the NETCONF <get-schema> RPC";
                            }

                            leaf kill-session {
                                type boolean;
                                default "false";
                                description "Allow the NETCONF <kill-session> RPC";
                            }

                            leaf lock {
                                type boolean;
                                default "false";
                                description "Allow the NETCONF <lock> and <unlock> RPCs";
                            }

                            leaf validate {
                                type boolean;
                                default "false";
                                description "Allow the NETCONF <validate> RPC";
                            }

                        } // container base-op-authorization

                    } // container netconf

                } // list profile

            } // container local-profiles

            list user-template {
                key "user-template-name";
                description "Enter the user-template list instance";

                leaf user-template-name {
                    type enumeration {
                        enum ldap-default {
                            value 0;
                            description "Default LDAP user template";
                        }
                        enum radius-default {
                            value 1;
                            description "Default RADIUS user template";
                        }
                        enum tacplus-default {
                            value 2;
                            description "Default TACACS+ user template";
                        }
                    }
                    description "Default user template applied to the remote user";
                }

                leaf home-directory {
                    type types-sros:cflash-without-slot-url;
                    description "User local home directory based on the template";
                }

                leaf profile {
                    type types-sros:named-item {
                        pattern "[^ ]*" {
                            error-message "The profile name cannot contain spaces.";
                        }
                    }
                    description "User profile based on the template";
                }

                leaf restricted-to-home {
                    type boolean;
                    default "true";
                    description "Restrict file access to the home directory of the user";
                }

                leaf save-when-restricted {
                    type boolean;
                    default "true";
                    description "Save configurations when the user is restricted to home";
                }

                leaf-list apply-groups {
                    type leafref {
                        path "../../../../../groups/group/name";
                    }
                    max-elements 8;
                    ordered-by user;
                    description "Apply a configuration group at this level";
                }

                leaf-list apply-groups-exclude {
                    type leafref {
                        path "../../../../../groups/group/name";
                    }
                    max-elements 8;
                    ordered-by user;
                    description "Exclude a configuration group at this level";
                }

                container access {
                    description "Enter the access context";

                    leaf ftp {
                        type boolean;
                        default "false";
                        description "Allow FTP access";
                    }

                    leaf console {
                        type boolean;
                        default "true";
                        description "Allow Bluetooth, console port CLI, SCP/SFTP, SSH CLI, and Telnet CLI access";
                    }

                    leaf grpc {
                        type boolean;
                        default "false";
                        description "Allow gRPC access";
                    }

                    leaf netconf {
                        type boolean;
                        default "false";
                        description "Allow NETCONF access";
                    }

                    leaf li {
                        type boolean;
                        default "false";
                        description "Allow access to Lawful Intercept (LI) commands";
                    }

                    leaf scp-sftp {
                        type boolean;
                        default "false";
                        description "Allow SCP/SFTP access";
                    }

                    leaf console-port-cli {
                        type boolean;
                        default "false";
                        description "Allow console port CLI access";
                    }

                    leaf ssh-cli {
                        type boolean;
                        default "false";
                        description "Allow SSH CLI access";
                    }

                    leaf telnet-cli {
                        type boolean;
                        default "false";
                        description "Allow Telnet CLI access";
                    }

                    leaf bluetooth {
                        type boolean;
                        default "false";
                        description "Allow Bluetooth access";
                    }

                } // container access

                container console {
                    description "Enter the console context";

                    leaf login-exec {
                        type types-sros:string-not-all-spaces {
                            length "1..200";
                        }
                        description "File to execute when the user logs in";
                    }

                } // container console

            } // list user-template

            list cli-session-group {
                key "cli-session-group-name";
                max-elements 16;
                description "Enter the cli-session-group list instance";

                leaf cli-session-group-name {
                    type types-sros:named-item {
                        pattern "[^ ]*" {
                            error-message "The name cannot contain spaces.";
                        }
                    }
                    description "CLI session group name";
                }

                leaf description {
                    type types-sros:description;
                    description "Text description";
                }

                leaf combined-max-sessions {
                    type types-system:session-limit;
                    description "Maximum number of concurrent SSH and Telnet sessions";
                }

                leaf ssh-max-sessions {
                    type types-system:session-limit;
                    description "Maximum number of concurrent SSH sessions";
                }

                leaf telnet-max-sessions {
                    type types-system:session-limit;
                    description "Maximum number of concurrent Telnet sessions";
                }

                leaf-list apply-groups {
                    type leafref {
                        path "../../../../../groups/group/name";
                    }
                    max-elements 8;
                    ordered-by user;
                    description "Apply a configuration group at this level";
                }

                leaf-list apply-groups-exclude {
                    type leafref {
                        path "../../../../../groups/group/name";
                    }
                    max-elements 8;
                    ordered-by user;
                    description "Exclude a configuration group at this level";
                }

            } // list cli-session-group

            container management-interface {
                description "Enter the management-interface context";

                leaf-list apply-groups {
                    type leafref {
                        path "../../../../../groups/group/name";
                    }
                    max-elements 8;
                    ordered-by user;
                    description "Apply a configuration group at this level";
                }

                leaf-list apply-groups-exclude {
                    type leafref {
                        path "../../../../../groups/group/name";
                    }
                    max-elements 8;
                    ordered-by user;
                    description "Exclude a configuration group at this level";
                }

                container output-authorization {
                    description "Enter the output-authorization context";

                    leaf md-interfaces {
                        type boolean;
                        default "true";
                        description "Authorize output in model-driven interfaces";
                    }

                    leaf telemetry-data {
                        type boolean;
                        default "false";
                        description "Authorize dial-in telemetry output";
                    }

                } // container output-authorization

                container md-cli {
                    description "Enter the md-cli context";

                    leaf command-accounting-during-load {
                        type boolean;
                        default "true";
                        description "Perform file command accounting for load or rollback";
                    }

                } // container md-cli

            } // container management-interface

        } // container aaa

    } // grouping conf-system-security-aaa

}
