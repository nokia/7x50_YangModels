submodule nokia-conf-router-rsvp {

    yang-version "1.1";

    belongs-to nokia-conf { prefix "conf"; }

    import nokia-sros-yang-extensions     { prefix "sros-ext"; }
    import nokia-types-mpls               { prefix "types-mpls"; }
    import nokia-types-rsvp               { prefix "types-rsvp"; }
    import nokia-types-sros               { prefix "types-sros"; }

    include nokia-conf-groups;
    include nokia-conf-router;
    include nokia-conf-system;
    include nokia-conf-system-security;

    sros-ext:sros-major-release "rel24";
    organization "Nokia";
    contact
        "Nokia SR OS Support
         Web: <http://www.nokia.com>";
    description
        "Nokia YANG Data model to configure RSVP protocol on SR OS based routers.

         Copyright 2016 Nokia. All rights reserved. Reproduction of this document
         is authorized on the condition that the foregoing copyright notice is included.

         This nokia-conf-router-rsvp YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";
    revision "2022-05-04";

    grouping conf-router-rsvp {
        container rsvp {
            presence "Enable the rsvp context";
            description "Enable the rsvp context";

            leaf authentication-over-bypass {
                type boolean;
                default "false";
                description "Enable MD5 authentication over bypass LSP of PLR and MP";
            }

            leaf entropy-label-capability {
                type boolean;
                default "false";
                description "Allow receiving and processing of the entropy label and ELI on incoming packets of RSVP LSPs";
            }

            leaf graceful-shutdown {
                type boolean;
                default "false";
                description "Initiate a graceful shutdown of all RSVP interfaces on the node";
            }

            leaf implicit-null-label {
                type boolean;
                sros-ext:auto-restart-to-modify;
                default "false";
                description "Signal the implicit null option for all RSVP LSPs";
            }

            leaf keep-multiplier {
                type uint32 {
                    range "1..255";
                }
                default "3";
                description "Value for the keep-multiplier to declare a reservation or neighbor as down";
            }

            leaf include-node-id-in-rro {
                type boolean;
                default "false";
                description "Include the node-id sub-object in the RRO (Record Route Object) on the RSVP instance";
            }

            leaf p2mp-merge-point-abort-timer {
                type uint32 {
                    range "1..65535";
                }
                units "seconds";
                description "Merge pointer timer for abort timer";
            }

            leaf p2p-merge-point-abort-timer {
                type uint32 {
                    range "1..65535";
                }
                units "seconds";
                description "Merge pointer timer for P2P paths";
            }

            leaf preemption-timer {
                type uint32 {
                    range "0..1800";
                }
                units "seconds";
                default "300";
                description "Preemption timer for the MPLS instance";
            }

            leaf rapid-retransmit-time {
                type uint32 {
                    range "1..100";
                }
                units "deciseconds";
                default "5";
                description "Rapid retransmission interval to reliably deliver RSVP messages";
            }

            leaf rapid-retry-limit {
                type uint32 {
                    range "1..6";
                }
                default "3";
                description "Rapid retry limit to reliably deliver RSVP messages";
            }

            leaf refresh-reduction-over-bypass {
                type boolean;
                default "false";
                description "Enable refresh reduction capabilities over tunnels";
            }

            leaf refresh-time {
                type uint32 {
                    range "1..65535";
                }
                units "seconds";
                default "30";
                description "Interval between refresh messages";
            }

            leaf admin-state {
                type types-sros:admin-state;
                default "disable";
                description "Administrative state of RSVP";
            }

            leaf-list te-down-threshold {
                type types-rsvp:rsvp-te-threshold-level;
                max-elements 16;
                ordered-by user;
                description "Value for the te-down-threshold";
            }

            leaf-list te-up-threshold {
                type types-rsvp:rsvp-te-threshold-level;
                max-elements 16;
                ordered-by user;
                description "Value for the te-up-threshold";
            }

            leaf-list apply-groups {
                type leafref {
                    path "../../../groups/group/name";
                }
                max-elements 8;
                ordered-by user;
                description "Apply a configuration group at this level";
            }

            leaf-list apply-groups-exclude {
                type leafref {
                    path "../../../groups/group/name";
                }
                max-elements 8;
                ordered-by user;
                description "Exclude a configuration group at this level";
            }

            container graceful-restart {
                description "Enter the graceful-restart context";

                leaf max-recovery {
                    type uint32 {
                        range "1..1800";
                    }
                    units "seconds";
                    default "300";
                    description "Maximum time to wait before a graceful helper recovers the session";
                }

                leaf max-restart {
                    type uint32 {
                        range "1..300";
                    }
                    units "seconds";
                    default "120";
                    description "Maximum time that a graceful helper waits for session restart after the neighbor is considered down";
                }

            } // container graceful-restart

            container msg-pacing {
                presence "Enable the msg-pacing context";
                description "Enable the msg-pacing context";

                leaf max-burst {
                    type uint32 {
                        range "100..1000";
                    }
                    default "650";
                    description "Maximum RSVP messages that are sent over a specified period when message pacing is enabled";
                }

                leaf period {
                    type uint32 {
                        range "100..1000";
                    }
                    units "milliseconds";
                    default "100";
                    description "Time for RSVP message pacing";
                }

            } // container msg-pacing

            container te-threshold-update {
                presence "Enable the te-threshold-update context";
                description "Enable the te-threshold-update context";

                leaf on-cac-failure {
                    type boolean;
                    default "false";
                    description "CAC (Call Admission Control) failure-triggered IGP update";
                }

                leaf update-timer {
                    type uint32 {
                        range "1..300";
                    }
                    units "seconds";
                    description "Timer-based IGP updates";
                }

            } // container te-threshold-update

            container dbw-accounting {
                presence "Enable the dbw-accounting context";
                description "Enable the dbw-accounting context";

                leaf dbw-multiplier {
                    type uint32 {
                        range "0..1000";
                    }
                    units "percent";
                    default "100";
                    description "Dark Bandwidth multiplier";
                }

                leaf sample-interval {
                    type uint32 {
                        range "10..600";
                    }
                    units "seconds";
                    default "30";
                    description "Dark Bandwidth sample interval";
                }

                leaf sample-multiplier {
                    type uint32 {
                        range "1..10";
                    }
                    default "3";
                    description "Dark Bandwidth sample multiplier";
                }

                container up-threshold {
                    description "Enter the up-threshold context";

                    leaf percent {
                        type types-sros:percent;
                        default "0";
                        description "Minimum difference in percent between dark bandwidth and sampled data rate, to trigger IGP-TE update";
                    }

                    leaf bw {
                        type int32 {
                            range "0..1000000";
                        }
                        units "megabps";
                        description "Minimum difference in MRLB or MRB to trigger an update";
                    }

                } // container up-threshold

                container down-threshold {
                    description "Enter the down-threshold context";

                    leaf percent {
                        type types-sros:percent;
                        default "0";
                        description "Minimum difference in percent between dark bandwidth and sampled data rate, to trigger IGP-TE update";
                    }

                    leaf bw {
                        type int32 {
                            range "0..1000000";
                        }
                        units "megabps";
                        description "Minimum difference in MRLB or MRB to trigger an update";
                    }

                } // container down-threshold

            } // container dbw-accounting

            container diffserv-te {
                presence "Enable the diffserv-te context";
                description "Enable the diffserv-te context";

                leaf admission-control-model {
                    type enumeration {
                        enum mam                            { value 1; }
                        enum rdm                            { value 2; }
                    }
                    mandatory true;
                    description "Parameters for the DiffServ TE node";
                }

                leaf-list apply-groups {
                    type leafref {
                        path "../../../../groups/group/name";
                    }
                    max-elements 8;
                    ordered-by user;
                    description "Apply a configuration group at this level";
                }

                leaf-list apply-groups-exclude {
                    type leafref {
                        path "../../../../groups/group/name";
                    }
                    max-elements 8;
                    ordered-by user;
                    description "Exclude a configuration group at this level";
                }

                container class-type-bw {
                    description "Enter the class-type-bw context";

                    leaf ct0 {
                        type int32 {
                            range "0..100";
                        }
                        default "0";
                        description "RSVP interface bandwidth percentage for class type 0";
                    }

                    leaf ct1 {
                        type int32 {
                            range "0..100";
                        }
                        default "0";
                        description "RSVP interface bandwidth percentage for class type 1";
                    }

                    leaf ct2 {
                        type int32 {
                            range "0..100";
                        }
                        default "0";
                        description "RSVP interface bandwidth percentage for class type 2";
                    }

                    leaf ct3 {
                        type int32 {
                            range "0..100";
                        }
                        default "0";
                        description "RSVP interface bandwidth percentage for class type 3";
                    }

                    leaf ct4 {
                        type int32 {
                            range "0..100";
                        }
                        default "0";
                        description "RSVP interface bandwidth percentage for class type 4";
                    }

                    leaf ct5 {
                        type int32 {
                            range "0..100";
                        }
                        default "0";
                        description "RSVP interface bandwidth percentage for class type 5";
                    }

                    leaf ct6 {
                        type int32 {
                            range "0..100";
                        }
                        default "0";
                        description "RSVP interface bandwidth percentage for class type 6";
                    }

                    leaf ct7 {
                        type int32 {
                            range "0..100";
                        }
                        default "0";
                        description "RSVP interface bandwidth percentage for class type 7";
                    }

                } // container class-type-bw

                list fc {
                    key "fc-name";
                    description "Enter the fc list instance";

                    leaf fc-name {
                        type types-sros:fc-name;
                        description "Forwarding class for this mapping";
                    }

                    leaf class-type {
                        type types-mpls:class-type;
                        mandatory true;
                        description "Diff-Serv Class Type (CT) for an LSP";
                    }

                    leaf-list apply-groups {
                        type leafref {
                            path "../../../../../groups/group/name";
                        }
                        max-elements 8;
                        ordered-by user;
                        description "Apply a configuration group at this level";
                    }

                    leaf-list apply-groups-exclude {
                        type leafref {
                            path "../../../../../groups/group/name";
                        }
                        max-elements 8;
                        ordered-by user;
                        description "Exclude a configuration group at this level";
                    }

                } // list fc

                list te-class {
                    key "te-class-number";
                    description "Enter the te-class list instance";

                    leaf te-class-number {
                        type uint32 {
                            range "0..7";
                        }
                        description "TE class number";
                    }

                    leaf class-type {
                        type types-mpls:class-type;
                        sros-ext:immutable;
                        mandatory true;
                        description "Class type (CT) associated with the TE class";
                    }

                    leaf priority {
                        type types-mpls:priority;
                        sros-ext:immutable;
                        mandatory true;
                        description "TE class priority";
                    }

                    leaf-list apply-groups {
                        type leafref {
                            path "../../../../../groups/group/name";
                        }
                        max-elements 8;
                        ordered-by user;
                        description "Apply a configuration group at this level";
                    }

                    leaf-list apply-groups-exclude {
                        type leafref {
                            path "../../../../../groups/group/name";
                        }
                        max-elements 8;
                        ordered-by user;
                        description "Exclude a configuration group at this level";
                    }

                } // list te-class

            } // container diffserv-te

            list interface {
                key "interface-name";
                description "Enter the interface list instance";

                leaf interface-name {
                    type leafref {
                        path "../../../interface/interface-name";
                    }
                    description "Index for router RSVP interface";
                }

                leaf admin-state {
                    type types-sros:admin-state;
                    default "enable";
                    description "Administrative state of RSVP on the IP interface";
                }

                leaf authentication-keychain {
                    type leafref {
                        path "../../../../system/security/keychains/keychain/keychain-name";
                    }
                    description "TCP authentication keychain for the session";
                }

                leaf authentication-key {
                    type types-sros:encrypted-leaf {
                        length "1..51";
                    }
                    description "Authentication or hash key string";
                }

                leaf bfd-liveness {
                    type boolean;
                    default "false";
                    description "Enable BFD";
                }

                leaf graceful-restart-helper-mode {
                    type boolean;
                    default "false";
                    description "Enable graceful restart helper for the RSVP interface";
                }

                leaf graceful-shutdown {
                    type boolean;
                    default "false";
                    description "Initiate a graceful shutdown of RSVP interface";
                }

                leaf hello-interval {
                    type uint32 {
                        range "0..60";
                    }
                    units "seconds";
                    default "3";
                    description "Time between RSVP Hello messages";
                }

                leaf subscription {
                    type uint32 {
                        range "0..1000";
                    }
                    default "100";
                    description "Percentage of the link bandwidth to use for reservation";
                }

                leaf dbw-multiplier {
                    type int32 {
                        range "0..1000";
                    }
                    units "percent";
                    description "Dark bandwidth multiplier";
                }

                leaf implicit-null-label {
                    type boolean;
                    sros-ext:auto-restart-to-modify;
                    description "Signal the implicit null label value for all LSPs";
                }

                leaf-list apply-groups {
                    type leafref {
                        path "../../../../groups/group/name";
                    }
                    max-elements 8;
                    ordered-by user;
                    description "Apply a configuration group at this level";
                }

                leaf-list apply-groups-exclude {
                    type leafref {
                        path "../../../../groups/group/name";
                    }
                    max-elements 8;
                    ordered-by user;
                    description "Exclude a configuration group at this level";
                }

                container class-type-bw {
                    presence "Enable the class-type-bw context";
                    description "Enable the class-type-bw context";

                    leaf ct0 {
                        type int32 {
                            range "0..100";
                        }
                        description "Percentage of link bandwidth for class type (CT) 0";
                    }

                    leaf ct1 {
                        type int32 {
                            range "0..100";
                        }
                        description "Percentage of link bandwidth for class type (CT) 1";
                    }

                    leaf ct2 {
                        type int32 {
                            range "0..100";
                        }
                        description "Percentage of link bandwidth for class type (CT) 2";
                    }

                    leaf ct3 {
                        type int32 {
                            range "0..100";
                        }
                        description "Percentage of link bandwidth for class type (CT) 3";
                    }

                    leaf ct4 {
                        type int32 {
                            range "0..100";
                        }
                        description "Percentage of link bandwidth for class type (CT) 4";
                    }

                    leaf ct5 {
                        type int32 {
                            range "0..100";
                        }
                        description "Percentage of link bandwidth for class type (CT) 5";
                    }

                    leaf ct6 {
                        type int32 {
                            range "0..100";
                        }
                        description "Percentage of link bandwidth for class type (CT) 6";
                    }

                    leaf ct7 {
                        type int32 {
                            range "0..100";
                        }
                        description "Percentage of link bandwidth for class type (CT) 7";
                    }

                } // container class-type-bw

                container refresh-reduction {
                    presence "Enable the refresh-reduction context";
                    description "Enable the refresh-reduction context";

                    leaf reliable-delivery {
                        type boolean;
                        default "false";
                        description "Reliable delivery of RSVP messages over the RSVP interface";
                    }

                } // container refresh-reduction

                container dbw-up-threshold {
                    presence "Enable the dbw-up-threshold context";
                    description "Enable the dbw-up-threshold context";

                    leaf percent {
                        type int32 {
                            range "0..100";
                        }
                        units "percent";
                        description "Minimum difference in percent between dark bandwidth and sampled data rate, to trigger IGP-TE update";
                    }

                    leaf bw {
                        type int32 {
                            range "0..1000000";
                        }
                        units "megabps";
                        description "Minimum difference in MRLB or MRB to trigger an update";
                    }

                } // container dbw-up-threshold

                container dbw-down-threshold {
                    presence "Enable the dbw-down-threshold context";
                    description "Enable the dbw-down-threshold context";

                    leaf percent {
                        type int32 {
                            range "0..100";
                        }
                        units "percent";
                        description "Minimum difference in percent between dark bandwidth and sampled data rate, to trigger IGP-TE update";
                    }

                    leaf bw {
                        type int32 {
                            range "0..1000000";
                        }
                        units "megabps";
                        description "Minimum difference in MRLB or MRB to trigger an update";
                    }

                } // container dbw-down-threshold

                container te-down-threshold {
                    presence "Enable the te-down-threshold context";
                    description "Enable the te-down-threshold context";

                    leaf-list value {
                        type types-rsvp:rsvp-te-threshold-level;
                        min-elements 1;
                        max-elements 16;
                        ordered-by user;
                        description "Threshold level per interface";
                    }

                    leaf-list apply-groups {
                        type leafref {
                            path "../../../../../groups/group/name";
                        }
                        max-elements 8;
                        ordered-by user;
                        description "Apply a configuration group at this level";
                    }

                    leaf-list apply-groups-exclude {
                        type leafref {
                            path "../../../../../groups/group/name";
                        }
                        max-elements 8;
                        ordered-by user;
                        description "Exclude a configuration group at this level";
                    }

                } // container te-down-threshold

                container te-up-threshold {
                    presence "Enable the te-up-threshold context";
                    description "Enable the te-up-threshold context";

                    leaf-list value {
                        type types-rsvp:rsvp-te-threshold-level;
                        min-elements 1;
                        max-elements 16;
                        ordered-by user;
                        description "Threshold level per interface";
                    }

                    leaf-list apply-groups {
                        type leafref {
                            path "../../../../../groups/group/name";
                        }
                        max-elements 8;
                        ordered-by user;
                        description "Apply a configuration group at this level";
                    }

                    leaf-list apply-groups-exclude {
                        type leafref {
                            path "../../../../../groups/group/name";
                        }
                        max-elements 8;
                        ordered-by user;
                        description "Exclude a configuration group at this level";
                    }

                } // container te-up-threshold

            } // list interface

        } // container rsvp

    } // grouping conf-router-rsvp

}
