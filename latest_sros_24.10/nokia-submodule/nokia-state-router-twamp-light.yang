submodule nokia-state-router-twamp-light {

    yang-version "1.1";

    belongs-to nokia-state { prefix "state"; }

    import ietf-yang-types                { prefix "yang"; }
    import nokia-sros-yang-extensions     { prefix "sros-ext"; }

    sros-ext:sros-major-release "rel24";
    organization "Nokia";
    contact
        "Nokia SR OS Support
         Web: <http://www.nokia.com>";
    description
        "Nokia YANG Data model with operational state for  OAM Performance Monitoring TWAMP-Light (Two-Way Active Measurement Protocol, Light) on SR OS based routers.

         Copyright 2016 Nokia. All rights reserved. Reproduction of this document
         is authorized on the condition that the foregoing copyright notice is included.

         This nokia-state-router-twamp-light YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";
    revision "2024-03-01";

    grouping state-router-twamp-light {
        container twamp-light {
            description "Enter the twamp-light context";

            container reflector {
                description "Enter the reflector context";

                leaf up-time {
                    type uint32;
                    units "seconds";
                    description "Time elapsed since the most recent transition of the reflector's administrative status to enabled";
                }

                leaf test-frames-received {
                    type yang:counter32;
                    description "TWAMP-Test frames received by the specified reflector";
                }

                leaf test-frames-sent {
                    type yang:counter32;
                    description "TWAMP-Test frames transmitted by the specified reflector";
                }

            } // container reflector

        } // container twamp-light

    } // grouping state-router-twamp-light

}
