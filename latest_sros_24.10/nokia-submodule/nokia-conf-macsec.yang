submodule nokia-conf-macsec {

    yang-version "1.1";

    belongs-to nokia-conf { prefix "conf"; }

    import ietf-yang-types                { prefix "yang"; }
    import nokia-sros-yang-extensions     { prefix "sros-ext"; }
    import nokia-types-security           { prefix "types-security"; }
    import nokia-types-sros               { prefix "types-sros"; }

    include nokia-conf-groups;

    sros-ext:sros-major-release "rel24";
    organization "Nokia";
    contact
        "Nokia SR OS Support
         Web: <http://www.nokia.com>";
    description
        "Nokia YANG Data model to configure MACsec connectivity-association configuration on SR OS based routers.

         Copyright 2016 Nokia. All rights reserved. Reproduction of this document
         is authorized on the condition that the foregoing copyright notice is included.

         This nokia-conf-macsec YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";
    revision "2025-05-30";

    grouping conf-macsec {
        container macsec {
            description "Enter the macsec context";

            leaf-list apply-groups {
                type leafref {
                    path "../../groups/group/name";
                }
                max-elements 8;
                ordered-by user;
                description "Apply a configuration group at this level";
            }

            leaf-list apply-groups-exclude {
                type leafref {
                    path "../../groups/group/name";
                }
                max-elements 8;
                ordered-by user;
                description "Exclude a configuration group at this level";
            }

            list connectivity-association {
                key "ca-name";
                description "Enter the connectivity-association list instance";

                leaf ca-name {
                    type string {
                        length "1..32";
                    }
                    description "Connectivity association name";
                }

                leaf admin-state {
                    type types-sros:admin-state;
                    default "disable";
                    description "Administrative state of the connectivity association";
                }

                leaf description {
                    type string {
                        length "1..80";
                    }
                    description "Text description";
                }

                leaf replay-window-size {
                    type uint32 {
                        range "0..4294967294";
                    }
                    sros-ext:auto-restart-to-modify;
                    default "0";
                    description "Replay protection window size";
                }

                leaf replay-protection {
                    type boolean;
                    sros-ext:auto-restart-to-modify;
                    default "false";
                    description "Discard packet when not within the replay window size";
                }

                leaf macsec-encrypt {
                    type boolean;
                    default "true";
                    description "Encrypt and authenticate all PDUs";
                }

                leaf clear-tag-mode {
                    type enumeration {
                        enum none                           { value 0; }
                        enum single-tag                     { value 1; }
                        enum dual-tag                       { value 2; }
                    }
                    sros-ext:auto-restart-to-modify;
                    default "none";
                    description "Clear tag mode for clear text before the SecTAG";
                }

                leaf encryption-offset {
                    type uint32 {
                        range "0|30|50";
                    }
                    default "0";
                    description "Confidentiality (encryption) offset";
                }

                leaf cipher-suite {
                    type enumeration {
                        enum gcm-aes-128                    { value 1; }
                        enum gcm-aes-256                    { value 2; }
                        enum gcm-aes-xpn-128                { value 3; }
                        enum gcm-aes-xpn-256                { value 4; }
                    }
                    default "gcm-aes-128";
                    description "Data path encryption algorithm";
                }

                leaf delay-protection {
                    type boolean;
                    sros-ext:auto-restart-to-modify;
                    default "false";
                    description "Enable delay protection";
                }

                leaf anysec {
                    type boolean;
                    sros-ext:auto-restart-to-modify;
                    default "false";
                    description "Mark the CA for use by ANYsec encryption only";
                }

                leaf-list apply-groups {
                    type leafref {
                        path "../../../groups/group/name";
                    }
                    max-elements 8;
                    ordered-by user;
                    description "Apply a configuration group at this level";
                }

                leaf-list apply-groups-exclude {
                    type leafref {
                        path "../../../groups/group/name";
                    }
                    max-elements 8;
                    ordered-by user;
                    description "Exclude a configuration group at this level";
                }

                container static-cak {
                    description "Enter the static-cak context";

                    leaf active-psk {
                        type uint32 {
                            range "1..2";
                        }
                        default "1";
                        description "Active pre-shared-key (PSK)";
                    }

                    leaf mka-hello-interval {
                        type enumeration {
                            enum 1                              { value 1; }
                            enum 2                              { value 2; }
                            enum 3                              { value 3; }
                            enum 4                              { value 4; }
                            enum 5                              { value 5; }
                            enum 6                              { value 6; }
                            enum 500ms                          { value 500; }
                        }
                        default "2";
                        description "MKA hello interval";
                    }

                    leaf mka-key-server-priority {
                        type uint32 {
                            range "0..255";
                        }
                        default "16";
                        description "Key server priority used by the MKA protocol";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                    list pre-shared-key {
                        key "psk-id";
                        max-elements 2;
                        description "Enter the pre-shared-key list instance";

                        leaf psk-id {
                            type uint32 {
                                range "1..2";
                            }
                            description "Pre-shared-key (PSK) ID";
                        }

                        leaf encryption-type {
                            type enumeration {
                                enum aes-128-cmac                   { value 1; }
                                enum aes-256-cmac                   { value 2; }
                            }
                            mandatory true;
                            description "Encryption for authentication of the MKA packet";
                        }

                        leaf cak {
                            type types-sros:encrypted-leaf-hex-without-prefix {
                                length "1..71";
                            }
                            description "Connectivity association key (CAK) for the PSK";
                        }

                        leaf cak-name {
                            type types-security:cak-name;
                            description "Connectivity association key name (CKN) for the PSK";
                        }

                        leaf-list apply-groups {
                            type leafref {
                                path "../../../../../groups/group/name";
                            }
                            max-elements 8;
                            ordered-by user;
                            description "Apply a configuration group at this level";
                        }

                        leaf-list apply-groups-exclude {
                            type leafref {
                                path "../../../../../groups/group/name";
                            }
                            max-elements 8;
                            ordered-by user;
                            description "Exclude a configuration group at this level";
                        }

                    } // list pre-shared-key

                } // container static-cak

            } // list connectivity-association

            list mac-policy {
                key "mac-policy-id";
                description "Enter the mac-policy list instance";

                leaf mac-policy-id {
                    type uint32;
                    description "MAC address policy ID";
                }

                leaf-list apply-groups {
                    type leafref {
                        path "../../../groups/group/name";
                    }
                    max-elements 8;
                    ordered-by user;
                    description "Apply a configuration group at this level";
                }

                leaf-list apply-groups-exclude {
                    type leafref {
                        path "../../../groups/group/name";
                    }
                    max-elements 8;
                    ordered-by user;
                    description "Exclude a configuration group at this level";
                }

                list destination-mac-address {
                    key "dest-mac-addr";
                    max-elements 5;
                    description "Add a list entry for destination-mac-address";

                    leaf dest-mac-addr {
                        type yang:mac-address;
                        description "Destination MAC address added to the MAC policy";
                    }

                } // list destination-mac-address

            } // list mac-policy

        } // container macsec

    } // grouping conf-macsec

}
