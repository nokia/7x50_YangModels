submodule nokia-state-port-eth-egress {

    yang-version "1.1";

    belongs-to nokia-state { prefix "state"; }

    import ietf-yang-types                { prefix "yang"; }
    import nokia-sros-yang-extensions     { prefix "sros-ext"; }
    import nokia-types-qos                { prefix "types-qos"; }
    import nokia-types-sros               { prefix "types-sros"; }

    sros-ext:sros-major-release "rel24";
    organization "Nokia";
    contact
        "Nokia SR OS Support
         Web: <http://www.nokia.com>";
    description
        "Nokia YANG Data model with operational state for egress capabilities for ethernet ports on SR OS based routers.

         Copyright 2016 Nokia. All rights reserved. Reproduction of this document
         is authorized on the condition that the foregoing copyright notice is included.

         This nokia-state-port-eth-egress YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";
    revision "2024-06-27";

    grouping state-port-eth-egress {
        container egress {
            description "Enter the egress context";

            container port-scheduler-policy {
                description "Enter the port-scheduler-policy context";

                container statistics {
                    description "Enter the statistics context";

                    leaf total-forwarded-octets {
                        type yang:counter64;
                        description "Indicates the total number of octets forwarded.";
                    }

                    leaf total-forwarded-packets {
                        type yang:counter64;
                        description "Indicates the total number of packets forwarded.";
                    }

                    leaf total-dropped-octets {
                        type yang:counter64;
                        description "Indicates the total number of octets dropped.";
                    }

                    leaf total-dropped-packets {
                        type yang:counter64;
                        description "Indicates the total number of packets dropped.";
                    }

                    list level {
                        key "priority-level";
                        description "Enter the level list instance";

                        leaf priority-level {
                            type uint32 {
                                range "1..8";
                            }
                            description "Specifies the priority level of the port scheduler policy.";
                        }

                        leaf forwarded-octets {
                            type yang:counter64;
                            description "Indicates the number of octets forwarded for this level.";
                        }

                        leaf forwarded-packets {
                            type yang:counter64;
                            description "Indicates the number of packets forwarded for this level.";
                        }

                        leaf dropped-octets {
                            type yang:counter64;
                            description "Indicates the number of octets dropped for this level.";
                        }

                        leaf dropped-packets {
                            type yang:counter64;
                            description "Indicates the number of packets dropped for this level.";
                        }

                    } // list level

                } // container statistics

                container port-scheduler {
                    description "Enter the port-scheduler context";

                    leaf max-rate {
                        type types-qos:kbps;
                        units "kilobps";
                        description "Max rate";
                    }

                    leaf port-bandwidth {
                        type types-qos:kbps;
                        units "kilobps";
                        description "Port Bandwidth";
                    }

                    leaf consumed-rate {
                        type types-qos:kbps;
                        units "kilobps";
                        description "Consumed rate";
                    }

                    leaf offered-rate {
                        type types-qos:kbps;
                        units "kilobps";
                        description "Offered rate";
                    }

                    list group {
                        key "group-name";
                        description "Enter the group list instance";

                        leaf group-name {
                            type string;
                            description "Name";
                        }

                        container sched-hierarchy {
                            description "Enter the sched-hierarchy context";

                            list level {
                                key "level-index";
                                description "Enter the level list instance";

                                leaf level-index {
                                    type int32 {
                                        range "0..8";
                                    }
                                }

                            } // list level

                        } // container sched-hierarchy

                        container within-cir {
                            description "Enter the within-cir context";

                            leaf rate {
                                type types-qos:kbps;
                                units "kilobps";
                                description "Rate";
                            }

                            leaf consumed {
                                type types-qos:kbps;
                                units "kilobps";
                                description "Consumed";
                            }

                            leaf offered {
                                type types-qos:kbps;
                                units "kilobps";
                                description "Offered";
                            }

                        } // container within-cir

                        container above-cir {
                            description "Enter the above-cir context";

                            leaf rate {
                                type types-qos:kbps;
                                units "kilobps";
                                description "Rate";
                            }

                            leaf consumed {
                                type types-qos:kbps;
                                units "kilobps";
                                description "Consumed";
                            }

                            leaf offered {
                                type types-qos:kbps;
                                units "kilobps";
                                description "Offered";
                            }

                        } // container above-cir

                    } // list group

                    list level {
                        key "level-index";
                        description "Enter the level list instance";

                        leaf level-index {
                            type int32 {
                                range "0..8";
                            }
                        }

                        container within-cir {
                            description "Enter the within-cir context";

                            leaf rate {
                                type types-qos:kbps;
                                units "kilobps";
                                description "Rate";
                            }

                            leaf consumed {
                                type types-qos:kbps;
                                units "kilobps";
                                description "Consumed";
                            }

                            leaf offered {
                                type types-qos:kbps;
                                units "kilobps";
                                description "Offered";
                            }

                            container sched-hierarchy {
                                description "Enter the sched-hierarchy context";

                                container queue {
                                    description "Enter the queue context";

                                    container port-queue-group {
                                        description "Enter the port-queue-group context";

                                        list queue {
                                            key "member";
                                            description "Enter the queue list instance";

                                            leaf member {
                                                type uint32;
                                                description "Member information";
                                            }

                                            leaf queue-id {
                                                type int32;
                                                description "Queue identifier";
                                            }

                                            leaf port {
                                                type types-sros:port;
                                                description "Port identifier";
                                            }

                                            leaf port-mode {
                                                type enumeration {
                                                    enum access                         { value 1; }
                                                    enum network                        { value 2; }
                                                }
                                                description "Port mode";
                                            }

                                            leaf queue-group-template {
                                                type string;
                                                description "Queue group template";
                                            }

                                            leaf queue-group-instance {
                                                type int32;
                                                description "Queue group instance";
                                            }

                                        } // list queue

                                    } // container port-queue-group

                                    container sap {
                                        description "Enter the sap context";

                                        list queue {
                                            key "member";
                                            description "Enter the queue list instance";

                                            leaf member {
                                                type uint32;
                                                description "Member information";
                                            }

                                            leaf queue-id {
                                                type int32;
                                                description "Queue identifier";
                                            }

                                            leaf sap-id {
                                                type types-sros:sap;
                                                description "SAP identifier";
                                            }

                                            leaf port {
                                                type types-sros:port;
                                                description "Port identifier";
                                            }

                                        } // list queue

                                    } // container sap

                                    container network {
                                        description "Enter the network context";

                                        list queue {
                                            key "member";
                                            description "Enter the queue list instance";

                                            leaf member {
                                                type uint32;
                                                description "Member information";
                                            }

                                            leaf queue-id {
                                                type int32;
                                                description "Queue identifier";
                                            }

                                            leaf port {
                                                type types-sros:port;
                                                description "Port identifier";
                                            }

                                        } // list queue

                                    } // container network

                                } // container queue

                                container scheduler {
                                    description "Enter the scheduler context";

                                    container sap {
                                        description "Enter the sap context";

                                        list scheduler {
                                            key "member";
                                            description "Enter the scheduler list instance";

                                            leaf member {
                                                type uint32;
                                                description "Member information";
                                            }

                                            leaf scheduler-name {
                                                type string;
                                                description "Name";
                                            }

                                            leaf sap-id {
                                                type types-sros:sap;
                                                description "SAP identifier";
                                            }

                                        } // list scheduler

                                    } // container sap

                                    container vport {
                                        description "Enter the vport context";

                                        list scheduler {
                                            key "member";
                                            description "Enter the scheduler list instance";

                                            leaf member {
                                                type uint32;
                                                description "Member information";
                                            }

                                            leaf scheduler-name {
                                                type string;
                                                description "Name";
                                            }

                                            leaf vport-name {
                                                type types-sros:named-item-or-empty;
                                                description "Virtual port name";
                                            }

                                        } // list scheduler

                                    } // container vport

                                } // container scheduler

                            } // container sched-hierarchy

                        } // container within-cir

                        container above-cir {
                            description "Enter the above-cir context";

                            leaf rate {
                                type types-qos:kbps;
                                units "kilobps";
                                description "Rate";
                            }

                            leaf consumed {
                                type types-qos:kbps;
                                units "kilobps";
                                description "Consumed";
                            }

                            leaf offered {
                                type types-qos:kbps;
                                units "kilobps";
                                description "Offered";
                            }

                            container sched-hierarchy {
                                description "Enter the sched-hierarchy context";

                                container queue {
                                    description "Enter the queue context";

                                    container port-queue-group {
                                        description "Enter the port-queue-group context";

                                        list queue {
                                            key "member";
                                            description "Enter the queue list instance";

                                            leaf member {
                                                type uint32;
                                                description "Member information";
                                            }

                                            leaf queue-id {
                                                type int32;
                                                description "Queue identifier";
                                            }

                                            leaf port {
                                                type types-sros:port;
                                                description "Port identifier";
                                            }

                                            leaf port-mode {
                                                type enumeration {
                                                    enum access                         { value 1; }
                                                    enum network                        { value 2; }
                                                }
                                                description "Port mode";
                                            }

                                            leaf queue-group-template {
                                                type string;
                                                description "Queue group template";
                                            }

                                            leaf queue-group-instance {
                                                type int32;
                                                description "Queue group instance";
                                            }

                                        } // list queue

                                    } // container port-queue-group

                                    container sap {
                                        description "Enter the sap context";

                                        list queue {
                                            key "member";
                                            description "Enter the queue list instance";

                                            leaf member {
                                                type uint32;
                                                description "Member information";
                                            }

                                            leaf queue-id {
                                                type int32;
                                                description "Queue identifier";
                                            }

                                            leaf sap-id {
                                                type types-sros:sap;
                                                description "SAP identifier";
                                            }

                                            leaf port {
                                                type types-sros:port;
                                                description "Port identifier";
                                            }

                                        } // list queue

                                    } // container sap

                                    container network {
                                        description "Enter the network context";

                                        list queue {
                                            key "member";
                                            description "Enter the queue list instance";

                                            leaf member {
                                                type uint32;
                                                description "Member information";
                                            }

                                            leaf queue-id {
                                                type int32;
                                                description "Queue identifier";
                                            }

                                            leaf port {
                                                type types-sros:port;
                                                description "Port identifier";
                                            }

                                        } // list queue

                                    } // container network

                                } // container queue

                                container scheduler {
                                    description "Enter the scheduler context";

                                    container sap {
                                        description "Enter the sap context";

                                        list scheduler {
                                            key "member";
                                            description "Enter the scheduler list instance";

                                            leaf member {
                                                type uint32;
                                                description "Member information";
                                            }

                                            leaf scheduler-name {
                                                type string;
                                                description "Name";
                                            }

                                            leaf sap-id {
                                                type types-sros:sap;
                                                description "SAP identifier";
                                            }

                                        } // list scheduler

                                    } // container sap

                                    container vport {
                                        description "Enter the vport context";

                                        list scheduler {
                                            key "member";
                                            description "Enter the scheduler list instance";

                                            leaf member {
                                                type uint32;
                                                description "Member information";
                                            }

                                            leaf scheduler-name {
                                                type string;
                                                description "Name";
                                            }

                                            leaf vport-name {
                                                type types-sros:named-item-or-empty;
                                                description "Virtual port name";
                                            }

                                        } // list scheduler

                                    } // container vport

                                } // container scheduler

                            } // container sched-hierarchy

                        } // container above-cir

                    } // list level

                } // container port-scheduler

                container lag-port-scheduler {
                    description "Enter the lag-port-scheduler context";

                    leaf max-rate {
                        type types-qos:kbps;
                        units "kilobps";
                        description "Max rate";
                    }

                    leaf port-bandwidth {
                        type types-qos:kbps;
                        units "kilobps";
                        description "Port Bandwidth";
                    }

                    leaf consumed-rate {
                        type types-qos:kbps;
                        units "kilobps";
                        description "Consumed rate";
                    }

                    leaf offered-rate {
                        type types-qos:kbps;
                        units "kilobps";
                        description "Offered rate";
                    }

                    leaf lag-name {
                        type types-sros:lag-interface;
                        description "LAG Name always to start with lag-";
                    }

                    list group {
                        key "group-name";
                        description "Enter the group list instance";

                        leaf group-name {
                            type string;
                            description "Name";
                        }

                        container sched-hierarchy {
                            description "Enter the sched-hierarchy context";

                            list level {
                                key "level-index";
                                description "Enter the level list instance";

                                leaf level-index {
                                    type int32 {
                                        range "0..8";
                                    }
                                }

                            } // list level

                        } // container sched-hierarchy

                        container within-cir {
                            description "Enter the within-cir context";

                            leaf rate {
                                type types-qos:kbps;
                                units "kilobps";
                                description "Rate";
                            }

                            leaf consumed {
                                type types-qos:kbps;
                                units "kilobps";
                                description "Consumed";
                            }

                            leaf offered {
                                type types-qos:kbps;
                                units "kilobps";
                                description "Offered";
                            }

                        } // container within-cir

                        container above-cir {
                            description "Enter the above-cir context";

                            leaf rate {
                                type types-qos:kbps;
                                units "kilobps";
                                description "Rate";
                            }

                            leaf consumed {
                                type types-qos:kbps;
                                units "kilobps";
                                description "Consumed";
                            }

                            leaf offered {
                                type types-qos:kbps;
                                units "kilobps";
                                description "Offered";
                            }

                        } // container above-cir

                    } // list group

                    list level {
                        key "level-index";
                        description "Enter the level list instance";

                        leaf level-index {
                            type int32 {
                                range "0..8";
                            }
                        }

                        container within-cir {
                            description "Enter the within-cir context";

                            leaf rate {
                                type types-qos:kbps;
                                units "kilobps";
                                description "Rate";
                            }

                            leaf consumed {
                                type types-qos:kbps;
                                units "kilobps";
                                description "Consumed";
                            }

                            leaf offered {
                                type types-qos:kbps;
                                units "kilobps";
                                description "Offered";
                            }

                            container sched-hierarchy {
                                description "Enter the sched-hierarchy context";

                                container queue {
                                    description "Enter the queue context";

                                    container port-queue-group {
                                        description "Enter the port-queue-group context";

                                        list queue {
                                            key "member";
                                            description "Enter the queue list instance";

                                            leaf member {
                                                type uint32;
                                                description "Member information";
                                            }

                                            leaf queue-id {
                                                type int32;
                                                description "Queue identifier";
                                            }

                                            leaf port {
                                                type types-sros:port;
                                                description "Port identifier";
                                            }

                                            leaf port-mode {
                                                type enumeration {
                                                    enum access                         { value 1; }
                                                    enum network                        { value 2; }
                                                }
                                                description "Port mode";
                                            }

                                            leaf queue-group-template {
                                                type string;
                                                description "Queue group template";
                                            }

                                            leaf queue-group-instance {
                                                type int32;
                                                description "Queue group instance";
                                            }

                                        } // list queue

                                    } // container port-queue-group

                                    container sap {
                                        description "Enter the sap context";

                                        list queue {
                                            key "member";
                                            description "Enter the queue list instance";

                                            leaf member {
                                                type uint32;
                                                description "Member information";
                                            }

                                            leaf queue-id {
                                                type int32;
                                                description "Queue identifier";
                                            }

                                            leaf sap-id {
                                                type types-sros:sap;
                                                description "SAP identifier";
                                            }

                                            leaf port {
                                                type types-sros:port;
                                                description "Port identifier";
                                            }

                                        } // list queue

                                    } // container sap

                                } // container queue

                                container scheduler {
                                    description "Enter the scheduler context";

                                    container sap {
                                        description "Enter the sap context";

                                        list scheduler {
                                            key "member";
                                            description "Enter the scheduler list instance";

                                            leaf member {
                                                type uint32;
                                                description "Member information";
                                            }

                                            leaf scheduler-name {
                                                type string;
                                                description "Name";
                                            }

                                            leaf sap-id {
                                                type types-sros:sap;
                                                description "SAP identifier";
                                            }

                                        } // list scheduler

                                        list t0-scheduler {
                                            key "member";
                                            description "Enter the t0-scheduler list instance";

                                            leaf member {
                                                type uint32;
                                                description "Member information";
                                            }

                                            leaf scheduler-name {
                                                type string;
                                                description "Name";
                                            }

                                            leaf sap-id {
                                                type types-sros:sap;
                                                description "SAP identifier";
                                            }

                                        } // list t0-scheduler

                                    } // container sap

                                } // container scheduler

                            } // container sched-hierarchy

                        } // container within-cir

                        container above-cir {
                            description "Enter the above-cir context";

                            leaf rate {
                                type types-qos:kbps;
                                units "kilobps";
                                description "Rate";
                            }

                            leaf consumed {
                                type types-qos:kbps;
                                units "kilobps";
                                description "Consumed";
                            }

                            leaf offered {
                                type types-qos:kbps;
                                units "kilobps";
                                description "Offered";
                            }

                            container sched-hierarchy {
                                description "Enter the sched-hierarchy context";

                                container queue {
                                    description "Enter the queue context";

                                    container port-queue-group {
                                        description "Enter the port-queue-group context";

                                        list queue {
                                            key "member";
                                            description "Enter the queue list instance";

                                            leaf member {
                                                type uint32;
                                                description "Member information";
                                            }

                                            leaf queue-id {
                                                type int32;
                                                description "Queue identifier";
                                            }

                                            leaf port {
                                                type types-sros:port;
                                                description "Port identifier";
                                            }

                                            leaf port-mode {
                                                type enumeration {
                                                    enum access                         { value 1; }
                                                    enum network                        { value 2; }
                                                }
                                                description "Port mode";
                                            }

                                            leaf queue-group-template {
                                                type string;
                                                description "Queue group template";
                                            }

                                            leaf queue-group-instance {
                                                type int32;
                                                description "Queue group instance";
                                            }

                                        } // list queue

                                    } // container port-queue-group

                                    container sap {
                                        description "Enter the sap context";

                                        list queue {
                                            key "member";
                                            description "Enter the queue list instance";

                                            leaf member {
                                                type uint32;
                                                description "Member information";
                                            }

                                            leaf queue-id {
                                                type int32;
                                                description "Queue identifier";
                                            }

                                            leaf sap-id {
                                                type types-sros:sap;
                                                description "SAP identifier";
                                            }

                                            leaf port {
                                                type types-sros:port;
                                                description "Port identifier";
                                            }

                                        } // list queue

                                    } // container sap

                                } // container queue

                                container scheduler {
                                    description "Enter the scheduler context";

                                    container sap {
                                        description "Enter the sap context";

                                        list scheduler {
                                            key "member";
                                            description "Enter the scheduler list instance";

                                            leaf member {
                                                type uint32;
                                                description "Member information";
                                            }

                                            leaf scheduler-name {
                                                type string;
                                                description "Name";
                                            }

                                            leaf sap-id {
                                                type types-sros:sap;
                                                description "SAP identifier";
                                            }

                                        } // list scheduler

                                        list t0-scheduler {
                                            key "member";
                                            description "Enter the t0-scheduler list instance";

                                            leaf member {
                                                type uint32;
                                                description "Member information";
                                            }

                                            leaf scheduler-name {
                                                type string;
                                                description "Name";
                                            }

                                            leaf sap-id {
                                                type types-sros:sap;
                                                description "SAP identifier";
                                            }

                                        } // list t0-scheduler

                                    } // container sap

                                } // container scheduler

                            } // container sched-hierarchy

                        } // container above-cir

                    } // list level

                } // container lag-port-scheduler

            } // container port-scheduler-policy

            list hs-secondary-shaper {
                key "secondary-shaper-name";
                description "Enter the hs-secondary-shaper list instance";

                leaf secondary-shaper-name {
                    type types-sros:named-item;
                    description "Specifies the expanded secondary shaper name on the egress side.";
                }

                container aggregate {
                    description "Enter the aggregate context";

                    container statistics {
                        description "Enter the statistics context";

                        leaf forwarded-octets {
                            type yang:counter64;
                            description "Indicates the number of octets forwarded.";
                        }

                        leaf forwarded-packets {
                            type yang:counter64;
                            description "Indicates the number of packets forwarded.";
                        }

                    } // container statistics

                } // container aggregate

                list class {
                    key "class-number";
                    description "Enter the class list instance";

                    leaf class-number {
                        type uint32 {
                            range "1..6";
                        }
                        description "The unique value of the class.";
                    }

                    container statistics {
                        description "Enter the statistics context";

                        leaf forwarded-octets {
                            type yang:counter64;
                            description "Indicates the number of octets forwarded.";
                        }

                        leaf forwarded-packets {
                            type yang:counter64;
                            description "Indicates the number of packets forwarded.";
                        }

                    } // container statistics

                } // list class

            } // list hs-secondary-shaper

            container hw-agg-shaper-scheduler {
                description "Enter the hw-agg-shaper-scheduler context";

                leaf oper-color {
                    type types-qos:color-oper;
                    description "Specify what is state of hw-agg-shaper scheduler algorithm";
                }

                leaf num-child-agg-shapers {
                    type int64 {
                        range "0..6400000000";
                    }
                    description "Specify number of agg-shapers parented to this port scheduler.";
                }

                leaf num-orphan-agg-shapers {
                    type int64 {
                        range "0..6400000000";
                    }
                    description "Specify number of agg-shapers not parented to this port scheduler.";
                }

                container statistics {
                    description "Enter the statistics context";

                    leaf total-forwarded-octets {
                        type yang:counter64;
                        description "Indicates the total number of octets forwarded.";
                    }

                    leaf total-forwarded-packets {
                        type yang:counter64;
                        description "Indicates the total number of packets forwarded.";
                    }

                    leaf total-dropped-octets {
                        type yang:counter64;
                        description "Indicates the total number of octets dropped.";
                    }

                    leaf total-dropped-packets {
                        type yang:counter64;
                        description "Indicates the total number of packets dropped.";
                    }

                    leaf last-cleared-time {
                        type yang:date-and-time;
                        description
                            "Indicates the time, since system startup, when the counters in
                             IF-MIB::ifTable were last cleared.";
                    }

                    list class {
                        key "sched-class";
                        description "Enter the class list instance";

                        leaf sched-class {
                            type uint32 {
                                range "1..6";
                            }
                            description "Specifies the scheduler class of the hardware aggregate shaper scheduler policy.";
                        }

                        leaf forwarded-octets {
                            type yang:counter64;
                            description "Indicates the total number of octets forwarded.";
                        }

                        leaf forwarded-packets {
                            type yang:counter64;
                            description "Indicates the total number of packets forwarded.";
                        }

                        leaf dropped-octets {
                            type yang:counter64;
                            description "Indicates the total number of octets dropped.";
                        }

                        leaf dropped-packets {
                            type yang:counter64;
                            description "Indicates the total number of packets dropped.";
                        }

                        leaf last-cleared-time {
                            type yang:date-and-time;
                            description
                                "Indicates the time, since system startup, when the counters in
                                 IF-MIB::ifTable were last cleared.";
                        }

                    } // list class

                } // container statistics

                container monitor-threshold {
                    description "Enter the monitor-threshold context";

                    leaf exceed-count {
                        type yang:counter32;
                        description "Indicates the exceed count for egress hardware aggregate shaper scheduler.";
                    }

                    leaf start-time {
                        type yang:date-and-time;
                        description "Indicates the start time for threshold monitoring.";
                    }

                    leaf end-time {
                        type yang:date-and-time;
                        description "Indicates the end time for threshold monitoring.";
                    }

                    leaf total-samples {
                        type yang:counter32;
                        description "Indicates the total samples collected during the threshold monitoring interval.";
                    }

                } // container monitor-threshold

            } // container hw-agg-shaper-scheduler

        } // container egress

    } // grouping state-port-eth-egress

}
