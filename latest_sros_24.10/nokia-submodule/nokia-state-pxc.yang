submodule nokia-state-pxc {

    yang-version "1.1";

    belongs-to nokia-state { prefix "state"; }

    import nokia-sros-yang-extensions     { prefix "sros-ext"; }
    import nokia-types-sros               { prefix "types-sros"; }

    sros-ext:sros-major-release "rel24";
    organization "Nokia";
    contact
        "Nokia SR OS Support
         Web: <http://www.nokia.com>";
    description
        "Nokia YANG Data model with operational state for ports cross connects (PXC) on SR OS based routers.

         Copyright 2016 Nokia. All rights reserved. Reproduction of this document
         is authorized on the condition that the foregoing copyright notice is included.

         This nokia-state-pxc YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";
    revision "2024-11-08";

    grouping state-pxc-port-xc {
        container port-xc {
            description "Enter the port-xc context";

            list pxc {
                key "pxc-id";
                description "Enter the pxc list instance";

                leaf pxc-id {
                    type uint32 {
                        range "1..256";
                    }
                    description "The identifier which uniquely identifies the PXC.";
                }

                leaf oper-state {
                    type types-sros:oper-state;
                    description "Indicates the operational state.";
                }

            } // list pxc

        } // container port-xc

    } // grouping state-pxc-port-xc

    grouping state-pxc-fwd-path-ext {
        container fwd-path-ext {
            description "Enter the fwd-path-ext context";

            list fpe {
                key "fpe-id";
                description "Enter the fpe list instance";

                leaf fpe-id {
                    type uint32 {
                        range "1..64";
                    }
                    description "Forward path extension identifier";
                }

                container application {
                    description "Enter the application context";

                    container pw-port-extension {
                        description "Enter the pw-port-extension context";

                        leaf oper-state {
                            type types-sros:oper-state;
                            description "Indicates the operational state.";
                        }

                    } // container pw-port-extension

                    container vxlan {
                        description "Enter the vxlan context";

                        leaf oper-state {
                            type types-sros:oper-state;
                            description "Indicates the operational state.";
                        }

                    } // container vxlan

                    container srv6 {
                        description "Enter the srv6 context";

                        leaf oper-state {
                            type types-sros:oper-state;
                            description "Operational status of SRv6";
                        }

                        container interface-b {
                            description "Enter the interface-b context";

                            leaf oper-mtu {
                                type uint32;
                                description "Operational value of interface MTU size";
                            }

                        } // container interface-b

                    } // container srv6

                } // container application

            } // list fpe

        } // container fwd-path-ext

    } // grouping state-pxc-fwd-path-ext

}
