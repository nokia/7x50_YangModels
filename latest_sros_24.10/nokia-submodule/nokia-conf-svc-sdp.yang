submodule nokia-conf-svc-sdp {

    yang-version "1.1";

    belongs-to nokia-conf { prefix "conf"; }

    import nokia-sros-yang-extensions     { prefix "sros-ext"; }
    import nokia-types-services           { prefix "types-services"; }
    import nokia-types-sros               { prefix "types-sros"; }

    include nokia-conf-groups;
    include nokia-conf-log;
    include nokia-conf-router;
    include nokia-conf-service;

    sros-ext:sros-major-release "rel24";
    organization "Nokia";
    contact
        "Nokia SR OS Support
         Web: <http://www.nokia.com>";
    description
        "Nokia YANG Data model to configure services on SR OS based routers.

         Copyright 2016 Nokia. All rights reserved. Reproduction of this document
         is authorized on the condition that the foregoing copyright notice is included.

         This nokia-conf-svc-sdp YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";
    revision "2024-10-09";

    grouping conf-svc-sdp {
        list sdp {
            key "sdp-id";
            description "Enter the sdp list instance";

            leaf sdp-id {
                type types-services:sdp-id;
                description "Service Destination Point (SDP) ID";
            }

            leaf description {
                type types-sros:description;
                description "Text description";
            }

            leaf admin-state {
                type types-sros:admin-state;
                default "disable";
                description "Administrative state of the SDP";
            }

            leaf delivery-type {
                type types-services:sdp-delivery-type;
                sros-ext:immutable;
                description "Delivery type used by the SDP";
            }

            leaf accounting-policy {
                type leafref {
                    path "../../../log/accounting-policy/policy-id";
                }
                description "Accounting policy associated with an SDP";
            }

            leaf adv-mtu-override {
                type boolean;
                default "false";
                description "Override the advertised VC-type MTU using the SDP ID";
            }

            leaf booking-factor {
                type uint32 {
                    range "0..1000";
                }
                default "100";
                description "Percentage of SDP max available bandwidth for VLL CAC";
            }

            leaf collect-stats {
                type boolean;
                default "false";
                description "Collect accounting statistics for this SDP";
            }

            leaf local-end {
                type types-sros:ip-address;
                sros-ext:auto-restart-to-modify;
                description "Local end address of tunnel defined by the SDP";
            }

            leaf metric {
                type uint32 {
                    range "1..65535";
                }
                description "Metric used in tunnel table manager for decision making";
            }

            leaf network-domain {
                type leafref {
                    path "../../../router/network-domains/network-domain/domain-name";
                }
                description "Network domain name associated with the SDP";
            }

            leaf path-mtu {
                type int32 {
                    range "576..9782";
                }
                units "bytes";
                description "Maximum Transmission Unit (MTU) the SDP can transmit";
            }

            leaf pbb-etype {
                type types-services:etype-value;
                default "0x88E7";
                description "Ethertype used for PBB";
            }

            leaf signaling {
                type enumeration {
                    enum off                            { value 1; }
                    enum tldp                           { value 2; }
                    enum bgp                            { value 3; }
                }
                sros-ext:auto-restart-to-modify;
                description "Signaling protocol used to obtain pseudowire labels";
            }

            leaf tunnel-far-end {
                type types-sros:ip-address;
                sros-ext:auto-restart-to-modify;
                description "System address of the far-end router for the SDP";
            }

            leaf vlan-vc-etype {
                type types-services:etype-value;
                default "0x8100";
                description "VLAN VC Ethertype";
            }

            leaf allow-fragmentation {
                type boolean;
                default "false";
                description "Allow packets to be sent without setting DF bit";
            }

            leaf ldp {
                type boolean;
                sros-ext:auto-restart-to-modify;
                default "false";
                description "Enable LDP-signaled LSPs";
            }

            leaf bgp-tunnel {
                type boolean;
                default "false";
                description "Allow use of BGP route tunnels to reach far-end nodes";
            }

            leaf sr-isis {
                type boolean;
                default "false";
                description "Enable Segment Routing for IS-IS";
            }

            leaf sr-ospf {
                type boolean;
                default "false";
                description "Enable an MPLS SDP of LSP type OSPF Segment Routing";
            }

            leaf weighted-ecmp {
                type boolean;
                default "false";
                description "Allow weighted load-balancing on an SDP";
            }

            leaf-list apply-groups {
                type leafref {
                    path "../../../groups/group/name";
                }
                max-elements 8;
                ordered-by user;
                description "Apply a configuration group at this level";
            }

            leaf-list apply-groups-exclude {
                type leafref {
                    path "../../../groups/group/name";
                }
                max-elements 8;
                ordered-by user;
                description "Exclude a configuration group at this level";
            }

            container keep-alive {
                description "Enter the keep-alive context";

                leaf admin-state {
                    type types-sros:admin-state;
                    default "disable";
                    description "Administrative state of keepalive mechanism for the SDP";
                }

                leaf hello-time {
                    type int32 {
                        range "1..3600";
                    }
                    units "seconds";
                    sros-ext:auto-restart-to-modify;
                    default "10";
                    description "Time period between SDP keepalive messages";
                }

                leaf hold-down-time {
                    type int32 {
                        range "0..3600";
                    }
                    units "seconds";
                    default "10";
                    description "Minimum time the SDP remains in the down state";
                }

                leaf maximum-drop-count {
                    type int32 {
                        range "1..5";
                    }
                    default "3";
                    description "Maximum failed request attempts when SDP is down";
                }

                leaf message-length {
                    type int32 {
                        range "40..9198";
                    }
                    description "Length of the keepalive request messages transmitted";
                }

                leaf timeout {
                    type int32 {
                        range "1..10";
                    }
                    units "seconds";
                    default "5";
                    description "Time SDP waits before tearing down the session";
                }

                leaf-list apply-groups {
                    type leafref {
                        path "../../../../groups/group/name";
                    }
                    max-elements 8;
                    ordered-by user;
                    description "Apply a configuration group at this level";
                }

                leaf-list apply-groups-exclude {
                    type leafref {
                        path "../../../../groups/group/name";
                    }
                    max-elements 8;
                    ordered-by user;
                    description "Exclude a configuration group at this level";
                }

            } // container keep-alive

            container mixed-lsp-mode {
                presence "Enable the mixed-lsp-mode context";
                description "Enable the mixed-lsp-mode context";

                leaf revert-time {
                    type types-services:revert-time;
                    default "immediate";
                    description "Delay before SDP can revert to higher priority LSP type";
                }

            } // container mixed-lsp-mode

            container source-bmac-lsb {
                description "Enter the source-bmac-lsb context";

                leaf value {
                    type types-services:bmac-lsb-no-zero;
                    description "16 least significant bits of virtual backbone MAC";
                }

                leaf control-pw-vc-id {
                    type types-services:vc-id;
                    description "VC ID of the control pseudowire";
                }

            } // container source-bmac-lsb

            container far-end {
                description "Enter the far-end context";

                choice ip-or-node {
                    case ip {

                        leaf ip-address {
                            type types-sros:ip-address;
                            sros-ext:auto-restart-to-modify;
                            description "IP address of the far end destination router";
                        }

                    }
                }
            } // container far-end

            container class-forwarding {
                presence "Enable the class-forwarding context";
                description "Enable the class-forwarding context";

                leaf admin-state {
                    type types-sros:admin-state;
                    default "disable";
                    description "Administrative state of class-based forwarding";
                }

                leaf default-lsp {
                    type leafref {
                        path "../../lsp/lsp-name";
                    }
                    mandatory true;
                    description "Default LSP for class-based forwarding on the SDP";
                }

                leaf enforce-diffserv-lsp-fc {
                    type boolean;
                    default "false";
                    description "Enable RSVP validation of FC support by the LSP";
                }

                leaf multicast-lsp {
                    type leafref {
                        path "../../lsp/lsp-name";
                    }
                    description "LSP to forward all multicast traffic";
                }

                leaf-list apply-groups {
                    type leafref {
                        path "../../../../groups/group/name";
                    }
                    max-elements 8;
                    ordered-by user;
                    description "Apply a configuration group at this level";
                }

                leaf-list apply-groups-exclude {
                    type leafref {
                        path "../../../../groups/group/name";
                    }
                    max-elements 8;
                    ordered-by user;
                    description "Exclude a configuration group at this level";
                }

                list fc {
                    key "fc-name";
                    description "Enter the fc list instance";

                    leaf fc-name {
                        type types-sros:fc-name;
                        description "Forwarding class to LSP mapping";
                    }

                    leaf lsp {
                        type leafref {
                            path "../../../lsp/lsp-name";
                        }
                        mandatory true;
                        description "LSP name used to forward service packets";
                    }

                    leaf-list apply-groups {
                        type leafref {
                            path "../../../../../groups/group/name";
                        }
                        max-elements 8;
                        ordered-by user;
                        description "Apply a configuration group at this level";
                    }

                    leaf-list apply-groups-exclude {
                        type leafref {
                            path "../../../../../groups/group/name";
                        }
                        max-elements 8;
                        ordered-by user;
                        description "Exclude a configuration group at this level";
                    }

                } // list fc

            } // container class-forwarding

            container pw-port {
                description "Enter the pw-port context";

                leaf binding-port {
                    type types-sros:port-named;
                    description "Binding port";
                }

            } // container pw-port

            list sdp-group {
                key "group-name";
                description "Add a list entry for sdp-group";

                leaf group-name {
                    type leafref {
                        path "../../../sdp-group/group-name/group-name";
                    }
                    description "SDP administrative group name";
                }

            } // list sdp-group

            list lsp {
                key "lsp-name";
                max-elements 16;
                description "Add a list entry for lsp";

                leaf lsp-name {
                    type types-sros:named-item-64;
                    description "LSP name to associate with the SDP";
                }

            } // list lsp

        } // list sdp

    } // grouping conf-svc-sdp

}
