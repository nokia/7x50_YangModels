submodule nokia-conf-isa-video-group {

    yang-version "1.1";

    belongs-to nokia-conf { prefix "conf"; }

    import nokia-sros-yang-extensions     { prefix "sros-ext"; }
    import nokia-types-isa                { prefix "types-isa"; }
    import nokia-types-mcast-mgmt         { prefix "types-mcast-mgmt"; }
    import nokia-types-sros               { prefix "types-sros"; }

    include nokia-conf-esa;
    include nokia-conf-groups;

    sros-ext:sros-major-release "rel24";
    organization "Nokia";
    contact
        "Nokia SR OS Support
         Web: <http://www.nokia.com>";
    description
        "Nokia YANG Data model to configure ISA Video Group configuration on SR OS based routers.

         Copyright 2016 Nokia. All rights reserved. Reproduction of this document
         is authorized on the condition that the foregoing copyright notice is included.

         This nokia-conf-isa-video-group YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";
    revision "2025-05-19";

    grouping conf-isa-video-group {
        list video-group {
            key "video-group-id";
            max-elements 4;
            description "Enter the video-group list instance";

            leaf video-group-id {
                type uint32 {
                    range "1..4";
                }
                description "Video group identifier";
            }

            leaf admin-state {
                type types-sros:admin-state;
                default "disable";
                description "Administrative state of the video group";
            }

            leaf ad-insert {
                status obsolete;
                type boolean;
                default "false";
                description "Enable the ad insert server for the ISA video group";
            }

            leaf analyzer {
                type boolean;
                default "false";
                description "Enable the analyzer for all streams on the video group";
            }

            leaf description {
                type types-sros:description;
                description "Text description";
            }

            leaf rt-client {
                status obsolete;
                type boolean;
                default "true";
                description "Allow client capability for retransmission";
            }

            leaf fcc-server {
                type boolean;
                default "false";
                description "Allow FCC server capability for the group";
            }

            leaf local-rt-server {
                type boolean;
                default "false";
                description "Enable the local RET server for the group";
            }

            leaf resv-ret {
                type uint32 {
                    range "0..10500";
                }
                units "megabps";
                description "Egress bandwidth reserved for retransmission";
            }

            leaf stream-selection {
                type boolean;
                default "false";
                description "Allow stream selection for the group";
            }

            leaf-list apply-groups {
                type leafref {
                    path "../../../groups/group/name";
                }
                max-elements 8;
                ordered-by user;
                description "Apply a configuration group at this level";
            }

            leaf-list apply-groups-exclude {
                type leafref {
                    path "../../../groups/group/name";
                }
                max-elements 8;
                ordered-by user;
                description "Exclude a configuration group at this level";
            }

            list mda {
                key "mda-id";
                max-elements 6;
                description "Add a list entry for mda";

                leaf mda-id {
                    type types-isa:slot-mda;
                    description "MDA identifier";
                }

            } // list mda

            list vapp {
                key "esa-id vapp-id";
                max-elements 32;
                description "Add a list entry for vapp";

                leaf esa-id {
                    type leafref {
                        path "../../../../esa/esa-id";
                    }
                    description "ESA ID";
                }

                leaf vapp-id {
                    type leafref {
                        path "../../../../esa[esa-id=current()/../esa-id]/vm/vm-id";
                    }
                    description "Virtual application ID";
                }

            } // list vapp

            container watermark {
                description "Enter the watermark context";

                container bandwidth {
                    description "Enter the bandwidth context";

                    leaf fcc {
                        type types-mcast-mgmt:percent-without-zero-and-hundred;
                        default "90";
                        description "FCC watermark parameters based on the bandwidth";
                    }

                    leaf ret {
                        type types-mcast-mgmt:percent-without-zero-and-hundred;
                        default "90";
                        description "RET watermark parameters based on the bandwidth";
                    }

                    leaf total {
                        type types-mcast-mgmt:percent-without-zero-and-hundred;
                        default "90";
                        description "Total watermark parameters based on the bandwidth";
                    }

                } // container bandwidth

                container session {
                    description "Enter the session context";

                    leaf fcc {
                        type types-mcast-mgmt:percent-without-zero-and-hundred;
                        default "90";
                        description "FCC watermark parameters based on the session";
                    }

                    leaf ret {
                        type types-mcast-mgmt:percent-without-zero-and-hundred;
                        default "90";
                        description "RET watermark parameters based on the session";
                    }

                    leaf total {
                        type types-mcast-mgmt:percent-without-zero-and-hundred;
                        default "90";
                        description "Total watermark parameters based on the session";
                    }

                } // container session

            } // container watermark

        } // list video-group

    } // grouping conf-isa-video-group

}
