submodule nokia-state-system-script-control {

    yang-version "1.1";

    belongs-to nokia-state { prefix "state"; }

    import ietf-yang-types                { prefix "yang"; }
    import nokia-sros-yang-extensions     { prefix "sros-ext"; }
    import nokia-types-sros               { prefix "types-sros"; }
    import nokia-types-system             { prefix "types-system"; }

    sros-ext:sros-major-release "rel24";
    organization "Nokia";
    contact
        "Nokia SR OS Support
         Web: <http://www.nokia.com>";
    description
        "Nokia YANG Data model with operational state for system scrip-control parameters on SR OS based routers.

         Copyright 2016 Nokia. All rights reserved. Reproduction of this document
         is authorized on the condition that the foregoing copyright notice is included.

         This nokia-state-system-script-control YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";
    revision "2021-10-04";

    grouping state-system-script-control {
        container script-control {
            description "Enter the script-control context";

            list script {
                key "script-name owner";
                description "Enter the script list instance";

                leaf script-name {
                    type types-sros:named-item;
                    description "Script name";
                }

                leaf owner {
                    type types-sros:named-item;
                    description "Script owner";
                }

                leaf oper-state {
                    type types-system:script-oper-state;
                    description
                        "The value of the this object indicates the operational
                         state of the accounting policy.";
                }

                leaf last-script-error {
                    type string {
                        length "0..256";
                    }
                    description
                        "Descriptive error message if the transition into the oper-state
                         up failed.";
                }

            } // list script

            list script-policy {
                key "policy-name owner";
                description "Enter the script-policy list instance";

                leaf policy-name {
                    type types-sros:named-item;
                    description "Script policy name.";
                }

                leaf owner {
                    type types-sros:named-item;
                    description "Script policy owner.";
                }

                leaf oper-state {
                    type types-system:script-policy-oper-state;
                    description
                        "The value of the this object indicates the operational
                         state of the accounting policy.";
                }

                choice script-type {
                    case scriptcontrol {

                        container script {
                            description "Enter the script context";

                            leaf script-start-error {
                                type string {
                                    length "0..256";
                                }
                                description "Descriptive error message if an attempt to launch a script fails.";
                            }

                            leaf last-application {
                                type types-system:script-auth-application;
                                description "Module that started this run of a script";
                            }

                            leaf last-auth-user-account {
                                type types-sros:named-item;
                                description
                                    "Name of the user account used to check access to CLI commands
                                     while executing the script.";
                            }

                            container run-histories {
                                description "Enter the run-histories context";

                                leaf completed {
                                    type uint32;
                                    description "Script's execution state";
                                }

                                leaf executing {
                                    type uint32;
                                    description "Script's execution state";
                                }

                                leaf initializing {
                                    type uint32;
                                    description "Script's execution state";
                                }

                            } // container run-histories

                            list run-history {
                                key "run";
                                description "Enter the run-history list instance";

                                leaf run {
                                    type uint32;
                                    description "Identifier associated with this running or finished script";
                                }

                                leaf start-time {
                                    type yang:date-and-time;
                                    description "The date and time when the execution started";
                                }

                                leaf end-time {
                                    type yang:date-and-time;
                                    description "The date and time when the execution ended.";
                                }

                                leaf elapsed-time {
                                    type types-sros:time-duration;
                                    description "Elapsed time of script";
                                }

                                leaf lifetime {
                                    type types-sros:time-duration;
                                    description "Specifies how long the script can execute";
                                }

                                leaf run-state {
                                    type types-system:run-state;
                                    description "Script's execution state";
                                }

                                leaf run-exit-code {
                                    type types-system:run-exit-code;
                                    description "Reason why a script finished execution";
                                }

                                leaf result-time {
                                    type yang:date-and-time;
                                    description
                                        "The date and time when the desired status of the script execution
                                         was updated.";
                                }

                                leaf keep-history {
                                    type types-sros:time-duration;
                                    description
                                        "Specifies how long this leaf can exist in the run-table after
                                         the script has terminated.";
                                }

                                leaf error-time {
                                    type yang:date-and-time;
                                    description
                                        "The date and time when leaf error was last updated if the script
                                         startup or execution raised an abnormal condition.";
                                }

                                leaf source-file {
                                    type string {
                                        length "1..255";
                                    }
                                    description "File name where the script source is";
                                }

                                leaf results-file {
                                    type string {
                                        length "1..511";
                                    }
                                    description "File name where the script result is written";
                                }

                                leaf run-exit {
                                    type string {
                                        length "1..511";
                                    }
                                    description "Status of the script execution";
                                }

                                leaf error {
                                    type string;
                                    description
                                        "Descriptive error message if the script startup or execution
                                         raised an abnormal condition.";
                                }

                                leaf application {
                                    type types-system:script-auth-application;
                                    description "Module that started this run of a script";
                                }

                                leaf auth-user-account {
                                    type types-sros:named-item;
                                    description
                                        "Name of the user account used to check access to CLI commands
                                         while executing the script.";
                                }

                            } // list run-history

                        } // container script

                    }
                    case python3script {

                        container python-script {
                            description "Enter the python-script context";

                            leaf script-start-error {
                                type string {
                                    length "0..256";
                                }
                                description "Descriptive error message if an attempt to launch a script fails.";
                            }

                            leaf last-application {
                                type types-system:script-auth-application;
                                description "Module that started this run of a script";
                            }

                            leaf last-auth-user-account {
                                type types-sros:named-item;
                                description
                                    "Name of the user account used to check access to CLI commands
                                     while executing the script.";
                            }

                            container run-histories {
                                description "Enter the run-histories context";

                                leaf completed {
                                    type uint32;
                                    description "Script's execution state";
                                }

                                leaf executing {
                                    type uint32;
                                    description "Script's execution state";
                                }

                                leaf initializing {
                                    type uint32;
                                    description "Script's execution state";
                                }

                            } // container run-histories

                            list run-history {
                                key "run";
                                description "Enter the run-history list instance";

                                leaf run {
                                    type uint32;
                                    description "Identifier associated with this running or finished script";
                                }

                                leaf start-time {
                                    type yang:date-and-time;
                                    description "The date and time when the execution started";
                                }

                                leaf end-time {
                                    type yang:date-and-time;
                                    description "The date and time when the execution ended.";
                                }

                                leaf elapsed-time {
                                    type types-sros:time-duration;
                                    description "Elapsed time of script";
                                }

                                leaf lifetime {
                                    type types-sros:time-duration;
                                    description "Specifies how long the script can execute";
                                }

                                leaf run-state {
                                    type types-system:run-state;
                                    description "Script's execution state";
                                }

                                leaf run-exit-code {
                                    type types-system:run-exit-code;
                                    description "Reason why a script finished execution";
                                }

                                leaf result-time {
                                    type yang:date-and-time;
                                    description
                                        "The date and time when the desired status of the script execution
                                         was updated.";
                                }

                                leaf keep-history {
                                    type types-sros:time-duration;
                                    description
                                        "Specifies how long this leaf can exist in the run-table after
                                         the script has terminated.";
                                }

                                leaf error-time {
                                    type yang:date-and-time;
                                    description
                                        "The date and time when leaf error was last updated if the script
                                         startup or execution raised an abnormal condition.";
                                }

                                leaf source-file {
                                    type string {
                                        length "1..255";
                                    }
                                    description "File name where the script source is";
                                }

                                leaf results-file {
                                    type string {
                                        length "1..511";
                                    }
                                    description "File name where the script result is written";
                                }

                                leaf run-exit {
                                    type string {
                                        length "1..511";
                                    }
                                    description "Status of the script execution";
                                }

                                leaf error {
                                    type string;
                                    description
                                        "Descriptive error message if the script startup or execution
                                         raised an abnormal condition.";
                                }

                                leaf application {
                                    type types-system:script-auth-application;
                                    description "Module that started this run of a script";
                                }

                                leaf auth-user-account {
                                    type types-sros:named-item;
                                    description
                                        "Name of the user account used to check access to CLI commands
                                         while executing the script.";
                                }

                            } // list run-history

                        } // container python-script

                    }
                }
            } // list script-policy

        } // container script-control

    } // grouping state-system-script-control

}
