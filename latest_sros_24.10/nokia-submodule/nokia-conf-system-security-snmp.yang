submodule nokia-conf-system-security-snmp {

    yang-version "1.1";

    belongs-to nokia-conf { prefix "conf"; }

    import nokia-sros-yang-extensions     { prefix "sros-ext"; }
    import nokia-types-sros               { prefix "types-sros"; }

    include nokia-conf-groups;

    sros-ext:sros-major-release "rel24";
    organization "Nokia";
    contact
        "Nokia SR OS Support
         Web: <http://www.nokia.com>";
    description
        "Nokia YANG Data model to configure system security snmp parameters. on SR OS based routers.

         Copyright 2016 Nokia. All rights reserved. Reproduction of this document
         is authorized on the condition that the foregoing copyright notice is included.

         This nokia-conf-system-security-snmp YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";
    revision "2017-10-24";

    grouping conf-system-security-snmp {
        container snmp {
            description "Enter the snmp context";

            leaf-list apply-groups {
                type leafref {
                    path "../../../../groups/group/name";
                }
                max-elements 8;
                ordered-by user;
                description "Apply a configuration group at this level";
            }

            leaf-list apply-groups-exclude {
                type leafref {
                    path "../../../../groups/group/name";
                }
                max-elements 8;
                ordered-by user;
                description "Exclude a configuration group at this level";
            }

            list access {
                key "group context security-model security-level";
                description "Enter the access list instance";

                leaf group {
                    type types-sros:named-item;
                    description "Group name";
                }

                leaf context {
                    type types-sros:named-item-or-empty;
                    description "String to match context name for access rights";
                }

                leaf security-model {
                    type enumeration {
                        enum snmpv1                         { value 1; }
                        enum snmpv2c                        { value 2; }
                        enum usm                            { value 3; }
                    }
                    description "Security model";
                }

                leaf security-level {
                    type enumeration {
                        enum no-auth-no-privacy             { value 1; }
                        enum auth-no-privacy                { value 2; }
                        enum privacy                        { value 3; }
                    }
                    description "Minimum security level required to gain access rights";
                }

                leaf prefix-match {
                    type enumeration {
                        enum exact                          { value 1; }
                        enum prefix                         { value 2; }
                    }
                    description "Match type for the context";
                }

                leaf read {
                    type types-sros:named-item;
                    description "SNMP view for read access";
                }

                leaf write {
                    type types-sros:named-item;
                    description "SNMP view for write access";
                }

                leaf notify {
                    type types-sros:named-item;
                    description "SNMP view for notification access";
                }

                leaf-list apply-groups {
                    type leafref {
                        path "../../../../../groups/group/name";
                    }
                    max-elements 8;
                    ordered-by user;
                    description "Apply a configuration group at this level";
                }

                leaf-list apply-groups-exclude {
                    type leafref {
                        path "../../../../../groups/group/name";
                    }
                    max-elements 8;
                    ordered-by user;
                    description "Exclude a configuration group at this level";
                }

            } // list access

            list community {
                key "community-string";
                description "Enter the community list instance";

                leaf community-string {
                    type types-sros:encrypted-leaf {
                        length "1..114";
                    }
                    description "SNMPv1 or SNMPv2c community string";
                }

                leaf access-permissions {
                    type enumeration {
                        enum r                              { value 1; }
                        enum rw                             { value 2; }
                        enum rwa                            { value 3; }
                        enum mgmt                           { value 4; }
                        enum vpls-mgmt                      { value 5; }
                    }
                    mandatory true;
                    description "Access permissions for objects in the MIB";
                }

                leaf version {
                    type enumeration {
                        enum v1                             { value 1; }
                        enum v2c                            { value 2; }
                        enum both                           { value 3; }
                    }
                    default "both";
                    description "SNMP version";
                }

                leaf source-access-list {
                    type leafref {
                        path "../../source-access-list/list-name";
                    }
                    description "Source access list to validate received SNMP requests";
                }

                leaf-list apply-groups {
                    type leafref {
                        path "../../../../../groups/group/name";
                    }
                    max-elements 8;
                    ordered-by user;
                    description "Apply a configuration group at this level";
                }

                leaf-list apply-groups-exclude {
                    type leafref {
                        path "../../../../../groups/group/name";
                    }
                    max-elements 8;
                    ordered-by user;
                    description "Exclude a configuration group at this level";
                }

            } // list community

            list usm-community {
                key "community-string";
                description "Enter the usm-community list instance";

                leaf community-string {
                    type types-sros:encrypted-leaf {
                        length "1..114";
                    }
                    description "Community string associated with SNMPv3 access group";
                }

                leaf group {
                    type types-sros:named-item;
                    description "Group to manage access rights of the community string";
                }

                leaf source-access-list {
                    type leafref {
                        path "../../source-access-list/list-name";
                    }
                    description "Source access list to validate received SNMP requests";
                }

                leaf-list apply-groups {
                    type leafref {
                        path "../../../../../groups/group/name";
                    }
                    max-elements 8;
                    ordered-by user;
                    description "Apply a configuration group at this level";
                }

                leaf-list apply-groups-exclude {
                    type leafref {
                        path "../../../../../groups/group/name";
                    }
                    max-elements 8;
                    ordered-by user;
                    description "Exclude a configuration group at this level";
                }

            } // list usm-community

            container attempts {
                description "Enter the attempts context";

                leaf count {
                    type uint16 {
                        range "1..64";
                    }
                    default "20";
                    description "Unsuccessful attempts allowed within time period";
                }

                leaf time {
                    type uint16 {
                        range "0..60";
                    }
                    units "minutes";
                    default "5";
                    description "Time before host lockout after unsuccessful attempts";
                }

                leaf lockout {
                    type uint16 {
                        range "0..1440";
                    }
                    units "minutes";
                    default "10";
                    description "Lockout period during which the host cannot log in";
                }

                leaf-list apply-groups {
                    type leafref {
                        path "../../../../../groups/group/name";
                    }
                    max-elements 8;
                    ordered-by user;
                    description "Apply a configuration group at this level";
                }

                leaf-list apply-groups-exclude {
                    type leafref {
                        path "../../../../../groups/group/name";
                    }
                    max-elements 8;
                    ordered-by user;
                    description "Exclude a configuration group at this level";
                }

            } // container attempts

            list source-access-list {
                key "list-name";
                max-elements 16;
                description "Enter the source-access-list list instance";

                leaf list-name {
                    type types-sros:string-not-all-spaces {
                        length "1..32";
                        pattern "[A-Za-z].*" {
                            error-message "List name must begin with a letter";
                        }
                    }
                    description "Source access list name";
                }

                leaf-list apply-groups {
                    type leafref {
                        path "../../../../../groups/group/name";
                    }
                    max-elements 8;
                    ordered-by user;
                    description "Apply a configuration group at this level";
                }

                leaf-list apply-groups-exclude {
                    type leafref {
                        path "../../../../../groups/group/name";
                    }
                    max-elements 8;
                    ordered-by user;
                    description "Exclude a configuration group at this level";
                }

                list source-host {
                    key "host-name";
                    max-elements 16;
                    description "Enter the source-host list instance";

                    leaf host-name {
                        type types-sros:named-item;
                        description "Source host entry name";
                    }

                    leaf address {
                        type types-sros:ip-unicast-address;
                        mandatory true;
                        description "Source IP address entry used to validate SNMP requests";
                    }

                    leaf-list apply-groups {
                        type leafref {
                            path "../../../../../../groups/group/name";
                        }
                        max-elements 8;
                        ordered-by user;
                        description "Apply a configuration group at this level";
                    }

                    leaf-list apply-groups-exclude {
                        type leafref {
                            path "../../../../../../groups/group/name";
                        }
                        max-elements 8;
                        ordered-by user;
                        description "Exclude a configuration group at this level";
                    }

                } // list source-host

            } // list source-access-list

            list view {
                key "view-name subtree";
                description "Enter the view list instance";

                leaf view-name {
                    type types-sros:named-item;
                    description "View name";
                }

                leaf subtree {
                    type string {
                        length "1..256";
                    }
                    description "Object Identifier (OID) value";
                }

                leaf mask {
                    type string {
                        length "1..16";
                        pattern "(0X|0x)?(([A-Fa-f0-9]){2})+" {
                            error-message "Hex value must be even number of characters.";
                        }
                    }
                    description "Mask value as binary value, or hex value";
                }

                leaf type {
                    type enumeration {
                        enum included                       { value 1; }
                        enum excluded                       { value 2; }
                    }
                    description "Type of SNMP security view mask";
                }

                leaf-list apply-groups {
                    type leafref {
                        path "../../../../../groups/group/name";
                    }
                    max-elements 8;
                    ordered-by user;
                    description "Apply a configuration group at this level";
                }

                leaf-list apply-groups-exclude {
                    type leafref {
                        path "../../../../../groups/group/name";
                    }
                    max-elements 8;
                    ordered-by user;
                    description "Exclude a configuration group at this level";
                }

            } // list view

        } // container snmp

    } // grouping conf-system-security-snmp

}
