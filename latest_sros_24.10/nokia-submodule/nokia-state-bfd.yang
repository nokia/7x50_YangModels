submodule nokia-state-bfd {

    yang-version "1.1";

    belongs-to nokia-state { prefix "state"; }

    import ietf-yang-types                { prefix "yang"; }
    import nokia-sros-yang-extensions     { prefix "sros-ext"; }
    import nokia-types-bfd                { prefix "types-bfd"; }
    import nokia-types-card               { prefix "types-card"; }
    import nokia-types-services           { prefix "types-services"; }
    import nokia-types-sros               { prefix "types-sros"; }

    sros-ext:sros-major-release "rel24";
    organization "Nokia";
    contact
        "Nokia SR OS Support
         Web: <http://www.nokia.com>";
    description
        "Nokia YANG Data model with operational state for BFD protocol on SR OS based routers.

         Copyright 2016 Nokia. All rights reserved. Reproduction of this document
         is authorized on the condition that the foregoing copyright notice is included.

         This nokia-state-bfd YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";
    revision "2024-08-30";

    grouping state-bfd {
        container bfd {
            description "Enter the bfd context";

            list oper-bfd-template {
                key "name";
                description "Enter the oper-bfd-template list instance";

                leaf name {
                    type types-sros:named-item;
                    description "BFD template name.";
                }

                leaf type {
                    type types-bfd:cfg-endpoint-type;
                    description "The BFD session endpoint type.";
                }

                leaf transmit-interval {
                    type uint32 {
                        range "10..100000";
                    }
                    description "Transmit interval.";
                }

                leaf receive-interval {
                    type uint32 {
                        range "10..100000";
                    }
                    description "Receive interval.";
                }

                leaf multiplier {
                    type uint32 {
                        range "1..20";
                    }
                    description "Multiplier.";
                }

                leaf echo-receive {
                    type uint32 {
                        range "100..100000";
                    }
                    description "Echo receive interval.";
                }

                container associations {
                    description "Enter the associations context";

                    leaf lsp-ldp {
                        type uint32;
                        description "Number of LSP LDP references to the BFD template.";
                    }

                    leaf dynamic-lsp-rsvp {
                        type uint32;
                        description "Number of dynamic LSP RSVP references to the BFD template.";
                    }

                    leaf template-lsp-rsvp {
                        type uint32;
                        description "Number of template LSP RSVP references to the BFD template.";
                    }

                    leaf lsp-sr-te {
                        type uint32;
                        description "Number of LSP SR-TE references to the BFD template.";
                    }

                    leaf template-lsp-sr-te {
                        type uint32;
                        description "Number of template LSP SR-TE references to the BFD template.";
                    }

                    leaf static-sr-policy {
                        type uint32;
                        description "Number of static sr-policy references to the BFD template.";
                    }

                    leaf bgp-sr-policy {
                        type uint32;
                        description "Number of BGP sr-policy references to the BFD template.";
                    }

                    leaf oam-template {
                        type uint32;
                        description "Number of OAM template references to the BFD template.";
                    }

                    leaf sdp-bind {
                        type uint32;
                        description "Number of SDP-bind references to the BFD template.";
                    }

                } // container associations

                list sdp-bind-ref {
                    key "svc-id sdp-bind-id";
                    description "Enter the sdp-bind-ref list instance";

                    leaf svc-id {
                        type types-services:service-id;
                        description "Service-id of the associated item.";
                    }

                    leaf sdp-bind-id {
                        type types-services:sdp-bind-id;
                        description "SDP Bind identifier of the associated item.";
                    }

                    leaf enabled {
                        type boolean;
                        description "Indicates whether BFD is enabled on this SDP binding.";
                    }

                    leaf encap {
                        type types-services:bfd-encap;
                        description "BFD encapsulation used on this SDP binding.";
                    }

                } // list sdp-bind-ref

                list oam-template-ref {
                    key "router-instance template-name";
                    description "Enter the oam-template-ref list instance";

                    leaf router-instance {
                        type types-sros:router-instance;
                        description
                            "Administrative name for this virtual router. The router
                             name must be unique among all virtual routers in the system.";
                    }

                    leaf template-name {
                        type types-sros:named-item;
                        description "OAM template name.";
                    }

                } // list oam-template-ref

            } // list oper-bfd-template

            list lsp-tail-session {
                key "router-instance session-fec-type remote-address address lsp-id tunnel-id";
                description "Enter the lsp-tail-session list instance";

                leaf router-instance {
                    type types-sros:router-instance;
                    description
                        "The administrative name for this virtual router. The router
                         name must be unique among all virtual routers in the system.";
                }

                leaf session-fec-type {
                    type types-bfd:fec-type;
                    description "Fec type of this BFD session.";
                }

                leaf remote-address {
                    type types-sros:ip-address-with-zone;
                    description "Address of the remote endpoint of this BFD session.";
                }

                leaf address {
                    type types-sros:ip-address-with-zone;
                    description "Address of the local endpoint of this BFD session.";
                }

                leaf lsp-id {
                    type uint32;
                    description "Path-id when applicable. 0 otherwise.";
                }

                leaf tunnel-id {
                    type uint32;
                    description "Tunnel-id when applicable. 0 otherwise.";
                }

                leaf session-name {
                    type string {
                        length "1..160";
                    }
                    description "Session name";
                }

                container state {
                    description "Enter the state context";

                    leaf location {
                        type types-bfd:act-endpoint-type;
                        description "Location of the BFD session.";
                    }

                    leaf configured-location {
                        type types-bfd:cfg-endpoint-type;
                        description "Configured location of the BFD session.";
                    }

                    leaf oper-state {
                        type types-sros:oper-state;
                        description "Current operational state of this session.";
                    }

                    leaf protocols {
                        type types-bfd:protocols;
                        description "Protocols using this BFD session.";
                    }

                    leaf session-state {
                        type types-bfd:session-state;
                        description "State of the BFD protocol.";
                    }

                    leaf down-reasons {
                        type bits {
                            bit no-protocols                   { position 0; }
                            bit no-heart-beat                  { position 1; }
                            bit echo-failed                    { position 2; }
                            bit nbr-signal-down                { position 3; }
                            bit fwd-plane-reset                { position 4; }
                            bit path-down                      { position 5; }
                            bit nbr-admin-down                 { position 6; }
                            bit admin-clear                    { position 7; }
                            bit mis-conn-defect                { position 8; }
                        }
                        description "Reasons why a BFD session is not up.";
                    }

                    leaf transmit-interval {
                        type uint32;
                        units "milliseconds";
                        description "Negotiated transmit interval.";
                    }

                    leaf receive-interval {
                        type uint32;
                        units "milliseconds";
                        description "Negotiated receive interval.";
                    }

                    leaf multiplier {
                        type uint32;
                        units "milliseconds";
                        description "Negotiated multiplier.";
                    }

                } // container state

                container statistics {
                    description "Enter the statistics context";

                    leaf up-count {
                        type yang:counter32;
                        description "Number of times the session-state changed to 'Up'.";
                    }

                    leaf down-count {
                        type yang:counter32;
                        description "Number of times the session-state changed to 'Down'.";
                    }

                    leaf up-time {
                        type types-sros:time-interval;
                        description "Time interval elapsed since the session is in state 'Up'.";
                    }

                    leaf down-time {
                        type types-sros:time-interval;
                        description "Time interval elapsed since the session is in state 'Down'.";
                    }

                    leaf last-down-duration {
                        type types-sros:time-interval;
                        description "Time interval the session was in another state before it went 'Up'";
                    }

                    leaf last-up-duration {
                        type types-sros:time-interval;
                        description "Time interval the session was in state 'Up' before it left this state";
                    }

                    leaf received-messages {
                        type yang:counter32;
                        description "Number of messages received for the bfd session.";
                    }

                    leaf version-mismatch {
                        type yang:counter32;
                        description "Number of version mismatch errors for the bfd session.";
                    }

                    leaf last-received {
                        type yang:date-and-time;
                        description
                            "Time when the most recent message was received for the
                             bfd session that was not handled by the network processor.";
                    }

                    leaf time-since-np-receive {
                        type uint32;
                        units "milliseconds";
                        description
                            "Time elapsed since the most recent message was received
                             by the network processor for the BFD session. Zero is returned
                             if the session is Down.";
                    }

                    leaf sent-messages {
                        type yang:counter32;
                        description "Number of messages sent in this session.";
                    }

                    leaf last-sent {
                        type yang:date-and-time;
                        description
                            "Time when the most recent message was sent
                             (not including the ones transmitted by the network processor).";
                    }

                    leaf finals-sent {
                        type uint32;
                        description
                            "Number of protocol messages sent with the final
                             flag set.";
                    }

                    leaf time-since-np-sent {
                        type uint32;
                        units "milliseconds";
                        description
                            "Time elapsed since the most recent message was sent
                             by the network processor for the BFD session. Zero is returned
                             if the session is Down.";
                    }

                } // container statistics

                container local-parameters {
                    description "Enter the local-parameters context";

                    leaf discriminator {
                        type uint32;
                        description "Unique discriminator for this session.";
                    }

                    leaf state {
                        type types-bfd:session-state;
                        description "State of this session.";
                    }

                    leaf diag {
                        type enumeration {
                            enum detect-time-expired            { value 1; }
                            enum echo-func-failed               { value 2; }
                            enum neighbor-down                  { value 3; }
                            enum forwarding-plane-reset         { value 4; }
                            enum path-down                      { value 5; }
                            enum concatenated-path-down         { value 6; }
                            enum admin-down                     { value 7; }
                            enum reverse-concat-path-down       { value 8; }
                            enum mis-connectivity-defect        { value 9; }
                            enum admin-clear                    { value 39; }
                        }
                        description "Diagnostic value.";
                    }

                    leaf mode {
                        type enumeration {
                            enum async                          { value 0; }
                            enum demand                         { value 1; }
                        }
                        description "Mode.";
                    }

                    leaf tx-interval {
                        type uint32;
                        description "Minimal transmit interval.";
                    }

                    leaf multiplier {
                        type uint32;
                        description "Multiplier.";
                    }

                    leaf rx-interval {
                        type uint32;
                        description "Minimal receive interval.";
                    }

                } // container local-parameters

                container remote-parameters {
                    description "Enter the remote-parameters context";

                    leaf discriminator {
                        type uint32;
                        description "Unique discriminator for this session.";
                    }

                    leaf state {
                        type types-bfd:session-state;
                        description "State of this session.";
                    }

                    leaf diag {
                        type enumeration {
                            enum detect-time-expired            { value 1; }
                            enum echo-func-failed               { value 2; }
                            enum neighbor-down                  { value 3; }
                            enum forwarding-plane-reset         { value 4; }
                            enum path-down                      { value 5; }
                            enum concatenated-path-down         { value 6; }
                            enum admin-down                     { value 7; }
                            enum reverse-concat-path-down       { value 8; }
                            enum mis-connectivity-defect        { value 9; }
                            enum admin-clear                    { value 39; }
                        }
                        description "Diagnostic value.";
                    }

                    leaf mode {
                        type enumeration {
                            enum async                          { value 0; }
                            enum demand                         { value 1; }
                        }
                        description "Mode.";
                    }

                    leaf tx-interval {
                        type uint32;
                        description "Minimal transmit interval.";
                    }

                    leaf multiplier {
                        type uint32;
                        description "Multiplier.";
                    }

                    leaf rx-interval {
                        type uint32;
                        description "Minimal receive interval.";
                    }

                    leaf c-flag {
                        type boolean;
                        description "BFD is independent of the control plane.";
                    }

                } // container remote-parameters

            } // list lsp-tail-session

            list lsp-head-session {
                status deprecated;
                key "router-instance session-fec-type remote-address address lsp-id tunnel-id";
                description "Enter the lsp-head-session list instance";

                leaf router-instance {
                    status deprecated;
                    type types-sros:router-instance;
                    description
                        "The administrative name for this virtual router. The router
                         name must be unique among all virtual routers in the system.";
                }

                leaf session-fec-type {
                    status deprecated;
                    type types-bfd:fec-type;
                    description "Fec type of this BFD session.";
                }

                leaf remote-address {
                    status deprecated;
                    type types-sros:ip-address-with-zone;
                    description "Address of the remote endpoint of this BFD session.";
                }

                leaf address {
                    status deprecated;
                    type types-sros:ip-address-with-zone;
                    description "Address of the local endpoint of this BFD session.";
                }

                leaf lsp-id {
                    status deprecated;
                    type uint32;
                    description "Path-id when applicable. 0 otherwise.";
                }

                leaf tunnel-id {
                    status deprecated;
                    type uint32;
                    description "Tunnel-id when applicable. 0 otherwise.";
                }

                leaf session-name {
                    status deprecated;
                    type string {
                        length "1..160";
                    }
                    description "Session name";
                }

                container state {
                    status deprecated;
                    description "Enter the state context";

                    leaf location {
                        status deprecated;
                        type types-bfd:act-endpoint-type;
                        description "Location of the BFD session.";
                    }

                    leaf configured-location {
                        status deprecated;
                        type types-bfd:cfg-endpoint-type;
                        description "Configured location of the BFD session.";
                    }

                    leaf oper-state {
                        status deprecated;
                        type types-sros:oper-state;
                        description "Current operational state of this session.";
                    }

                    leaf protocols {
                        status deprecated;
                        type types-bfd:protocols;
                        description "Protocols using this BFD session.";
                    }

                    leaf session-state {
                        status deprecated;
                        type types-bfd:session-state;
                        description "State of the BFD protocol.";
                    }

                    leaf down-reasons {
                        status deprecated;
                        type bits {
                            bit no-protocols                   { position 0; }
                            bit no-heart-beat                  { position 1; }
                            bit echo-failed                    { position 2; }
                            bit nbr-signal-down                { position 3; }
                            bit fwd-plane-reset                { position 4; }
                            bit path-down                      { position 5; }
                            bit nbr-admin-down                 { position 6; }
                            bit admin-clear                    { position 7; }
                            bit mis-conn-defect                { position 8; }
                        }
                        description "Reasons why a BFD session is not up.";
                    }

                    leaf transmit-interval {
                        status deprecated;
                        type uint32;
                        units "milliseconds";
                        description "Negotiated transmit interval.";
                    }

                    leaf receive-interval {
                        status deprecated;
                        type uint32;
                        units "milliseconds";
                        description "Negotiated receive interval.";
                    }

                    leaf multiplier {
                        status deprecated;
                        type uint32;
                        units "milliseconds";
                        description "Negotiated multiplier.";
                    }

                } // container state

                container local-parameters {
                    status deprecated;
                    description "Enter the local-parameters context";

                    leaf discriminator {
                        status deprecated;
                        type uint32;
                        description "Unique discriminator for this session.";
                    }

                    leaf state {
                        status deprecated;
                        type types-bfd:session-state;
                        description "State of this session.";
                    }

                    leaf diag {
                        status deprecated;
                        type enumeration {
                            enum detect-time-expired            { value 1; }
                            enum echo-func-failed               { value 2; }
                            enum neighbor-down                  { value 3; }
                            enum forwarding-plane-reset         { value 4; }
                            enum path-down                      { value 5; }
                            enum concatenated-path-down         { value 6; }
                            enum admin-down                     { value 7; }
                            enum reverse-concat-path-down       { value 8; }
                            enum mis-connectivity-defect        { value 9; }
                            enum admin-clear                    { value 39; }
                        }
                        description "Diagnostic value.";
                    }

                    leaf mode {
                        status deprecated;
                        type enumeration {
                            enum async                          { value 0; }
                            enum demand                         { value 1; }
                        }
                        description "Mode.";
                    }

                    leaf tx-interval {
                        status deprecated;
                        type uint32;
                        description "Minimal transmit interval.";
                    }

                    leaf multiplier {
                        status deprecated;
                        type uint32;
                        description "Multiplier.";
                    }

                    leaf rx-interval {
                        status deprecated;
                        type uint32;
                        description "Minimal receive interval.";
                    }

                } // container local-parameters

                container remote-parameters {
                    status deprecated;
                    description "Enter the remote-parameters context";

                    leaf discriminator {
                        status deprecated;
                        type uint32;
                        description "Unique discriminator for this session.";
                    }

                    leaf state {
                        status deprecated;
                        type types-bfd:session-state;
                        description "State of this session.";
                    }

                    leaf diag {
                        status deprecated;
                        type enumeration {
                            enum detect-time-expired            { value 1; }
                            enum echo-func-failed               { value 2; }
                            enum neighbor-down                  { value 3; }
                            enum forwarding-plane-reset         { value 4; }
                            enum path-down                      { value 5; }
                            enum concatenated-path-down         { value 6; }
                            enum admin-down                     { value 7; }
                            enum reverse-concat-path-down       { value 8; }
                            enum mis-connectivity-defect        { value 9; }
                            enum admin-clear                    { value 39; }
                        }
                        description "Diagnostic value.";
                    }

                    leaf mode {
                        status deprecated;
                        type enumeration {
                            enum async                          { value 0; }
                            enum demand                         { value 1; }
                        }
                        description "Mode.";
                    }

                    leaf tx-interval {
                        status deprecated;
                        type uint32;
                        description "Minimal transmit interval.";
                    }

                    leaf multiplier {
                        status deprecated;
                        type uint32;
                        description "Multiplier.";
                    }

                    leaf rx-interval {
                        status deprecated;
                        type uint32;
                        description "Minimal receive interval.";
                    }

                    leaf c-flag {
                        status deprecated;
                        type boolean;
                        description "BFD is independent of the control plane.";
                    }

                } // container remote-parameters

                container statistics {
                    status deprecated;
                    description "Enter the statistics context";

                    leaf up-count {
                        status deprecated;
                        type yang:counter32;
                        description "Number of times the session-state changed to 'Up'.";
                    }

                    leaf down-count {
                        status deprecated;
                        type yang:counter32;
                        description "Number of times the session-state changed to 'Down'.";
                    }

                    leaf up-time {
                        status deprecated;
                        type types-sros:time-interval;
                        description "Time interval elapsed since the session is in state 'Up'.";
                    }

                    leaf down-time {
                        status deprecated;
                        type types-sros:time-interval;
                        description "Time interval elapsed since the session is in state 'Down'.";
                    }

                    leaf last-down-duration {
                        status deprecated;
                        type types-sros:time-interval;
                        description "Time interval the session was in another state before it went 'Up'";
                    }

                    leaf last-up-duration {
                        status deprecated;
                        type types-sros:time-interval;
                        description "Time interval the session was in state 'Up' before it left this state";
                    }

                    leaf received-messages {
                        status deprecated;
                        type yang:counter32;
                        description "Number of messages received for the bfd session.";
                    }

                    leaf version-mismatch {
                        status deprecated;
                        type yang:counter32;
                        description "Number of version mismatch errors for the bfd session.";
                    }

                    leaf last-received {
                        status deprecated;
                        type yang:date-and-time;
                        description
                            "Time when the most recent message was received for the
                             bfd session that was not handled by the network processor.";
                    }

                    leaf time-since-np-receive {
                        status deprecated;
                        type uint32;
                        units "milliseconds";
                        description
                            "Time elapsed since the most recent message was received
                             by the network processor for the BFD session. Zero is returned
                             if the session is Down.";
                    }

                    leaf sent-messages {
                        status deprecated;
                        type yang:counter32;
                        description "Number of messages sent in this session.";
                    }

                    leaf last-sent {
                        status deprecated;
                        type yang:date-and-time;
                        description
                            "Time when the most recent message was sent
                             (not including the ones transmitted by the network processor).";
                    }

                    leaf finals-sent {
                        status deprecated;
                        type uint32;
                        description
                            "Number of protocol messages sent with the final
                             flag set.";
                    }

                    leaf time-since-np-sent {
                        status deprecated;
                        type uint32;
                        units "milliseconds";
                        description
                            "Time elapsed since the most recent message was sent
                             by the network processor for the BFD session. Zero is returned
                             if the session is Down.";
                    }

                } // container statistics

            } // list lsp-head-session

            list named-lsp-head-session {
                key "router-instance session-fec-type remote-address address path-id lsp";
                description "Enter the named-lsp-head-session list instance";

                leaf router-instance {
                    type types-sros:router-instance;
                    description
                        "The administrative name for this virtual router. The router
                         name must be unique among all virtual routers in the system.";
                }

                leaf session-fec-type {
                    type types-bfd:fec-type;
                    description "Fec type of this BFD session.";
                }

                leaf remote-address {
                    type types-sros:ip-address-with-zone;
                    description "Address of the remote endpoint of this BFD session.";
                }

                leaf address {
                    type types-sros:ip-address-with-zone;
                    description "Address of the local endpoint of this BFD session.";
                }

                leaf path-id {
                    type uint32;
                    description "Tunnel id when applicable. 0 otherwise";
                }

                leaf lsp {
                    type types-sros:named-item-64-or-empty;
                    description "LSP";
                }

                leaf session-name {
                    type string {
                        length "1..160";
                    }
                    description "Session name";
                }

                container state {
                    description "Enter the state context";

                    leaf location {
                        type types-bfd:act-endpoint-type;
                        description "Location of the BFD session.";
                    }

                    leaf configured-location {
                        type types-bfd:cfg-endpoint-type;
                        description "Configured location of the BFD session.";
                    }

                    leaf oper-state {
                        type types-sros:oper-state;
                        description "Current operational state of this session.";
                    }

                    leaf protocols {
                        type types-bfd:protocols;
                        description "Protocols using this BFD session.";
                    }

                    leaf session-state {
                        type types-bfd:session-state;
                        description "State of the BFD protocol.";
                    }

                    leaf down-reasons {
                        type bits {
                            bit no-protocols                   { position 0; }
                            bit no-heart-beat                  { position 1; }
                            bit echo-failed                    { position 2; }
                            bit nbr-signal-down                { position 3; }
                            bit fwd-plane-reset                { position 4; }
                            bit path-down                      { position 5; }
                            bit nbr-admin-down                 { position 6; }
                            bit admin-clear                    { position 7; }
                            bit mis-conn-defect                { position 8; }
                        }
                        description "Reasons why a BFD session is not up.";
                    }

                    leaf transmit-interval {
                        type uint32;
                        units "milliseconds";
                        description "Negotiated transmit interval.";
                    }

                    leaf receive-interval {
                        type uint32;
                        units "milliseconds";
                        description "Negotiated receive interval.";
                    }

                    leaf multiplier {
                        type uint32;
                        units "milliseconds";
                        description "Negotiated multiplier.";
                    }

                } // container state

                container local-parameters {
                    description "Enter the local-parameters context";

                    leaf discriminator {
                        type uint32;
                        description "Unique discriminator for this session.";
                    }

                    leaf state {
                        type types-bfd:session-state;
                        description "State of this session.";
                    }

                    leaf diag {
                        type enumeration {
                            enum detect-time-expired            { value 1; }
                            enum echo-func-failed               { value 2; }
                            enum neighbor-down                  { value 3; }
                            enum forwarding-plane-reset         { value 4; }
                            enum path-down                      { value 5; }
                            enum concatenated-path-down         { value 6; }
                            enum admin-down                     { value 7; }
                            enum reverse-concat-path-down       { value 8; }
                            enum mis-connectivity-defect        { value 9; }
                            enum admin-clear                    { value 39; }
                        }
                        description "Diagnostic value.";
                    }

                    leaf mode {
                        type enumeration {
                            enum async                          { value 0; }
                            enum demand                         { value 1; }
                        }
                        description "Mode.";
                    }

                    leaf tx-interval {
                        type uint32;
                        description "Minimal transmit interval.";
                    }

                    leaf multiplier {
                        type uint32;
                        description "Multiplier.";
                    }

                    leaf rx-interval {
                        type uint32;
                        description "Minimal receive interval.";
                    }

                } // container local-parameters

                container remote-parameters {
                    description "Enter the remote-parameters context";

                    leaf discriminator {
                        type uint32;
                        description "Unique discriminator for this session.";
                    }

                    leaf state {
                        type types-bfd:session-state;
                        description "State of this session.";
                    }

                    leaf diag {
                        type enumeration {
                            enum detect-time-expired            { value 1; }
                            enum echo-func-failed               { value 2; }
                            enum neighbor-down                  { value 3; }
                            enum forwarding-plane-reset         { value 4; }
                            enum path-down                      { value 5; }
                            enum concatenated-path-down         { value 6; }
                            enum admin-down                     { value 7; }
                            enum reverse-concat-path-down       { value 8; }
                            enum mis-connectivity-defect        { value 9; }
                            enum admin-clear                    { value 39; }
                        }
                        description "Diagnostic value.";
                    }

                    leaf mode {
                        type enumeration {
                            enum async                          { value 0; }
                            enum demand                         { value 1; }
                        }
                        description "Mode.";
                    }

                    leaf tx-interval {
                        type uint32;
                        description "Minimal transmit interval.";
                    }

                    leaf multiplier {
                        type uint32;
                        description "Multiplier.";
                    }

                    leaf rx-interval {
                        type uint32;
                        description "Minimal receive interval.";
                    }

                    leaf c-flag {
                        type boolean;
                        description "BFD is independent of the control plane.";
                    }

                } // container remote-parameters

                container statistics {
                    description "Enter the statistics context";

                    leaf up-count {
                        type yang:counter32;
                        description "Number of times the session-state changed to 'Up'.";
                    }

                    leaf down-count {
                        type yang:counter32;
                        description "Number of times the session-state changed to 'Down'.";
                    }

                    leaf up-time {
                        type types-sros:time-interval;
                        description "Time interval elapsed since the session is in state 'Up'.";
                    }

                    leaf down-time {
                        type types-sros:time-interval;
                        description "Time interval elapsed since the session is in state 'Down'.";
                    }

                    leaf last-down-duration {
                        type types-sros:time-interval;
                        description "Time interval the session was in another state before it went 'Up'";
                    }

                    leaf last-up-duration {
                        type types-sros:time-interval;
                        description "Time interval the session was in state 'Up' before it left this state";
                    }

                    leaf received-messages {
                        type yang:counter32;
                        description "Number of messages received for the bfd session.";
                    }

                    leaf version-mismatch {
                        type yang:counter32;
                        description "Number of version mismatch errors for the bfd session.";
                    }

                    leaf last-received {
                        type yang:date-and-time;
                        description
                            "Time when the most recent message was received for the
                             bfd session that was not handled by the network processor.";
                    }

                    leaf time-since-np-receive {
                        type uint32;
                        units "milliseconds";
                        description
                            "Time elapsed since the most recent message was received
                             by the network processor for the BFD session. Zero is returned
                             if the session is Down.";
                    }

                    leaf sent-messages {
                        type yang:counter32;
                        description "Number of messages sent in this session.";
                    }

                    leaf last-sent {
                        type yang:date-and-time;
                        description
                            "Time when the most recent message was sent
                             (not including the ones transmitted by the network processor).";
                    }

                    leaf finals-sent {
                        type uint32;
                        description
                            "Number of protocol messages sent with the final
                             flag set.";
                    }

                    leaf time-since-np-sent {
                        type uint32;
                        units "milliseconds";
                        description
                            "Time elapsed since the most recent message was sent
                             by the network processor for the BFD session. Zero is returned
                             if the session is Down.";
                    }

                } // container statistics

            } // list named-lsp-head-session

            list pt-to-pt-session {
                key "router-instance interface-name address remote-address";
                description "Enter the pt-to-pt-session list instance";

                leaf router-instance {
                    type types-sros:router-instance;
                    description
                        "Administrative name for this virtual router. The router
                         name must be unique among all virtual routers in the system.";
                }

                leaf interface-name {
                    type types-sros:named-item;
                    description "Administrative name assigned to this router interface.";
                }

                leaf address {
                    type types-sros:ip-address-with-zone;
                    description "Address of the local endpoint of this BFD session.";
                }

                leaf remote-address {
                    type types-sros:ip-address-with-zone;
                    description "Address of the remote endpoint of this BFD session.";
                }

                container state {
                    description "Enter the state context";

                    leaf location {
                        type types-bfd:act-endpoint-type;
                        description "Location of the BFD session.";
                    }

                    leaf configured-location {
                        type types-bfd:cfg-endpoint-type;
                        description "Configured location of the BFD session.";
                    }

                    leaf oper-state {
                        type types-sros:oper-state;
                        description "Current operational state of this session.";
                    }

                    leaf protocols {
                        type types-bfd:protocols;
                        description "Protocols using this BFD session.";
                    }

                    leaf session-state {
                        type types-bfd:session-state;
                        description "State of the BFD protocol.";
                    }

                    leaf down-reasons {
                        type bits {
                            bit no-protocols                   { position 0; }
                            bit no-heart-beat                  { position 1; }
                            bit echo-failed                    { position 2; }
                            bit nbr-signal-down                { position 3; }
                            bit fwd-plane-reset                { position 4; }
                            bit path-down                      { position 5; }
                            bit nbr-admin-down                 { position 6; }
                            bit admin-clear                    { position 7; }
                            bit mis-conn-defect                { position 8; }
                        }
                        description "Reasons why a BFD session is not up.";
                    }

                    leaf transmit-interval {
                        type uint32;
                        units "milliseconds";
                        description "Negotiated transmit interval.";
                    }

                    leaf receive-interval {
                        type uint32;
                        units "milliseconds";
                        description "Negotiated receive interval.";
                    }

                    leaf multiplier {
                        type uint32;
                        units "milliseconds";
                        description "Negotiated multiplier.";
                    }

                } // container state

                container statistics {
                    description "Enter the statistics context";

                    leaf up-count {
                        type yang:counter32;
                        description "Number of times the session-state changed to 'Up'.";
                    }

                    leaf down-count {
                        type yang:counter32;
                        description "Number of times the session-state changed to 'Down'.";
                    }

                    leaf up-time {
                        type types-sros:time-interval;
                        description "Time interval elapsed since the session is in state 'Up'.";
                    }

                    leaf down-time {
                        type types-sros:time-interval;
                        description "Time interval elapsed since the session is in state 'Down'.";
                    }

                    leaf last-down-duration {
                        type types-sros:time-interval;
                        description "Time interval the session was in another state before it went 'Up'";
                    }

                    leaf last-up-duration {
                        type types-sros:time-interval;
                        description "Time interval the session was in state 'Up' before it left this state";
                    }

                    leaf received-messages {
                        type yang:counter32;
                        description "Number of messages received for the bfd session.";
                    }

                    leaf version-mismatch {
                        type yang:counter32;
                        description "Number of version mismatch errors for the bfd session.";
                    }

                    leaf last-received {
                        type yang:date-and-time;
                        description
                            "Time when the most recent message was received for the
                             bfd session that was not handled by the network processor.";
                    }

                    leaf time-since-np-receive {
                        type uint32;
                        units "milliseconds";
                        description
                            "Time elapsed since the most recent message was received
                             by the network processor for the BFD session. Zero is returned
                             if the session is Down.";
                    }

                    leaf sent-messages {
                        type yang:counter32;
                        description "Number of messages sent in this session.";
                    }

                    leaf last-sent {
                        type yang:date-and-time;
                        description
                            "Time when the most recent message was sent
                             (not including the ones transmitted by the network processor).";
                    }

                    leaf finals-sent {
                        type uint32;
                        description
                            "Number of protocol messages sent with the final
                             flag set.";
                    }

                    leaf time-since-np-sent {
                        type uint32;
                        units "milliseconds";
                        description
                            "Time elapsed since the most recent message was sent
                             by the network processor for the BFD session. Zero is returned
                             if the session is Down.";
                    }

                } // container statistics

                container local-parameters {
                    description "Enter the local-parameters context";

                    leaf discriminator {
                        type uint32;
                        description "Unique discriminator for this session.";
                    }

                    leaf state {
                        type types-bfd:session-state;
                        description "State of this session.";
                    }

                    leaf diag {
                        type enumeration {
                            enum detect-time-expired            { value 1; }
                            enum echo-func-failed               { value 2; }
                            enum neighbor-down                  { value 3; }
                            enum forwarding-plane-reset         { value 4; }
                            enum path-down                      { value 5; }
                            enum concatenated-path-down         { value 6; }
                            enum admin-down                     { value 7; }
                            enum reverse-concat-path-down       { value 8; }
                            enum mis-connectivity-defect        { value 9; }
                            enum admin-clear                    { value 39; }
                        }
                        description "Diagnostic value.";
                    }

                    leaf mode {
                        type enumeration {
                            enum async                          { value 0; }
                            enum demand                         { value 1; }
                        }
                        description "Mode.";
                    }

                    leaf tx-interval {
                        type uint32;
                        description "Minimal transmit interval.";
                    }

                    leaf multiplier {
                        type uint32;
                        description "Multiplier.";
                    }

                    leaf rx-interval {
                        type uint32;
                        description "Minimal receive interval.";
                    }

                } // container local-parameters

                container remote-parameters {
                    description "Enter the remote-parameters context";

                    leaf discriminator {
                        type uint32;
                        description "Unique discriminator for this session.";
                    }

                    leaf state {
                        type types-bfd:session-state;
                        description "State of this session.";
                    }

                    leaf diag {
                        type enumeration {
                            enum detect-time-expired            { value 1; }
                            enum echo-func-failed               { value 2; }
                            enum neighbor-down                  { value 3; }
                            enum forwarding-plane-reset         { value 4; }
                            enum path-down                      { value 5; }
                            enum concatenated-path-down         { value 6; }
                            enum admin-down                     { value 7; }
                            enum reverse-concat-path-down       { value 8; }
                            enum mis-connectivity-defect        { value 9; }
                            enum admin-clear                    { value 39; }
                        }
                        description "Diagnostic value.";
                    }

                    leaf mode {
                        type enumeration {
                            enum async                          { value 0; }
                            enum demand                         { value 1; }
                        }
                        description "Mode.";
                    }

                    leaf tx-interval {
                        type uint32;
                        description "Minimal transmit interval.";
                    }

                    leaf multiplier {
                        type uint32;
                        description "Multiplier.";
                    }

                    leaf rx-interval {
                        type uint32;
                        description "Minimal receive interval.";
                    }

                    leaf c-flag {
                        type boolean;
                        description "BFD is independent of the control plane.";
                    }

                } // container remote-parameters

            } // list pt-to-pt-session

            list mp-head-session {
                key "router-instance interface-name address remote-address";
                description "Enter the mp-head-session list instance";

                leaf router-instance {
                    type types-sros:router-instance;
                    description
                        "Administrative name for this virtual router. The router
                         name must be unique among all virtual routers in the system.";
                }

                leaf interface-name {
                    type types-sros:named-item;
                    description
                        "Administrative name assigned to this point to multipoint
                         interface.";
                }

                leaf address {
                    type types-sros:ip-address-with-zone;
                    description "Address of the local endpoint of this BFD session.";
                }

                leaf remote-address {
                    type types-sros:ip-address-with-zone;
                    description "Address of the remote endpoint of this BFD session.";
                }

                container state {
                    description "Enter the state context";

                    leaf location {
                        type types-bfd:act-endpoint-type;
                        description "Location of the BFD session.";
                    }

                    leaf configured-location {
                        type types-bfd:cfg-endpoint-type;
                        description "Configured location of the BFD session.";
                    }

                    leaf oper-state {
                        type types-sros:oper-state;
                        description "Current operational state of this session.";
                    }

                    leaf protocols {
                        type types-bfd:protocols;
                        description "Protocols using this BFD session.";
                    }

                    leaf session-state {
                        type types-bfd:session-state;
                        description "State of the BFD protocol.";
                    }

                    leaf down-reasons {
                        type bits {
                            bit no-protocols                   { position 0; }
                            bit no-heart-beat                  { position 1; }
                            bit echo-failed                    { position 2; }
                            bit nbr-signal-down                { position 3; }
                            bit fwd-plane-reset                { position 4; }
                            bit path-down                      { position 5; }
                            bit nbr-admin-down                 { position 6; }
                            bit admin-clear                    { position 7; }
                            bit mis-conn-defect                { position 8; }
                        }
                        description "Reasons why a BFD session is not up.";
                    }

                    leaf transmit-interval {
                        type uint32;
                        units "milliseconds";
                        description "Negotiated transmit interval.";
                    }

                    leaf receive-interval {
                        type uint32;
                        units "milliseconds";
                        description "Negotiated receive interval.";
                    }

                    leaf multiplier {
                        type uint32;
                        units "milliseconds";
                        description "Negotiated multiplier.";
                    }

                } // container state

                container statistics {
                    description "Enter the statistics context";

                    leaf up-count {
                        type yang:counter32;
                        description "Number of times the session-state changed to 'Up'.";
                    }

                    leaf down-count {
                        type yang:counter32;
                        description "Number of times the session-state changed to 'Down'.";
                    }

                    leaf up-time {
                        type types-sros:time-interval;
                        description "Time interval elapsed since the session is in state 'Up'.";
                    }

                    leaf down-time {
                        type types-sros:time-interval;
                        description "Time interval elapsed since the session is in state 'Down'.";
                    }

                    leaf last-down-duration {
                        type types-sros:time-interval;
                        description "Time interval the session was in another state before it went 'Up'";
                    }

                    leaf last-up-duration {
                        type types-sros:time-interval;
                        description "Time interval the session was in state 'Up' before it left this state";
                    }

                    leaf sent-messages {
                        type yang:counter32;
                        description "Number of messages sent in this session.";
                    }

                    leaf last-sent {
                        type yang:date-and-time;
                        description
                            "Time when the most recent message was sent
                             (not including the ones transmitted by the network processor).";
                    }

                    leaf finals-sent {
                        type uint32;
                        description
                            "Number of protocol messages sent with the final
                             flag set.";
                    }

                    leaf time-since-np-sent {
                        type uint32;
                        units "milliseconds";
                        description
                            "Time elapsed since the most recent message was sent
                             by the network processor for the BFD session. Zero is returned
                             if the session is Down.";
                    }

                } // container statistics

                container local-parameters {
                    description "Enter the local-parameters context";

                    leaf discriminator {
                        type uint32;
                        description "Unique discriminator for this session.";
                    }

                    leaf state {
                        type types-bfd:session-state;
                        description "State of this session.";
                    }

                    leaf diag {
                        type enumeration {
                            enum detect-time-expired            { value 1; }
                            enum echo-func-failed               { value 2; }
                            enum neighbor-down                  { value 3; }
                            enum forwarding-plane-reset         { value 4; }
                            enum path-down                      { value 5; }
                            enum concatenated-path-down         { value 6; }
                            enum admin-down                     { value 7; }
                            enum reverse-concat-path-down       { value 8; }
                            enum mis-connectivity-defect        { value 9; }
                            enum admin-clear                    { value 39; }
                        }
                        description "Diagnostic value.";
                    }

                    leaf mode {
                        type enumeration {
                            enum async                          { value 0; }
                            enum demand                         { value 1; }
                        }
                        description "Mode.";
                    }

                    leaf tx-interval {
                        type uint32;
                        description "Minimal transmit interval.";
                    }

                    leaf multiplier {
                        type uint32;
                        description "Multiplier.";
                    }

                    leaf rx-interval {
                        type uint32;
                        description "Minimal receive interval.";
                    }

                } // container local-parameters

            } // list mp-head-session

            list mp-tail-session {
                key "router-instance interface-name address remote-address";
                description "Enter the mp-tail-session list instance";

                leaf router-instance {
                    type types-sros:router-instance;
                    description
                        "Administrative name for this virtual router. The router
                         name must be unique among all virtual routers in the system.";
                }

                leaf interface-name {
                    type types-sros:named-item;
                    description
                        "Administrative name assigned to this point to multipoint
                         interface.";
                }

                leaf address {
                    type types-sros:ip-address-with-zone;
                    description "Address of the local endpoint of this BFD session.";
                }

                leaf remote-address {
                    type types-sros:ip-address-with-zone;
                    description "Address of the remote endpoint of this BFD session.";
                }

                container state {
                    description "Enter the state context";

                    leaf location {
                        type types-bfd:act-endpoint-type;
                        description "Location of the BFD session.";
                    }

                    leaf configured-location {
                        type types-bfd:cfg-endpoint-type;
                        description "Configured location of the BFD session.";
                    }

                    leaf oper-state {
                        type types-sros:oper-state;
                        description "Current operational state of this session.";
                    }

                    leaf protocols {
                        type types-bfd:protocols;
                        description "Protocols using this BFD session.";
                    }

                    leaf session-state {
                        type types-bfd:session-state;
                        description "State of the BFD protocol.";
                    }

                    leaf down-reasons {
                        type bits {
                            bit no-protocols                   { position 0; }
                            bit no-heart-beat                  { position 1; }
                            bit echo-failed                    { position 2; }
                            bit nbr-signal-down                { position 3; }
                            bit fwd-plane-reset                { position 4; }
                            bit path-down                      { position 5; }
                            bit nbr-admin-down                 { position 6; }
                            bit admin-clear                    { position 7; }
                            bit mis-conn-defect                { position 8; }
                        }
                        description "Reasons why a BFD session is not up.";
                    }

                    leaf transmit-interval {
                        type uint32;
                        units "milliseconds";
                        description "Negotiated transmit interval.";
                    }

                    leaf receive-interval {
                        type uint32;
                        units "milliseconds";
                        description "Negotiated receive interval.";
                    }

                    leaf multiplier {
                        type uint32;
                        units "milliseconds";
                        description "Negotiated multiplier.";
                    }

                } // container state

                container statistics {
                    description "Enter the statistics context";

                    leaf up-count {
                        type yang:counter32;
                        description "Number of times the session-state changed to 'Up'.";
                    }

                    leaf down-count {
                        type yang:counter32;
                        description "Number of times the session-state changed to 'Down'.";
                    }

                    leaf up-time {
                        type types-sros:time-interval;
                        description "Time interval elapsed since the session is in state 'Up'.";
                    }

                    leaf down-time {
                        type types-sros:time-interval;
                        description "Time interval elapsed since the session is in state 'Down'.";
                    }

                    leaf last-down-duration {
                        type types-sros:time-interval;
                        description "Time interval the session was in another state before it went 'Up'";
                    }

                    leaf last-up-duration {
                        type types-sros:time-interval;
                        description "Time interval the session was in state 'Up' before it left this state";
                    }

                    leaf received-messages {
                        type yang:counter32;
                        description "Number of messages received for the bfd session.";
                    }

                    leaf version-mismatch {
                        type yang:counter32;
                        description "Number of version mismatch errors for the bfd session.";
                    }

                    leaf last-received {
                        type yang:date-and-time;
                        description
                            "Time when the most recent message was received for the
                             bfd session that was not handled by the network processor.";
                    }

                    leaf time-since-np-receive {
                        type uint32;
                        units "milliseconds";
                        description
                            "Time elapsed since the most recent message was received
                             by the network processor for the BFD session. Zero is returned
                             if the session is Down.";
                    }

                } // container statistics

                container remote-parameters {
                    description "Enter the remote-parameters context";

                    leaf discriminator {
                        type uint32;
                        description "Unique discriminator for this session.";
                    }

                    leaf state {
                        type types-bfd:session-state;
                        description "State of this session.";
                    }

                    leaf diag {
                        type enumeration {
                            enum detect-time-expired            { value 1; }
                            enum echo-func-failed               { value 2; }
                            enum neighbor-down                  { value 3; }
                            enum forwarding-plane-reset         { value 4; }
                            enum path-down                      { value 5; }
                            enum concatenated-path-down         { value 6; }
                            enum admin-down                     { value 7; }
                            enum reverse-concat-path-down       { value 8; }
                            enum mis-connectivity-defect        { value 9; }
                            enum admin-clear                    { value 39; }
                        }
                        description "Diagnostic value.";
                    }

                    leaf mode {
                        type enumeration {
                            enum async                          { value 0; }
                            enum demand                         { value 1; }
                        }
                        description "Mode.";
                    }

                    leaf tx-interval {
                        type uint32;
                        description "Minimal transmit interval.";
                    }

                    leaf multiplier {
                        type uint32;
                        description "Multiplier.";
                    }

                    leaf rx-interval {
                        type uint32;
                        description "Minimal receive interval.";
                    }

                    leaf c-flag {
                        type boolean;
                        description "BFD is independent of the control plane.";
                    }

                } // container remote-parameters

            } // list mp-tail-session

            list mp-client-session {
                key "router-instance interface-name address remote-address";
                description "Enter the mp-client-session list instance";

                leaf router-instance {
                    type types-sros:router-instance;
                    description
                        "Administrative name for this virtual router. The router
                         name must be unique among all virtual routers in the system.";
                }

                leaf interface-name {
                    type types-sros:named-item;
                    description
                        "Administrative name assigned to this point to multipoint
                         interface.";
                }

                leaf address {
                    type types-sros:ip-address-with-zone;
                    description "Address of the local endpoint of this BFD session.";
                }

                leaf remote-address {
                    type types-sros:ip-address-with-zone;
                    description "Address of the remote endpoint of this BFD session.";
                }

                container state {
                    description "Enter the state context";

                    leaf location {
                        type types-bfd:act-endpoint-type;
                        description "Location of the BFD session.";
                    }

                    leaf configured-location {
                        type types-bfd:cfg-endpoint-type;
                        description "Configured location of the BFD session.";
                    }

                    leaf oper-state {
                        type types-sros:oper-state;
                        description "Current operational state of this session.";
                    }

                    leaf protocols {
                        type types-bfd:protocols;
                        description "Protocols using this BFD session.";
                    }

                    leaf session-state {
                        type types-bfd:session-state;
                        description "State of the BFD protocol.";
                    }

                    leaf down-reasons {
                        type bits {
                            bit no-protocols                   { position 0; }
                            bit no-heart-beat                  { position 1; }
                            bit echo-failed                    { position 2; }
                            bit nbr-signal-down                { position 3; }
                            bit fwd-plane-reset                { position 4; }
                            bit path-down                      { position 5; }
                            bit nbr-admin-down                 { position 6; }
                            bit admin-clear                    { position 7; }
                            bit mis-conn-defect                { position 8; }
                        }
                        description "Reasons why a BFD session is not up.";
                    }

                    leaf transmit-interval {
                        type uint32;
                        units "milliseconds";
                        description "Negotiated transmit interval.";
                    }

                    leaf receive-interval {
                        type uint32;
                        units "milliseconds";
                        description "Negotiated receive interval.";
                    }

                    leaf multiplier {
                        type uint32;
                        units "milliseconds";
                        description "Negotiated multiplier.";
                    }

                } // container state

                container statistics {
                    description "Enter the statistics context";

                    leaf up-count {
                        type yang:counter32;
                        description "Number of times the session-state changed to 'Up'.";
                    }

                    leaf down-count {
                        type yang:counter32;
                        description "Number of times the session-state changed to 'Down'.";
                    }

                    leaf up-time {
                        type types-sros:time-interval;
                        description "Time interval elapsed since the session is in state 'Up'.";
                    }

                    leaf down-time {
                        type types-sros:time-interval;
                        description "Time interval elapsed since the session is in state 'Down'.";
                    }

                    leaf last-down-duration {
                        type types-sros:time-interval;
                        description "Time interval the session was in another state before it went 'Up'";
                    }

                    leaf last-up-duration {
                        type types-sros:time-interval;
                        description "Time interval the session was in state 'Up' before it left this state";
                    }

                    leaf received-messages {
                        type yang:counter32;
                        description "Number of messages received for the bfd session.";
                    }

                    leaf version-mismatch {
                        type yang:counter32;
                        description "Number of version mismatch errors for the bfd session.";
                    }

                    leaf last-received {
                        type yang:date-and-time;
                        description
                            "Time when the most recent message was received for the
                             bfd session that was not handled by the network processor.";
                    }

                    leaf time-since-np-receive {
                        type uint32;
                        units "milliseconds";
                        description
                            "Time elapsed since the most recent message was received
                             by the network processor for the BFD session. Zero is returned
                             if the session is Down.";
                    }

                    leaf sent-messages {
                        type yang:counter32;
                        description "Number of messages sent in this session.";
                    }

                    leaf last-sent {
                        type yang:date-and-time;
                        description
                            "Time when the most recent message was sent
                             (not including the ones transmitted by the network processor).";
                    }

                    leaf finals-sent {
                        type uint32;
                        description
                            "Number of protocol messages sent with the final
                             flag set.";
                    }

                    leaf time-since-np-sent {
                        type uint32;
                        units "milliseconds";
                        description
                            "Time elapsed since the most recent message was sent
                             by the network processor for the BFD session. Zero is returned
                             if the session is Down.";
                    }

                } // container statistics

                container local-parameters {
                    description "Enter the local-parameters context";

                    leaf discriminator {
                        type uint32;
                        description "Unique discriminator for this session.";
                    }

                    leaf state {
                        type types-bfd:session-state;
                        description "State of this session.";
                    }

                    leaf diag {
                        type enumeration {
                            enum detect-time-expired            { value 1; }
                            enum echo-func-failed               { value 2; }
                            enum neighbor-down                  { value 3; }
                            enum forwarding-plane-reset         { value 4; }
                            enum path-down                      { value 5; }
                            enum concatenated-path-down         { value 6; }
                            enum admin-down                     { value 7; }
                            enum reverse-concat-path-down       { value 8; }
                            enum mis-connectivity-defect        { value 9; }
                            enum admin-clear                    { value 39; }
                        }
                        description "Diagnostic value.";
                    }

                    leaf mode {
                        type enumeration {
                            enum async                          { value 0; }
                            enum demand                         { value 1; }
                        }
                        description "Mode.";
                    }

                    leaf tx-interval {
                        type uint32;
                        description "Minimal transmit interval.";
                    }

                    leaf multiplier {
                        type uint32;
                        description "Multiplier.";
                    }

                    leaf rx-interval {
                        type uint32;
                        description "Minimal receive interval.";
                    }

                } // container local-parameters

                container remote-parameters {
                    description "Enter the remote-parameters context";

                    leaf discriminator {
                        type uint32;
                        description "Unique discriminator for this session.";
                    }

                    leaf state {
                        type types-bfd:session-state;
                        description "State of this session.";
                    }

                    leaf diag {
                        type enumeration {
                            enum detect-time-expired            { value 1; }
                            enum echo-func-failed               { value 2; }
                            enum neighbor-down                  { value 3; }
                            enum forwarding-plane-reset         { value 4; }
                            enum path-down                      { value 5; }
                            enum concatenated-path-down         { value 6; }
                            enum admin-down                     { value 7; }
                            enum reverse-concat-path-down       { value 8; }
                            enum mis-connectivity-defect        { value 9; }
                            enum admin-clear                    { value 39; }
                        }
                        description "Diagnostic value.";
                    }

                    leaf mode {
                        type enumeration {
                            enum async                          { value 0; }
                            enum demand                         { value 1; }
                        }
                        description "Mode.";
                    }

                    leaf tx-interval {
                        type uint32;
                        description "Minimal transmit interval.";
                    }

                    leaf multiplier {
                        type uint32;
                        description "Multiplier.";
                    }

                    leaf rx-interval {
                        type uint32;
                        description "Minimal receive interval.";
                    }

                    leaf c-flag {
                        type boolean;
                        description "BFD is independent of the control plane.";
                    }

                } // container remote-parameters

            } // list mp-client-session

            list cc-only-session {
                key "label-id router-instance interface-name";
                description "Enter the cc-only-session list instance";

                leaf label-id {
                    type types-services:ingress-vc-label;
                    description "Incoming label id for this BFD session.";
                }

                leaf router-instance {
                    type types-sros:router-instance;
                    description
                        "Administrative name for this virtual router. The router
                         name must be unique among all virtual routers in the system.";
                }

                leaf interface-name {
                    type types-sros:named-item;
                    description "Administrative name assigned to this router interface.";
                }

                container state {
                    description "Enter the state context";

                    leaf location {
                        type types-bfd:act-endpoint-type;
                        description "Location of the BFD session.";
                    }

                    leaf configured-location {
                        type types-bfd:cfg-endpoint-type;
                        description "Configured location of the BFD session.";
                    }

                    leaf oper-state {
                        type types-sros:oper-state;
                        description "Current operational state of this session.";
                    }

                    leaf protocols {
                        type types-bfd:protocols;
                        description "Protocols using this BFD session.";
                    }

                    leaf session-state {
                        type types-bfd:session-state;
                        description "State of the BFD protocol.";
                    }

                    leaf down-reasons {
                        type bits {
                            bit no-protocols                   { position 0; }
                            bit no-heart-beat                  { position 1; }
                            bit echo-failed                    { position 2; }
                            bit nbr-signal-down                { position 3; }
                            bit fwd-plane-reset                { position 4; }
                            bit path-down                      { position 5; }
                            bit nbr-admin-down                 { position 6; }
                            bit admin-clear                    { position 7; }
                            bit mis-conn-defect                { position 8; }
                        }
                        description "Reasons why a BFD session is not up.";
                    }

                    leaf transmit-interval {
                        type uint32;
                        units "milliseconds";
                        description "Negotiated transmit interval.";
                    }

                    leaf receive-interval {
                        type uint32;
                        units "milliseconds";
                        description "Negotiated receive interval.";
                    }

                    leaf multiplier {
                        type uint32;
                        units "milliseconds";
                        description "Negotiated multiplier.";
                    }

                    leaf path-id {
                        type enumeration {
                            enum not-applicable                 { value 0; }
                            enum working                        { value 1; }
                            enum protecting                     { value 2; }
                        }
                        description "Source path index for the MPLS-TP LSP path.";
                    }

                    leaf lsp-index {
                        type uint32;
                        description "Source tunnel id for the MPLS-TP path.";
                    }

                    leaf remote-tunnel-number {
                        type uint32;
                        description "Destination tunnel id for the MPLS-TP path.";
                    }

                    leaf remote-node-id {
                        type uint32;
                        description "Destination node id of an MPLS-TP LSP.";
                    }

                    leaf remote-global-id {
                        type uint32;
                        description "Global identifier for an MPLS-TP LSP.";
                    }

                    leaf remote-lsp-num {
                        type uint32;
                        description "MPLS-TP LSP destination path number.";
                    }

                } // container state

                container statistics {
                    description "Enter the statistics context";

                    leaf up-count {
                        type yang:counter32;
                        description "Number of times the session-state changed to 'Up'.";
                    }

                    leaf down-count {
                        type yang:counter32;
                        description "Number of times the session-state changed to 'Down'.";
                    }

                    leaf up-time {
                        type types-sros:time-interval;
                        description "Time interval elapsed since the session is in state 'Up'.";
                    }

                    leaf down-time {
                        type types-sros:time-interval;
                        description "Time interval elapsed since the session is in state 'Down'.";
                    }

                    leaf last-down-duration {
                        type types-sros:time-interval;
                        description "Time interval the session was in another state before it went 'Up'";
                    }

                    leaf last-up-duration {
                        type types-sros:time-interval;
                        description "Time interval the session was in state 'Up' before it left this state";
                    }

                    leaf received-messages {
                        type yang:counter32;
                        description "Number of messages received for the bfd session.";
                    }

                    leaf version-mismatch {
                        type yang:counter32;
                        description "Number of version mismatch errors for the bfd session.";
                    }

                    leaf last-received {
                        type yang:date-and-time;
                        description
                            "Time when the most recent message was received for the
                             bfd session that was not handled by the network processor.";
                    }

                    leaf time-since-np-receive {
                        type uint32;
                        units "milliseconds";
                        description
                            "Time elapsed since the most recent message was received
                             by the network processor for the BFD session. Zero is returned
                             if the session is Down.";
                    }

                    leaf sent-messages {
                        type yang:counter32;
                        description "Number of messages sent in this session.";
                    }

                    leaf last-sent {
                        type yang:date-and-time;
                        description
                            "Time when the most recent message was sent
                             (not including the ones transmitted by the network processor).";
                    }

                    leaf finals-sent {
                        type uint32;
                        description
                            "Number of protocol messages sent with the final
                             flag set.";
                    }

                    leaf time-since-np-sent {
                        type uint32;
                        units "milliseconds";
                        description
                            "Time elapsed since the most recent message was sent
                             by the network processor for the BFD session. Zero is returned
                             if the session is Down.";
                    }

                } // container statistics

                container local-parameters {
                    description "Enter the local-parameters context";

                    leaf discriminator {
                        type uint32;
                        description "Unique discriminator for this session.";
                    }

                    leaf state {
                        type types-bfd:session-state;
                        description "State of this session.";
                    }

                    leaf diag {
                        type enumeration {
                            enum detect-time-expired            { value 1; }
                            enum echo-func-failed               { value 2; }
                            enum neighbor-down                  { value 3; }
                            enum forwarding-plane-reset         { value 4; }
                            enum path-down                      { value 5; }
                            enum concatenated-path-down         { value 6; }
                            enum admin-down                     { value 7; }
                            enum reverse-concat-path-down       { value 8; }
                            enum mis-connectivity-defect        { value 9; }
                            enum admin-clear                    { value 39; }
                        }
                        description "Diagnostic value.";
                    }

                    leaf mode {
                        type enumeration {
                            enum async                          { value 0; }
                            enum demand                         { value 1; }
                        }
                        description "Mode.";
                    }

                    leaf tx-interval {
                        type uint32;
                        description "Minimal transmit interval.";
                    }

                    leaf multiplier {
                        type uint32;
                        description "Multiplier.";
                    }

                    leaf rx-interval {
                        type uint32;
                        description "Minimal receive interval.";
                    }

                } // container local-parameters

                container remote-parameters {
                    description "Enter the remote-parameters context";

                    leaf discriminator {
                        type uint32;
                        description "Unique discriminator for this session.";
                    }

                    leaf state {
                        type types-bfd:session-state;
                        description "State of this session.";
                    }

                    leaf diag {
                        type enumeration {
                            enum detect-time-expired            { value 1; }
                            enum echo-func-failed               { value 2; }
                            enum neighbor-down                  { value 3; }
                            enum forwarding-plane-reset         { value 4; }
                            enum path-down                      { value 5; }
                            enum concatenated-path-down         { value 6; }
                            enum admin-down                     { value 7; }
                            enum reverse-concat-path-down       { value 8; }
                            enum mis-connectivity-defect        { value 9; }
                            enum admin-clear                    { value 39; }
                        }
                        description "Diagnostic value.";
                    }

                    leaf mode {
                        type enumeration {
                            enum async                          { value 0; }
                            enum demand                         { value 1; }
                        }
                        description "Mode.";
                    }

                    leaf tx-interval {
                        type uint32;
                        description "Minimal transmit interval.";
                    }

                    leaf multiplier {
                        type uint32;
                        description "Multiplier.";
                    }

                    leaf rx-interval {
                        type uint32;
                        description "Minimal receive interval.";
                    }

                    leaf c-flag {
                        type boolean;
                        description "BFD is independent of the control plane.";
                    }

                } // container remote-parameters

            } // list cc-only-session

            list cc-with-cv-session {
                key "label-id router-instance interface-name";
                description "Enter the cc-with-cv-session list instance";

                leaf label-id {
                    type types-services:ingress-vc-label;
                    description "Incoming label id for this BFD session.";
                }

                leaf router-instance {
                    type types-sros:router-instance;
                    description
                        "Administrative name for this virtual router. The router
                         name must be unique among all virtual routers in the system.";
                }

                leaf interface-name {
                    type types-sros:named-item;
                    description "Administrative name assigned to this router interface.";
                }

                container state {
                    description "Enter the state context";

                    leaf location {
                        type types-bfd:act-endpoint-type;
                        description "Location of the BFD session.";
                    }

                    leaf configured-location {
                        type types-bfd:cfg-endpoint-type;
                        description "Configured location of the BFD session.";
                    }

                    leaf oper-state {
                        type types-sros:oper-state;
                        description "Current operational state of this session.";
                    }

                    leaf protocols {
                        type types-bfd:protocols;
                        description "Protocols using this BFD session.";
                    }

                    leaf session-state {
                        type types-bfd:session-state;
                        description "State of the BFD protocol.";
                    }

                    leaf down-reasons {
                        type bits {
                            bit no-protocols                   { position 0; }
                            bit no-heart-beat                  { position 1; }
                            bit echo-failed                    { position 2; }
                            bit nbr-signal-down                { position 3; }
                            bit fwd-plane-reset                { position 4; }
                            bit path-down                      { position 5; }
                            bit nbr-admin-down                 { position 6; }
                            bit admin-clear                    { position 7; }
                            bit mis-conn-defect                { position 8; }
                        }
                        description "Reasons why a BFD session is not up.";
                    }

                    leaf transmit-interval {
                        type uint32;
                        units "milliseconds";
                        description "Negotiated transmit interval.";
                    }

                    leaf receive-interval {
                        type uint32;
                        units "milliseconds";
                        description "Negotiated receive interval.";
                    }

                    leaf multiplier {
                        type uint32;
                        units "milliseconds";
                        description "Negotiated multiplier.";
                    }

                    leaf path-id {
                        type enumeration {
                            enum not-applicable                 { value 0; }
                            enum working                        { value 1; }
                            enum protecting                     { value 2; }
                        }
                        description "Source path index for the MPLS-TP LSP path.";
                    }

                    leaf lsp-index {
                        type uint32;
                        description "Source tunnel id for the MPLS-TP path.";
                    }

                    leaf remote-tunnel-number {
                        type uint32;
                        description "Destination tunnel id for the MPLS-TP path.";
                    }

                    leaf remote-node-id {
                        type uint32;
                        description "Destination node id of an MPLS-TP LSP.";
                    }

                    leaf remote-global-id {
                        type uint32;
                        description "Global identifier for an MPLS-TP LSP.";
                    }

                    leaf remote-lsp-num {
                        type uint32;
                        description "MPLS-TP LSP destination path number.";
                    }

                } // container state

                container statistics {
                    description "Enter the statistics context";

                    leaf up-count {
                        type yang:counter32;
                        description "Number of times the session-state changed to 'Up'.";
                    }

                    leaf down-count {
                        type yang:counter32;
                        description "Number of times the session-state changed to 'Down'.";
                    }

                    leaf up-time {
                        type types-sros:time-interval;
                        description "Time interval elapsed since the session is in state 'Up'.";
                    }

                    leaf down-time {
                        type types-sros:time-interval;
                        description "Time interval elapsed since the session is in state 'Down'.";
                    }

                    leaf last-down-duration {
                        type types-sros:time-interval;
                        description "Time interval the session was in another state before it went 'Up'";
                    }

                    leaf last-up-duration {
                        type types-sros:time-interval;
                        description "Time interval the session was in state 'Up' before it left this state";
                    }

                    leaf received-messages {
                        type yang:counter32;
                        description "Number of messages received for the bfd session.";
                    }

                    leaf version-mismatch {
                        type yang:counter32;
                        description "Number of version mismatch errors for the bfd session.";
                    }

                    leaf last-received {
                        type yang:date-and-time;
                        description
                            "Time when the most recent message was received for the
                             bfd session that was not handled by the network processor.";
                    }

                    leaf time-since-np-receive {
                        type uint32;
                        units "milliseconds";
                        description
                            "Time elapsed since the most recent message was received
                             by the network processor for the BFD session. Zero is returned
                             if the session is Down.";
                    }

                    leaf sent-messages {
                        type yang:counter32;
                        description "Number of messages sent in this session.";
                    }

                    leaf last-sent {
                        type yang:date-and-time;
                        description
                            "Time when the most recent message was sent
                             (not including the ones transmitted by the network processor).";
                    }

                    leaf finals-sent {
                        type uint32;
                        description
                            "Number of protocol messages sent with the final
                             flag set.";
                    }

                    leaf time-since-np-sent {
                        type uint32;
                        units "milliseconds";
                        description
                            "Time elapsed since the most recent message was sent
                             by the network processor for the BFD session. Zero is returned
                             if the session is Down.";
                    }

                } // container statistics

                container local-parameters {
                    description "Enter the local-parameters context";

                    leaf discriminator {
                        type uint32;
                        description "Unique discriminator for this session.";
                    }

                    leaf state {
                        type types-bfd:session-state;
                        description "State of this session.";
                    }

                    leaf diag {
                        type enumeration {
                            enum detect-time-expired            { value 1; }
                            enum echo-func-failed               { value 2; }
                            enum neighbor-down                  { value 3; }
                            enum forwarding-plane-reset         { value 4; }
                            enum path-down                      { value 5; }
                            enum concatenated-path-down         { value 6; }
                            enum admin-down                     { value 7; }
                            enum reverse-concat-path-down       { value 8; }
                            enum mis-connectivity-defect        { value 9; }
                            enum admin-clear                    { value 39; }
                        }
                        description "Diagnostic value.";
                    }

                    leaf mode {
                        type enumeration {
                            enum async                          { value 0; }
                            enum demand                         { value 1; }
                        }
                        description "Mode.";
                    }

                    leaf tx-interval {
                        type uint32;
                        description "Minimal transmit interval.";
                    }

                    leaf multiplier {
                        type uint32;
                        description "Multiplier.";
                    }

                    leaf rx-interval {
                        type uint32;
                        description "Minimal receive interval.";
                    }

                } // container local-parameters

                container remote-parameters {
                    description "Enter the remote-parameters context";

                    leaf discriminator {
                        type uint32;
                        description "Unique discriminator for this session.";
                    }

                    leaf state {
                        type types-bfd:session-state;
                        description "State of this session.";
                    }

                    leaf diag {
                        type enumeration {
                            enum detect-time-expired            { value 1; }
                            enum echo-func-failed               { value 2; }
                            enum neighbor-down                  { value 3; }
                            enum forwarding-plane-reset         { value 4; }
                            enum path-down                      { value 5; }
                            enum concatenated-path-down         { value 6; }
                            enum admin-down                     { value 7; }
                            enum reverse-concat-path-down       { value 8; }
                            enum mis-connectivity-defect        { value 9; }
                            enum admin-clear                    { value 39; }
                        }
                        description "Diagnostic value.";
                    }

                    leaf mode {
                        type enumeration {
                            enum async                          { value 0; }
                            enum demand                         { value 1; }
                        }
                        description "Mode.";
                    }

                    leaf tx-interval {
                        type uint32;
                        description "Minimal transmit interval.";
                    }

                    leaf multiplier {
                        type uint32;
                        description "Multiplier.";
                    }

                    leaf rx-interval {
                        type uint32;
                        description "Minimal receive interval.";
                    }

                    leaf c-flag {
                        type boolean;
                        description "BFD is independent of the control plane.";
                    }

                } // container remote-parameters

            } // list cc-with-cv-session

            list micro-bfd-session {
                key "port-id router-instance interface-name address remote-address";
                description "Enter the micro-bfd-session list instance";

                leaf port-id {
                    type types-sros:port;
                    description "Port on which the BFD session is terminated.";
                }

                leaf router-instance {
                    type types-sros:router-instance;
                    description
                        "Administrative name for this virtual router. The router
                         name must be unique among all virtual routers in the system.";
                }

                leaf interface-name {
                    type types-sros:named-item;
                    description "Administrative name assigned to this router interface.";
                }

                leaf address {
                    type types-sros:ip-address-with-zone;
                    description "Address of the local endpoint of this BFD session.";
                }

                leaf remote-address {
                    type types-sros:ip-address-with-zone;
                    description "Address of the remote endpoint of this BFD session.";
                }

                container state {
                    description "Enter the state context";

                    leaf location {
                        type types-bfd:act-endpoint-type;
                        description "Location of the BFD session.";
                    }

                    leaf configured-location {
                        type types-bfd:cfg-endpoint-type;
                        description "Configured location of the BFD session.";
                    }

                    leaf oper-state {
                        type types-sros:oper-state;
                        description "Current operational state of this session.";
                    }

                    leaf protocols {
                        type types-bfd:protocols;
                        description "Protocols using this BFD session.";
                    }

                    leaf session-state {
                        type types-bfd:session-state;
                        description "State of the BFD protocol.";
                    }

                    leaf down-reasons {
                        type bits {
                            bit no-protocols                   { position 0; }
                            bit no-heart-beat                  { position 1; }
                            bit echo-failed                    { position 2; }
                            bit nbr-signal-down                { position 3; }
                            bit fwd-plane-reset                { position 4; }
                            bit path-down                      { position 5; }
                            bit nbr-admin-down                 { position 6; }
                            bit admin-clear                    { position 7; }
                            bit mis-conn-defect                { position 8; }
                        }
                        description "Reasons why a BFD session is not up.";
                    }

                    leaf transmit-interval {
                        type uint32;
                        units "milliseconds";
                        description "Negotiated transmit interval.";
                    }

                    leaf receive-interval {
                        type uint32;
                        units "milliseconds";
                        description "Negotiated receive interval.";
                    }

                    leaf multiplier {
                        type uint32;
                        units "milliseconds";
                        description "Negotiated multiplier.";
                    }

                    leaf lag-id {
                        type uint32;
                        description "Number of the lag on which this session is established.";
                    }

                    leaf lag-name {
                        type types-sros:lag-interface;
                        description "Name of the lag on which this session is established.";
                    }

                } // container state

                container statistics {
                    description "Enter the statistics context";

                    leaf up-count {
                        type yang:counter32;
                        description "Number of times the session-state changed to 'Up'.";
                    }

                    leaf down-count {
                        type yang:counter32;
                        description "Number of times the session-state changed to 'Down'.";
                    }

                    leaf up-time {
                        type types-sros:time-interval;
                        description "Time interval elapsed since the session is in state 'Up'.";
                    }

                    leaf down-time {
                        type types-sros:time-interval;
                        description "Time interval elapsed since the session is in state 'Down'.";
                    }

                    leaf last-down-duration {
                        type types-sros:time-interval;
                        description "Time interval the session was in another state before it went 'Up'";
                    }

                    leaf last-up-duration {
                        type types-sros:time-interval;
                        description "Time interval the session was in state 'Up' before it left this state";
                    }

                    leaf received-messages {
                        type yang:counter32;
                        description "Number of messages received for the bfd session.";
                    }

                    leaf version-mismatch {
                        type yang:counter32;
                        description "Number of version mismatch errors for the bfd session.";
                    }

                    leaf last-received {
                        type yang:date-and-time;
                        description
                            "Time when the most recent message was received for the
                             bfd session that was not handled by the network processor.";
                    }

                    leaf time-since-np-receive {
                        type uint32;
                        units "milliseconds";
                        description
                            "Time elapsed since the most recent message was received
                             by the network processor for the BFD session. Zero is returned
                             if the session is Down.";
                    }

                    leaf sent-messages {
                        type yang:counter32;
                        description "Number of messages sent in this session.";
                    }

                    leaf last-sent {
                        type yang:date-and-time;
                        description
                            "Time when the most recent message was sent
                             (not including the ones transmitted by the network processor).";
                    }

                    leaf finals-sent {
                        type uint32;
                        description
                            "Number of protocol messages sent with the final
                             flag set.";
                    }

                    leaf time-since-np-sent {
                        type uint32;
                        units "milliseconds";
                        description
                            "Time elapsed since the most recent message was sent
                             by the network processor for the BFD session. Zero is returned
                             if the session is Down.";
                    }

                } // container statistics

                container local-parameters {
                    description "Enter the local-parameters context";

                    leaf discriminator {
                        type uint32;
                        description "Unique discriminator for this session.";
                    }

                    leaf state {
                        type types-bfd:session-state;
                        description "State of this session.";
                    }

                    leaf diag {
                        type enumeration {
                            enum detect-time-expired            { value 1; }
                            enum echo-func-failed               { value 2; }
                            enum neighbor-down                  { value 3; }
                            enum forwarding-plane-reset         { value 4; }
                            enum path-down                      { value 5; }
                            enum concatenated-path-down         { value 6; }
                            enum admin-down                     { value 7; }
                            enum reverse-concat-path-down       { value 8; }
                            enum mis-connectivity-defect        { value 9; }
                            enum admin-clear                    { value 39; }
                        }
                        description "Diagnostic value.";
                    }

                    leaf mode {
                        type enumeration {
                            enum async                          { value 0; }
                            enum demand                         { value 1; }
                        }
                        description "Mode.";
                    }

                    leaf tx-interval {
                        type uint32;
                        description "Minimal transmit interval.";
                    }

                    leaf multiplier {
                        type uint32;
                        description "Multiplier.";
                    }

                    leaf rx-interval {
                        type uint32;
                        description "Minimal receive interval.";
                    }

                } // container local-parameters

                container remote-parameters {
                    description "Enter the remote-parameters context";

                    leaf discriminator {
                        type uint32;
                        description "Unique discriminator for this session.";
                    }

                    leaf state {
                        type types-bfd:session-state;
                        description "State of this session.";
                    }

                    leaf diag {
                        type enumeration {
                            enum detect-time-expired            { value 1; }
                            enum echo-func-failed               { value 2; }
                            enum neighbor-down                  { value 3; }
                            enum forwarding-plane-reset         { value 4; }
                            enum path-down                      { value 5; }
                            enum concatenated-path-down         { value 6; }
                            enum admin-down                     { value 7; }
                            enum reverse-concat-path-down       { value 8; }
                            enum mis-connectivity-defect        { value 9; }
                            enum admin-clear                    { value 39; }
                        }
                        description "Diagnostic value.";
                    }

                    leaf mode {
                        type enumeration {
                            enum async                          { value 0; }
                            enum demand                         { value 1; }
                        }
                        description "Mode.";
                    }

                    leaf tx-interval {
                        type uint32;
                        description "Minimal transmit interval.";
                    }

                    leaf multiplier {
                        type uint32;
                        description "Multiplier.";
                    }

                    leaf rx-interval {
                        type uint32;
                        description "Minimal receive interval.";
                    }

                    leaf c-flag {
                        type boolean;
                        description "BFD is independent of the control plane.";
                    }

                } // container remote-parameters

            } // list micro-bfd-session

            list pw-vccv-session {
                key "session-id router-instance interface-name address remote-address";
                description "Enter the pw-vccv-session list instance";

                leaf session-id {
                    type uint32;
                    description "VCCV BFD session identifier";
                }

                leaf router-instance {
                    type types-sros:router-instance;
                    description
                        "Administrative name for this virtual router. The router
                         name must be unique among all virtual routers in the system.";
                }

                leaf interface-name {
                    type types-sros:named-item;
                    description "Administrative name assigned to this router interface.";
                }

                leaf address {
                    type types-sros:ip-address-with-zone;
                    description "Address of the local endpoint of this BFD session.";
                }

                leaf remote-address {
                    type types-sros:ip-address-with-zone;
                    description "Address of the remote endpoint of this BFD session.";
                }

                container state {
                    description "Enter the state context";

                    leaf location {
                        type types-bfd:act-endpoint-type;
                        description "Location of the BFD session.";
                    }

                    leaf configured-location {
                        type types-bfd:cfg-endpoint-type;
                        description "Configured location of the BFD session.";
                    }

                    leaf oper-state {
                        type types-sros:oper-state;
                        description "Current operational state of this session.";
                    }

                    leaf protocols {
                        type types-bfd:protocols;
                        description "Protocols using this BFD session.";
                    }

                    leaf session-state {
                        type types-bfd:session-state;
                        description "State of the BFD protocol.";
                    }

                    leaf down-reasons {
                        type bits {
                            bit no-protocols                   { position 0; }
                            bit no-heart-beat                  { position 1; }
                            bit echo-failed                    { position 2; }
                            bit nbr-signal-down                { position 3; }
                            bit fwd-plane-reset                { position 4; }
                            bit path-down                      { position 5; }
                            bit nbr-admin-down                 { position 6; }
                            bit admin-clear                    { position 7; }
                            bit mis-conn-defect                { position 8; }
                        }
                        description "Reasons why a BFD session is not up.";
                    }

                    leaf transmit-interval {
                        type uint32;
                        units "milliseconds";
                        description "Negotiated transmit interval.";
                    }

                    leaf receive-interval {
                        type uint32;
                        units "milliseconds";
                        description "Negotiated receive interval.";
                    }

                    leaf multiplier {
                        type uint32;
                        units "milliseconds";
                        description "Negotiated multiplier.";
                    }

                    leaf svc-id {
                        type types-services:service-id;
                        description "Service-id associated with this BFD session.";
                    }

                    leaf sdp-bind-id {
                        type types-services:sdp-bind-id;
                        description "SDP Bind identifier associated with this BFD session.";
                    }

                } // container state

                container local-parameters {
                    description "Enter the local-parameters context";

                    leaf discriminator {
                        type uint32;
                        description "Unique discriminator for this session.";
                    }

                    leaf state {
                        type types-bfd:session-state;
                        description "State of this session.";
                    }

                    leaf diag {
                        type enumeration {
                            enum detect-time-expired            { value 1; }
                            enum echo-func-failed               { value 2; }
                            enum neighbor-down                  { value 3; }
                            enum forwarding-plane-reset         { value 4; }
                            enum path-down                      { value 5; }
                            enum concatenated-path-down         { value 6; }
                            enum admin-down                     { value 7; }
                            enum reverse-concat-path-down       { value 8; }
                            enum mis-connectivity-defect        { value 9; }
                            enum admin-clear                    { value 39; }
                        }
                        description "Diagnostic value.";
                    }

                    leaf mode {
                        type enumeration {
                            enum async                          { value 0; }
                            enum demand                         { value 1; }
                        }
                        description "Mode.";
                    }

                    leaf tx-interval {
                        type uint32;
                        description "Minimal transmit interval.";
                    }

                    leaf multiplier {
                        type uint32;
                        description "Multiplier.";
                    }

                    leaf rx-interval {
                        type uint32;
                        description "Minimal receive interval.";
                    }

                } // container local-parameters

                container remote-parameters {
                    description "Enter the remote-parameters context";

                    leaf discriminator {
                        type uint32;
                        description "Unique discriminator for this session.";
                    }

                    leaf state {
                        type types-bfd:session-state;
                        description "State of this session.";
                    }

                    leaf diag {
                        type enumeration {
                            enum detect-time-expired            { value 1; }
                            enum echo-func-failed               { value 2; }
                            enum neighbor-down                  { value 3; }
                            enum forwarding-plane-reset         { value 4; }
                            enum path-down                      { value 5; }
                            enum concatenated-path-down         { value 6; }
                            enum admin-down                     { value 7; }
                            enum reverse-concat-path-down       { value 8; }
                            enum mis-connectivity-defect        { value 9; }
                            enum admin-clear                    { value 39; }
                        }
                        description "Diagnostic value.";
                    }

                    leaf mode {
                        type enumeration {
                            enum async                          { value 0; }
                            enum demand                         { value 1; }
                        }
                        description "Mode.";
                    }

                    leaf tx-interval {
                        type uint32;
                        description "Minimal transmit interval.";
                    }

                    leaf multiplier {
                        type uint32;
                        description "Multiplier.";
                    }

                    leaf rx-interval {
                        type uint32;
                        description "Minimal receive interval.";
                    }

                    leaf c-flag {
                        type boolean;
                        description "BFD is independent of the control plane.";
                    }

                } // container remote-parameters

                container statistics {
                    description "Enter the statistics context";

                    leaf up-count {
                        type yang:counter32;
                        description "Number of times the session-state changed to 'Up'.";
                    }

                    leaf down-count {
                        type yang:counter32;
                        description "Number of times the session-state changed to 'Down'.";
                    }

                    leaf up-time {
                        type types-sros:time-interval;
                        description "Time interval elapsed since the session is in state 'Up'.";
                    }

                    leaf down-time {
                        type types-sros:time-interval;
                        description "Time interval elapsed since the session is in state 'Down'.";
                    }

                    leaf last-down-duration {
                        type types-sros:time-interval;
                        description "Time interval the session was in another state before it went 'Up'";
                    }

                    leaf last-up-duration {
                        type types-sros:time-interval;
                        description "Time interval the session was in state 'Up' before it left this state";
                    }

                    leaf received-messages {
                        type yang:counter32;
                        description "Number of messages received for the bfd session.";
                    }

                    leaf version-mismatch {
                        type yang:counter32;
                        description "Number of version mismatch errors for the bfd session.";
                    }

                    leaf last-received {
                        type yang:date-and-time;
                        description
                            "Time when the most recent message was received for the
                             bfd session that was not handled by the network processor.";
                    }

                    leaf time-since-np-receive {
                        type uint32;
                        units "milliseconds";
                        description
                            "Time elapsed since the most recent message was received
                             by the network processor for the BFD session. Zero is returned
                             if the session is Down.";
                    }

                    leaf sent-messages {
                        type yang:counter32;
                        description "Number of messages sent in this session.";
                    }

                    leaf last-sent {
                        type yang:date-and-time;
                        description
                            "Time when the most recent message was sent
                             (not including the ones transmitted by the network processor).";
                    }

                    leaf finals-sent {
                        type uint32;
                        description
                            "Number of protocol messages sent with the final
                             flag set.";
                    }

                    leaf time-since-np-sent {
                        type uint32;
                        units "milliseconds";
                        description
                            "Time elapsed since the most recent message was sent
                             by the network processor for the BFD session. Zero is returned
                             if the session is Down.";
                    }

                } // container statistics

            } // list pw-vccv-session

            container seamless-bfd {
                description "Enter the seamless-bfd context";


                list lsp-path-session {
                    key "router-instance session-fec-type remote-address address path-id lsp";
                    description "Enter the lsp-path-session list instance";

                    leaf router-instance {
                        type types-sros:router-instance;
                        description
                            "The administrative name for this virtual router. The router
                             name must be unique among all virtual routers in the system.";
                    }

                    leaf session-fec-type {
                        type types-bfd:fec-type;
                        description "Fec type of this BFD session.";
                    }

                    leaf remote-address {
                        type types-sros:ip-address-with-zone;
                        description "Address of the remote endpoint of this BFD session.";
                    }

                    leaf address {
                        type types-sros:ip-address-with-zone;
                        description "Address of the local endpoint of this BFD session.";
                    }

                    leaf path-id {
                        type uint32;
                        description "Path id";
                    }

                    leaf lsp {
                        type types-sros:named-item-64-or-empty;
                        description "LSP";
                    }

                    leaf session-name {
                        type string {
                            length "1..160";
                        }
                        description "Session name";
                    }

                    container state {
                        description "Enter the state context";

                        leaf return-path {
                            type uint32 {
                                range "32..1048575|4294967295";
                            }
                            description "The label of the return path.";
                        }

                        leaf location {
                            type types-bfd:act-endpoint-type;
                            description "Location of the BFD session.";
                        }

                        leaf configured-location {
                            type types-bfd:cfg-endpoint-type;
                            description "Configured location of the BFD session.";
                        }

                        leaf oper-state {
                            type types-sros:oper-state;
                            description "Current operational state of this session.";
                        }

                        leaf protocols {
                            type types-bfd:protocols;
                            description "Protocols using this BFD session.";
                        }

                        leaf session-state {
                            type types-bfd:session-state;
                            description "State of the BFD protocol.";
                        }

                        leaf down-reasons {
                            type bits {
                                bit no-protocols                   { position 0; }
                                bit no-heart-beat                  { position 1; }
                                bit echo-failed                    { position 2; }
                                bit nbr-signal-down                { position 3; }
                                bit fwd-plane-reset                { position 4; }
                                bit path-down                      { position 5; }
                                bit nbr-admin-down                 { position 6; }
                                bit admin-clear                    { position 7; }
                                bit mis-conn-defect                { position 8; }
                            }
                            description "Reasons why a BFD session is not up.";
                        }

                        leaf transmit-interval {
                            type uint32;
                            units "milliseconds";
                            description "Negotiated transmit interval.";
                        }

                        leaf receive-interval {
                            type uint32;
                            units "milliseconds";
                            description "Negotiated receive interval.";
                        }

                        leaf multiplier {
                            type uint32;
                            units "milliseconds";
                            description "Negotiated multiplier.";
                        }

                    } // container state

                    container local-parameters {
                        description "Enter the local-parameters context";

                        leaf discriminator {
                            type uint32;
                            description "Unique discriminator for this session.";
                        }

                        leaf state {
                            type types-bfd:session-state;
                            description "State of this session.";
                        }

                        leaf diag {
                            type enumeration {
                                enum detect-time-expired            { value 1; }
                                enum echo-func-failed               { value 2; }
                                enum neighbor-down                  { value 3; }
                                enum forwarding-plane-reset         { value 4; }
                                enum path-down                      { value 5; }
                                enum concatenated-path-down         { value 6; }
                                enum admin-down                     { value 7; }
                                enum reverse-concat-path-down       { value 8; }
                                enum mis-connectivity-defect        { value 9; }
                                enum admin-clear                    { value 39; }
                            }
                            description "Diagnostic value.";
                        }

                        leaf mode {
                            type enumeration {
                                enum async                          { value 0; }
                                enum demand                         { value 1; }
                            }
                            description "Mode.";
                        }

                        leaf tx-interval {
                            type uint32;
                            description "Minimal transmit interval.";
                        }

                        leaf multiplier {
                            type uint32;
                            description "Multiplier.";
                        }

                        leaf rx-interval {
                            type uint32;
                            description "Minimal receive interval.";
                        }

                    } // container local-parameters

                    container remote-parameters {
                        description "Enter the remote-parameters context";

                        leaf discriminator {
                            type uint32;
                            description "Unique discriminator for this session.";
                        }

                        leaf state {
                            type types-bfd:session-state;
                            description "State of this session.";
                        }

                        leaf diag {
                            type enumeration {
                                enum detect-time-expired            { value 1; }
                                enum echo-func-failed               { value 2; }
                                enum neighbor-down                  { value 3; }
                                enum forwarding-plane-reset         { value 4; }
                                enum path-down                      { value 5; }
                                enum concatenated-path-down         { value 6; }
                                enum admin-down                     { value 7; }
                                enum reverse-concat-path-down       { value 8; }
                                enum mis-connectivity-defect        { value 9; }
                                enum admin-clear                    { value 39; }
                            }
                            description "Diagnostic value.";
                        }

                        leaf mode {
                            type enumeration {
                                enum async                          { value 0; }
                                enum demand                         { value 1; }
                            }
                            description "Mode.";
                        }

                        leaf tx-interval {
                            type uint32;
                            description "Minimal transmit interval.";
                        }

                        leaf multiplier {
                            type uint32;
                            description "Multiplier.";
                        }

                        leaf rx-interval {
                            type uint32;
                            description "Minimal receive interval.";
                        }

                        leaf c-flag {
                            type boolean;
                            description "BFD is independent of the control plane.";
                        }

                    } // container remote-parameters

                    container statistics {
                        description "Enter the statistics context";

                        leaf up-count {
                            type yang:counter32;
                            description "Number of times the session-state changed to 'Up'.";
                        }

                        leaf down-count {
                            type yang:counter32;
                            description "Number of times the session-state changed to 'Down'.";
                        }

                        leaf up-time {
                            type types-sros:time-interval;
                            description "Time interval elapsed since the session is in state 'Up'.";
                        }

                        leaf down-time {
                            type types-sros:time-interval;
                            description "Time interval elapsed since the session is in state 'Down'.";
                        }

                        leaf last-down-duration {
                            type types-sros:time-interval;
                            description "Time interval the session was in another state before it went 'Up'";
                        }

                        leaf last-up-duration {
                            type types-sros:time-interval;
                            description "Time interval the session was in state 'Up' before it left this state";
                        }

                        leaf received-messages {
                            type yang:counter32;
                            description "Number of messages received for the bfd session.";
                        }

                        leaf version-mismatch {
                            type yang:counter32;
                            description "Number of version mismatch errors for the bfd session.";
                        }

                        leaf last-received {
                            type yang:date-and-time;
                            description
                                "Time when the most recent message was received for the
                                 bfd session that was not handled by the network processor.";
                        }

                        leaf time-since-np-receive {
                            type uint32;
                            units "milliseconds";
                            description
                                "Time elapsed since the most recent message was received
                                 by the network processor for the BFD session. Zero is returned
                                 if the session is Down.";
                        }

                        leaf sent-messages {
                            type yang:counter32;
                            description "Number of messages sent in this session.";
                        }

                        leaf last-sent {
                            type yang:date-and-time;
                            description
                                "Time when the most recent message was sent
                                 (not including the ones transmitted by the network processor).";
                        }

                        leaf finals-sent {
                            type uint32;
                            description
                                "Number of protocol messages sent with the final
                                 flag set.";
                        }

                        leaf time-since-np-sent {
                            type uint32;
                            units "milliseconds";
                            description
                                "Time elapsed since the most recent message was sent
                                 by the network processor for the BFD session. Zero is returned
                                 if the session is Down.";
                        }

                    } // container statistics

                } // list lsp-path-session

                list sr-policy-session {
                    key "router-instance session-fec-type remote-address address path-id tunnel-id hop";
                    description "Enter the sr-policy-session list instance";

                    leaf router-instance {
                        type types-sros:router-instance;
                        description
                            "The administrative name for this virtual router. The router
                             name must be unique among all virtual routers in the system.";
                    }

                    leaf session-fec-type {
                        type types-bfd:fec-type;
                        description "Fec type of this BFD session.";
                    }

                    leaf remote-address {
                        type types-sros:ip-address-with-zone;
                        description "Address of the remote endpoint of this BFD session.";
                    }

                    leaf address {
                        type types-sros:ip-address-with-zone;
                        description "Address of the local endpoint of this BFD session.";
                    }

                    leaf path-id {
                        type uint32;
                        description "Path id";
                    }

                    leaf tunnel-id {
                        type uint32;
                        description "tunnel id";
                    }

                    leaf hop {
                        type uint32;
                        description "Hop id";
                    }

                    leaf session-name {
                        type string {
                            length "1..160";
                        }
                        description "Session name";
                    }

                    container state {
                        description "Enter the state context";

                        leaf return-path {
                            type uint32 {
                                range "32..1048575|4294967295";
                            }
                            description "The label of the return path.";
                        }

                        leaf location {
                            type types-bfd:act-endpoint-type;
                            description "Location of the BFD session.";
                        }

                        leaf configured-location {
                            type types-bfd:cfg-endpoint-type;
                            description "Configured location of the BFD session.";
                        }

                        leaf oper-state {
                            type types-sros:oper-state;
                            description "Current operational state of this session.";
                        }

                        leaf protocols {
                            type types-bfd:protocols;
                            description "Protocols using this BFD session.";
                        }

                        leaf session-state {
                            type types-bfd:session-state;
                            description "State of the BFD protocol.";
                        }

                        leaf down-reasons {
                            type bits {
                                bit no-protocols                   { position 0; }
                                bit no-heart-beat                  { position 1; }
                                bit echo-failed                    { position 2; }
                                bit nbr-signal-down                { position 3; }
                                bit fwd-plane-reset                { position 4; }
                                bit path-down                      { position 5; }
                                bit nbr-admin-down                 { position 6; }
                                bit admin-clear                    { position 7; }
                                bit mis-conn-defect                { position 8; }
                            }
                            description "Reasons why a BFD session is not up.";
                        }

                        leaf transmit-interval {
                            type uint32;
                            units "milliseconds";
                            description "Negotiated transmit interval.";
                        }

                        leaf receive-interval {
                            type uint32;
                            units "milliseconds";
                            description "Negotiated receive interval.";
                        }

                        leaf multiplier {
                            type uint32;
                            units "milliseconds";
                            description "Negotiated multiplier.";
                        }

                    } // container state

                    container local-parameters {
                        description "Enter the local-parameters context";

                        leaf discriminator {
                            type uint32;
                            description "Unique discriminator for this session.";
                        }

                        leaf state {
                            type types-bfd:session-state;
                            description "State of this session.";
                        }

                        leaf diag {
                            type enumeration {
                                enum detect-time-expired            { value 1; }
                                enum echo-func-failed               { value 2; }
                                enum neighbor-down                  { value 3; }
                                enum forwarding-plane-reset         { value 4; }
                                enum path-down                      { value 5; }
                                enum concatenated-path-down         { value 6; }
                                enum admin-down                     { value 7; }
                                enum reverse-concat-path-down       { value 8; }
                                enum mis-connectivity-defect        { value 9; }
                                enum admin-clear                    { value 39; }
                            }
                            description "Diagnostic value.";
                        }

                        leaf mode {
                            type enumeration {
                                enum async                          { value 0; }
                                enum demand                         { value 1; }
                            }
                            description "Mode.";
                        }

                        leaf tx-interval {
                            type uint32;
                            description "Minimal transmit interval.";
                        }

                        leaf multiplier {
                            type uint32;
                            description "Multiplier.";
                        }

                        leaf rx-interval {
                            type uint32;
                            description "Minimal receive interval.";
                        }

                    } // container local-parameters

                    container remote-parameters {
                        description "Enter the remote-parameters context";

                        leaf discriminator {
                            type uint32;
                            description "Unique discriminator for this session.";
                        }

                        leaf state {
                            type types-bfd:session-state;
                            description "State of this session.";
                        }

                        leaf diag {
                            type enumeration {
                                enum detect-time-expired            { value 1; }
                                enum echo-func-failed               { value 2; }
                                enum neighbor-down                  { value 3; }
                                enum forwarding-plane-reset         { value 4; }
                                enum path-down                      { value 5; }
                                enum concatenated-path-down         { value 6; }
                                enum admin-down                     { value 7; }
                                enum reverse-concat-path-down       { value 8; }
                                enum mis-connectivity-defect        { value 9; }
                                enum admin-clear                    { value 39; }
                            }
                            description "Diagnostic value.";
                        }

                        leaf mode {
                            type enumeration {
                                enum async                          { value 0; }
                                enum demand                         { value 1; }
                            }
                            description "Mode.";
                        }

                        leaf tx-interval {
                            type uint32;
                            description "Minimal transmit interval.";
                        }

                        leaf multiplier {
                            type uint32;
                            description "Multiplier.";
                        }

                        leaf rx-interval {
                            type uint32;
                            description "Minimal receive interval.";
                        }

                        leaf c-flag {
                            type boolean;
                            description "BFD is independent of the control plane.";
                        }

                    } // container remote-parameters

                    container statistics {
                        description "Enter the statistics context";

                        leaf up-count {
                            type yang:counter32;
                            description "Number of times the session-state changed to 'Up'.";
                        }

                        leaf down-count {
                            type yang:counter32;
                            description "Number of times the session-state changed to 'Down'.";
                        }

                        leaf up-time {
                            type types-sros:time-interval;
                            description "Time interval elapsed since the session is in state 'Up'.";
                        }

                        leaf down-time {
                            type types-sros:time-interval;
                            description "Time interval elapsed since the session is in state 'Down'.";
                        }

                        leaf last-down-duration {
                            type types-sros:time-interval;
                            description "Time interval the session was in another state before it went 'Up'";
                        }

                        leaf last-up-duration {
                            type types-sros:time-interval;
                            description "Time interval the session was in state 'Up' before it left this state";
                        }

                        leaf received-messages {
                            type yang:counter32;
                            description "Number of messages received for the bfd session.";
                        }

                        leaf version-mismatch {
                            type yang:counter32;
                            description "Number of version mismatch errors for the bfd session.";
                        }

                        leaf last-received {
                            type yang:date-and-time;
                            description
                                "Time when the most recent message was received for the
                                 bfd session that was not handled by the network processor.";
                        }

                        leaf time-since-np-receive {
                            type uint32;
                            units "milliseconds";
                            description
                                "Time elapsed since the most recent message was received
                                 by the network processor for the BFD session. Zero is returned
                                 if the session is Down.";
                        }

                        leaf sent-messages {
                            type yang:counter32;
                            description "Number of messages sent in this session.";
                        }

                        leaf last-sent {
                            type yang:date-and-time;
                            description
                                "Time when the most recent message was sent
                                 (not including the ones transmitted by the network processor).";
                        }

                        leaf finals-sent {
                            type uint32;
                            description
                                "Number of protocol messages sent with the final
                                 flag set.";
                        }

                        leaf time-since-np-sent {
                            type uint32;
                            units "milliseconds";
                            description
                                "Time elapsed since the most recent message was sent
                                 by the network processor for the BFD session. Zero is returned
                                 if the session is Down.";
                        }

                    } // container statistics

                } // list sr-policy-session

            } // container seamless-bfd

            container resources {
                description "Enter the resources context";

                list card {
                    key "slot-number";
                    description "Enter the card list instance";

                    leaf slot-number {
                        type types-card:iom-card-slot;
                        description "The unique value which identifies this IOM slot within a chassis in the system.";
                    }

                    container sessions {
                        description "Enter the sessions context";

                        leaf maximum {
                            type uint32;
                            description "The maximum number of sessions that can be assigned to this group";
                        }

                        leaf available {
                            type uint32;
                            description "The number of sessions that can still be assigned to this group";
                        }

                    } // container sessions

                    container transmit-capacity {
                        description "Enter the transmit-capacity context";

                        leaf maximum {
                            type uint32;
                            units "packets per second";
                            description "The maximum transmit capacity that can be assisgned to this group";
                        }

                        leaf available {
                            type uint32;
                            units "packets per second";
                            description "The transmit capacity that can still be assigned to this group";
                        }

                    } // container transmit-capacity

                    container receive-capacity {
                        description "Enter the receive-capacity context";

                        leaf maximum {
                            type uint32;
                            units "packets per second";
                            description "The maximum receive capacity that can be assisgned to this group";
                        }

                        leaf available {
                            type uint32;
                            units "packets per second";
                            description "The receive capacity that can still be assigned to this group";
                        }

                    } // container receive-capacity

                    container table-entries {
                        description "Enter the table-entries context";

                        leaf maximum {
                            type uint32;
                            description "The maximum table entries that can be assisgned to this group";
                        }

                        leaf available {
                            type uint32;
                            description "The table entries that can still be assigned to this group";
                        }

                    } // container table-entries

                } // list card

                container central {
                    description "Enter the central context";

                    container sessions {
                        description "Enter the sessions context";

                        leaf maximum {
                            type uint32;
                            description "The maximum number of sessions that can be assigned to this group";
                        }

                        leaf available {
                            type uint32;
                            description "The number of sessions that can still be assigned to this group";
                        }

                    } // container sessions

                    container transmit-capacity {
                        description "Enter the transmit-capacity context";

                        leaf maximum {
                            type uint32;
                            units "packets per second";
                            description "The maximum transmit capacity that can be assisgned to this group";
                        }

                        leaf available {
                            type uint32;
                            units "packets per second";
                            description "The transmit capacity that can still be assigned to this group";
                        }

                    } // container transmit-capacity

                    container receive-capacity {
                        description "Enter the receive-capacity context";

                        leaf maximum {
                            type uint32;
                            units "packets per second";
                            description "The maximum receive capacity that can be assisgned to this group";
                        }

                        leaf available {
                            type uint32;
                            units "packets per second";
                            description "The receive capacity that can still be assigned to this group";
                        }

                    } // container receive-capacity

                    container table-entries {
                        description "Enter the table-entries context";

                        leaf maximum {
                            type uint32;
                            description "The maximum table entries that can be assisgned to this group";
                        }

                        leaf available {
                            type uint32;
                            description "The table entries that can still be assigned to this group";
                        }

                    } // container table-entries

                } // container central

                container cpm {
                    description "Enter the cpm context";

                    container sessions {
                        description "Enter the sessions context";

                        leaf maximum {
                            type uint32;
                            description "The maximum number of sessions that can be assigned to this group";
                        }

                        leaf available {
                            type uint32;
                            description "The number of sessions that can still be assigned to this group";
                        }

                    } // container sessions

                } // container cpm

                container cpm-np {
                    description "Enter the cpm-np context";

                    container sessions {
                        description "Enter the sessions context";

                        leaf maximum {
                            type uint32;
                            description "The maximum number of sessions that can be assigned to this group";
                        }

                        leaf available {
                            type uint32;
                            description "The number of sessions that can still be assigned to this group";
                        }

                    } // container sessions

                    container transmit-capacity {
                        description "Enter the transmit-capacity context";

                        leaf maximum {
                            type uint32;
                            units "packets per second";
                            description "The maximum transmit capacity that can be assisgned to this group";
                        }

                        leaf available {
                            type uint32;
                            units "packets per second";
                            description "The transmit capacity that can still be assigned to this group";
                        }

                    } // container transmit-capacity

                    container receive-capacity {
                        description "Enter the receive-capacity context";

                        leaf maximum {
                            type uint32;
                            units "packets per second";
                            description "The maximum receive capacity that can be assisgned to this group";
                        }

                        leaf available {
                            type uint32;
                            units "packets per second";
                            description "The receive capacity that can still be assigned to this group";
                        }

                    } // container receive-capacity

                    container table-entries {
                        description "Enter the table-entries context";

                        leaf maximum {
                            type uint32;
                            description "The maximum table entries that can be assisgned to this group";
                        }

                        leaf available {
                            type uint32;
                            description "The table entries that can still be assigned to this group";
                        }

                    } // container table-entries

                } // container cpm-np

                container ipv4-fp {
                    description "Enter the ipv4-fp context";

                    container sessions {
                        description "Enter the sessions context";

                        leaf maximum {
                            type uint32;
                            description "The maximum number of sessions that can be assigned to this group";
                        }

                        leaf available {
                            type uint32;
                            description "The number of sessions that can still be assigned to this group";
                        }

                    } // container sessions

                    container transmit-capacity {
                        description "Enter the transmit-capacity context";

                        leaf maximum {
                            type uint32;
                            units "packets per second";
                            description "The maximum transmit capacity that can be assisgned to this group";
                        }

                        leaf available {
                            type uint32;
                            units "packets per second";
                            description "The transmit capacity that can still be assigned to this group";
                        }

                    } // container transmit-capacity

                    container receive-capacity {
                        description "Enter the receive-capacity context";

                        leaf maximum {
                            type uint32;
                            units "packets per second";
                            description "The maximum receive capacity that can be assisgned to this group";
                        }

                        leaf available {
                            type uint32;
                            units "packets per second";
                            description "The receive capacity that can still be assigned to this group";
                        }

                    } // container receive-capacity

                    container table-entries {
                        description "Enter the table-entries context";

                        leaf maximum {
                            type uint32;
                            description "The maximum table entries that can be assisgned to this group";
                        }

                        leaf available {
                            type uint32;
                            description "The table entries that can still be assigned to this group";
                        }

                    } // container table-entries

                } // container ipv4-fp

                container ipv6-fp {
                    description "Enter the ipv6-fp context";

                    container sessions {
                        description "Enter the sessions context";

                        leaf maximum {
                            type uint32;
                            description "The maximum number of sessions that can be assigned to this group";
                        }

                        leaf available {
                            type uint32;
                            description "The number of sessions that can still be assigned to this group";
                        }

                    } // container sessions

                    container transmit-capacity {
                        description "Enter the transmit-capacity context";

                        leaf maximum {
                            type uint32;
                            units "packets per second";
                            description "The maximum transmit capacity that can be assisgned to this group";
                        }

                        leaf available {
                            type uint32;
                            units "packets per second";
                            description "The transmit capacity that can still be assigned to this group";
                        }

                    } // container transmit-capacity

                    container receive-capacity {
                        description "Enter the receive-capacity context";

                        leaf maximum {
                            type uint32;
                            units "packets per second";
                            description "The maximum receive capacity that can be assisgned to this group";
                        }

                        leaf available {
                            type uint32;
                            units "packets per second";
                            description "The receive capacity that can still be assigned to this group";
                        }

                    } // container receive-capacity

                    container table-entries {
                        description "Enter the table-entries context";

                        leaf maximum {
                            type uint32;
                            description "The maximum table entries that can be assisgned to this group";
                        }

                        leaf available {
                            type uint32;
                            description "The table entries that can still be assigned to this group";
                        }

                    } // container table-entries

                } // container ipv6-fp

                container fp {
                    description "Enter the fp context";

                    container sessions {
                        description "Enter the sessions context";

                        leaf maximum {
                            type uint32;
                            description "The maximum number of sessions that can be assigned to this group";
                        }

                        leaf available {
                            type uint32;
                            description "The number of sessions that can still be assigned to this group";
                        }

                    } // container sessions

                    container transmit-capacity {
                        description "Enter the transmit-capacity context";

                        leaf maximum {
                            type uint32;
                            units "packets per second";
                            description "The maximum transmit capacity that can be assisgned to this group";
                        }

                        leaf available {
                            type uint32;
                            units "packets per second";
                            description "The transmit capacity that can still be assigned to this group";
                        }

                    } // container transmit-capacity

                    container receive-capacity {
                        description "Enter the receive-capacity context";

                        leaf maximum {
                            type uint32;
                            units "packets per second";
                            description "The maximum receive capacity that can be assisgned to this group";
                        }

                        leaf available {
                            type uint32;
                            units "packets per second";
                            description "The receive capacity that can still be assigned to this group";
                        }

                    } // container receive-capacity

                    container table-entries {
                        description "Enter the table-entries context";

                        leaf maximum {
                            type uint32;
                            description "The maximum table entries that can be assisgned to this group";
                        }

                        leaf available {
                            type uint32;
                            description "The table entries that can still be assigned to this group";
                        }

                    } // container table-entries

                } // container fp

            } // container resources

        } // container bfd

    } // grouping state-bfd

}
