submodule nokia-state-group-encryption {

    yang-version "1.1";

    belongs-to nokia-state { prefix "state"; }

    import ietf-yang-types                { prefix "yang"; }
    import nokia-sros-yang-extensions     { prefix "sros-ext"; }
    import nokia-types-sros               { prefix "types-sros"; }

    sros-ext:sros-major-release "rel24";
    organization "Nokia";
    contact
        "Nokia SR OS Support
         Web: <http://www.nokia.com>";
    description
        "Nokia YANG Data model with operational state for Group encryption on SR OS based routers.

         Copyright 2016 Nokia. All rights reserved. Reproduction of this document
         is authorized on the condition that the foregoing copyright notice is included.

         This nokia-state-group-encryption YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";
    revision "2022-09-08";

    grouping state-group-encryption {
        container group-encryption {
            description "Enter the group-encryption context";

            list encryption-keygroup {
                key "id";
                description "Enter the encryption-keygroup list instance";

                leaf id {
                    type uint32 {
                        range "1..127";
                    }
                    description "Identification of the encryption keygroup";
                }

                leaf outbound-security-association-activation-time {
                    type yang:date-and-time;
                    description "Outbound security association activation time";
                }

                leaf encrypted-packets {
                    type uint64;
                    description "Number of encrypted packets";
                }

                leaf encrypted-bytes {
                    type uint64;
                    description "Number of encrypted bytes";
                }

                leaf decrypted-packets {
                    type uint64;
                    description "Number of decrypted packets";
                }

                leaf decrypted-bytes {
                    type uint64;
                    description "Number of decrypted bytes";
                }

                container outbound-dropped-packets {
                    description "Enter the outbound-dropped-packets context";

                    leaf total {
                        type uint32;
                        description
                            "Total number of packets dropped before and during outbound (encryption)
                             processing by the group encryption keygroup.";
                    }

                    leaf unsupported-uplink {
                        type uint32;
                        description
                            "Number of packets dropped before and during outbound (encryption)
                             processing by the group encryption keygroup. This implies that
                             the resolved uplink does not support encryption.";
                    }

                    leaf enqueue-error {
                        type uint32;
                        description
                            "Number of packets dropped before and during outbound (encryption)
                             processing by the group encryption keygroup. This implies that
                             there are enqueue errors in the encryption engine.";
                    }

                    leaf other {
                        type uint32;
                        description
                            "Number of packets dropped before and during outbound (encryption)
                             processing by the group encryption keygroup for unspecified reasons.";
                    }

                } // container outbound-dropped-packets

                container inbound-dropped-packets {
                    description "Enter the inbound-dropped-packets context";

                    leaf total {
                        type uint32;
                        description
                            "Total number of packets dropped before and during inbound (decryption)
                             processing by the group encryption keygroup.";
                    }

                    leaf invalid-spi {
                        type uint32;
                        description
                            "Number of packets dropped before and during inbound (decryption)
                             processing by the group encryption keygroup. This implies that
                             1) the received SPI does not exist within the system
                             2) the received SPI is not part of the associated inbound keygroup
                             3) un-encrypted packet has been received on SDP with an associated inbound keygroup";
                    }

                    leaf authentication-failure {
                        type uint32;
                        description
                            "Number of packets dropped before and during inbound (decryption)
                             processing by the group encryption keygroup. This implies that
                             authentication failed on the received packets.";
                    }

                    leaf padding-failure {
                        type uint32;
                        description
                            "Number of packets dropped before and during inbound (decryption)
                             processing by the group encryption keygroup. This implies that
                             there are padding errors detected on the received packets.";
                    }

                    leaf enqueue-error {
                        type uint32;
                        description
                            "Number of packets dropped before and during inbound (decryption)
                             processing by the group encryption keygroup. This implies that
                             there are enqueue errors in the encryption engine.";
                    }

                    leaf control-word-mismatch {
                        type uint32;
                        description
                            "Number of packets dropped before and during inbound (decryption)
                             processing by the group encryption keygroup. This implies that
                             the decrypted control word does not match the outer control word.";
                    }

                    leaf other {
                        type uint32;
                        description
                            "Number of packets dropped before and during inbound (decryption)
                             processing by the group encryption keygroup for unspecifed reasons.";
                    }

                    leaf last-dropped-spi {
                        type uint32;
                        description
                            "The last SPI value of the packet dropped before and during
                             inbound (decryption) processing by the group encryption keygroup.

                             If 0x00000000 is received, it implies that no discard involving SPIs
                             has occured.

                             If 0xFFFFFFFF is received, it implies that discards occured involving
                             unencrypted traffic without encryption label.

                             Any other values should be interpreted as a normal SPI ID.";
                    }

                } // container inbound-dropped-packets

                list security-association {
                    key "security-parameter-index";
                    description "Enter the security-association list instance";

                    leaf security-parameter-index {
                        type uint32 {
                            range "1..1023";
                        }
                        description "Security Parameter Index";
                    }

                    leaf install-time {
                        type yang:date-and-time;
                        description "The sysUpTime at the time the security association is installed.";
                    }

                    leaf key-crc {
                        type types-sros:hex-string {
                            length "10";
                        }
                        description
                            "Result of the CRC calculation based on the configured
                             security association key.";
                    }

                    leaf encrypted-packets {
                        type uint64;
                        description "Number of encrypted packets";
                    }

                    leaf encrypted-bytes {
                        type uint64;
                        description "Number of encrypted bytes";
                    }

                    leaf decrypted-packets {
                        type uint64;
                        description "Number of decrypted packets";
                    }

                    leaf decrypted-bytes {
                        type uint64;
                        description "Number of decrypted bytes";
                    }

                    container outbound-dropped-packets {
                        description "Enter the outbound-dropped-packets context";

                        leaf total {
                            type uint32;
                            description
                                "Total number of packets dropped before and during outbound (encryption)
                                 processing by the group encryption keygroup SPI.";
                        }

                        leaf enqueue-error {
                            type uint32;
                            description
                                "Number of packets dropped before and during outbound (encryption)
                                 processing by the group encryption keygroup SPI. This implies that
                                 there are enqueue errors in the encryption engine.";
                        }

                        leaf other {
                            type uint32;
                            description
                                "Number of packets dropped before and during outbound (encryption)
                                 processing by the group encryption keygroup SPI for unspecified reasons.";
                        }

                    } // container outbound-dropped-packets

                    container inbound-dropped-packets {
                        description "Enter the inbound-dropped-packets context";

                        leaf total {
                            type uint32;
                            description
                                "Total number of packets dropped before and during inbound (decryption)
                                 processing by the group encryption keygroup SPI.";
                        }

                        leaf authentication-failure {
                            type uint32;
                            description
                                "Number of packets dropped before and during inbound (decryption)
                                 processing by the group encryption keygroup SPI. This implies that
                                 authentication failed on the received packets.";
                        }

                        leaf padding-failure {
                            type uint32;
                            description
                                "Number of packets dropped before and during inbound (decryption)
                                 processing by the group encryption keygroup SPI. This implies that
                                 there are padding errors detected on the received packets.";
                        }

                        leaf enqueue-error {
                            type uint32;
                            description
                                "Number of packets dropped before and during inbound (decryption)
                                 processing by the group encryption keygroup SPI. This implies that
                                 there are enqueue errors in the encryption engine.";
                        }

                        leaf control-word-mismatch {
                            type uint32;
                            description
                                "Number of packets dropped before and during inbound (decryption)
                                 processing by the group encryption keygroup SPI. This implies that
                                 the decrypted control word does not match the outer control word.";
                        }

                        leaf other {
                            type uint32;
                            description
                                "Number of packets dropped before and during inbound (decryption)
                                 processing by the group encryption keygroup SPI for unspecifed reasons.";
                        }

                    } // container inbound-dropped-packets

                } // list security-association

            } // list encryption-keygroup

        } // container group-encryption

    } // grouping state-group-encryption

}
