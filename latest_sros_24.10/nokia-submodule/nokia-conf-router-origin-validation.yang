submodule nokia-conf-router-origin-validation {

    yang-version "1.1";

    belongs-to nokia-conf { prefix "conf"; }

    import ietf-inet-types                { prefix "inet"; }
    import nokia-sros-yang-extensions     { prefix "sros-ext"; }
    import nokia-types-sros               { prefix "types-sros"; }

    include nokia-conf-groups;

    sros-ext:sros-major-release "rel24";
    organization "Nokia";
    contact
        "Nokia SR OS Support
         Web: <http://www.nokia.com>";
    description
        "Nokia YANG Data model to configure origin-validation on SR OS based routers.

         Copyright 2016 Nokia. All rights reserved. Reproduction of this document
         is authorized on the condition that the foregoing copyright notice is included.

         This nokia-conf-router-origin-validation YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";
    revision "2021-12-06";

    grouping conf-router-origin-validation {
        container origin-validation {
            when "../router-name = 'Base' or ../router-name = 'management'" {
                description "not allowed in a CPM router instance";
            }
            description "Enter the origin-validation context";

            leaf-list apply-groups {
                type leafref {
                    path "../../../groups/group/name";
                }
                max-elements 8;
                ordered-by user;
                description "Apply a configuration group at this level";
            }

            leaf-list apply-groups-exclude {
                type leafref {
                    path "../../../groups/group/name";
                }
                max-elements 8;
                ordered-by user;
                description "Exclude a configuration group at this level";
            }

            list static-entry {
                key "ip-prefix upto origin-as";
                description "Enter the static-entry list instance";

                leaf ip-prefix {
                    type types-sros:ip-unicast-prefix;
                    description "IPv4 or IPv6 address with the minimum prefix and length";
                }

                leaf upto {
                    type uint32 {
                        range "1..128";
                    }
                    description "Maximum prefix length";
                }

                leaf origin-as {
                    type inet:as-number;
                    description "Origin AS number";
                }

                leaf valid {
                    type boolean;
                    default "true";
                    description "Designate mix of origin AS and prefix range as valid";
                }

                leaf-list apply-groups {
                    type leafref {
                        path "../../../../groups/group/name";
                    }
                    max-elements 8;
                    ordered-by user;
                    description "Apply a configuration group at this level";
                }

                leaf-list apply-groups-exclude {
                    type leafref {
                        path "../../../../groups/group/name";
                    }
                    max-elements 8;
                    ordered-by user;
                    description "Exclude a configuration group at this level";
                }

            } // list static-entry

            list rpki-session {
                key "ip-address";
                description "Enter the rpki-session list instance";

                leaf ip-address {
                    type types-sros:ip-address;
                    description "IPv4 or IPv6 address for the RPKI local cache server";
                }

                leaf connect-retry {
                    type uint32 {
                        range "1..65535";
                    }
                    units "seconds";
                    default "120";
                    description "RPKI connect retry timer value";
                }

                leaf description {
                    type types-sros:description;
                    description "Text description";
                }

                leaf local-address {
                    type types-sros:ip-address;
                    sros-ext:auto-restart-to-modify;
                    description "Local address for the TCP connection setup";
                }

                leaf port {
                    type uint32 {
                        range "0..65535";
                    }
                    sros-ext:auto-restart-to-modify;
                    default "323";
                    description "Destination port used to connect to the cache server";
                }

                leaf admin-state {
                    type types-sros:admin-state;
                    default "disable";
                    description "Administrative state of the RPKI session";
                }

                leaf stale-time {
                    type uint32 {
                        range "60..3600";
                    }
                    units "seconds";
                    default "3600";
                    description "Maximum time prefix origin validation remains usable";
                }

                leaf-list apply-groups {
                    type leafref {
                        path "../../../../groups/group/name";
                    }
                    max-elements 8;
                    ordered-by user;
                    description "Apply a configuration group at this level";
                }

                leaf-list apply-groups-exclude {
                    type leafref {
                        path "../../../../groups/group/name";
                    }
                    max-elements 8;
                    ordered-by user;
                    description "Exclude a configuration group at this level";
                }

                container refresh-time {
                    description "Enter the refresh-time context";

                    leaf value {
                        type uint32 {
                            range "30..32767";
                        }
                        units "seconds";
                        default "300";
                        description "Periodic Serial Query PDUs sent for liveness detection";
                    }

                    leaf hold-time {
                        type uint32 {
                            range "60..65535";
                        }
                        units "seconds";
                        default "600";
                        description "Length of time that the session is considered Up";
                    }

                } // container refresh-time

            } // list rpki-session

        } // container origin-validation

    } // grouping conf-router-origin-validation

}
