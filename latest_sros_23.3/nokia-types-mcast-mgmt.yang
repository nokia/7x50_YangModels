module nokia-types-mcast-mgmt {

    yang-version "1.1";

    namespace "urn:nokia.com:sros:ns:yang:sr:types-mcast-mgmt";

    prefix "types-mcast-mgmt";

    import nokia-sros-yang-extensions     { prefix "sros-ext"; }

    sros-ext:sros-major-release "rel23";

    organization "Nokia";

    contact
        "Nokia SR OS Support
         Web: <http://www.nokia.com>";

    description
        "Common mcast mgmt data types used in the SR OS management system.

         Copyright 2016 Nokia. All rights reserved. Reproduction of this document
         is authorized on the condition that the foregoing copyright notice is included.

         This nokia-types-mcast-mgmt YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";

    revision "2018-06-19";

    typedef mode {
        type enumeration {
            enum "burst"                        { value 1; }
            enum "dent"                         { value 2; }
            enum "hybrid"                       { value 3; }
        }
        description
            "An enumerated integer that describes the values used to
             identify the mode of the Fast Channel Change (FCC) server
             configured";
    }

    typedef channel-type {
        type enumeration {
            enum "hd"                           { value 2; }
            enum "sd"                           { value 3; }
            enum "pip"                          { value 4; }
        }
        default "hd";
        description
            "The channel-type data type is an enumerated integer that
             describes the video channel type. It identifies whether
             the video channel is High Definition (HD), Standard
             Definition (SD) or Picture-in-Picture (PIP).";
    }

    typedef channel-type-with-inherit {
        type enumeration {
            enum "hd"                           { value 2; }
            enum "sd"                           { value 3; }
            enum "pip"                          { value 4; }
        }
        description
            "The channel-type-with-inherit data type is an enumerated integer that describes
             the video channel type. It identifies whether the video channel type is
             High Definition (HD), Standard Definition (SD), Picture-in-Picture(PIP) or
             inherited from another mo object";
    }

    typedef percent-without-zero {
        type uint32 {
            range "1..100";
        }
        units "percent";
        description "Integer number used to specify the percentage value.";
    }

    typedef percent-without-zero-and-hundred {
        type uint32 {
            range "1..99";
        }
        units "percent";
        description "Integer number used to specify the percentage value.";
    }

}
