module nokia-li-state {

    yang-version "1.1";

    namespace "urn:nokia.com:sros:ns:yang:sr:li-state";

    prefix "li-state";

    import ietf-inet-types                { prefix "inet"; }
    import ietf-yang-types                { prefix "yang"; }
    import nokia-sros-yang-extensions     { prefix "sros-ext"; }
    import nokia-state                    { prefix "state"; }
    import nokia-types-filter             { prefix "types-filter"; }
    import nokia-types-log                { prefix "types-log"; }
    import nokia-types-services           { prefix "types-services"; }
    import nokia-types-sros               { prefix "types-sros"; }
    import nokia-types-subscriber-mgmt    { prefix "types-submgt"; }

    sros-ext:sros-major-release "rel23";

    organization "Nokia";

    contact
        "Nokia SR OS Support
         Web: <http://www.nokia.com>";

    description
        "Nokia YANG Data model to show state data on SR OS based routers.

         Copyright 2016 Nokia. All rights reserved. Reproduction of this document
         is authorized on the condition that the foregoing copyright notice is included.

         This nokia-li-state YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";

    revision "2022-11-25";

    augment /state:state {

        container li {
            config false;
            description "Enter the li context";

            container li-filter {
                description "Enter the li-filter context";

                list li-ip-filter {
                    key "li-filter-name";
                    description "Enter the li-ip-filter list instance";

                    leaf li-filter-name {
                        type types-sros:named-item;
                        description "LI filter name";
                    }

                    list entry {
                        key "li-entry-id";
                        description "Enter the entry list instance";

                        leaf li-entry-id {
                            type types-filter:limited-entry-id;
                            description "LI filter entry ID";
                        }

                        container statistics {
                            description "Enter the statistics context";

                            leaf ingress-hit-pkt {
                                type yang:zero-based-counter64;
                                description
                                    "This object indicates the number of times an ingress packet
                                     matched this entry.";
                            }

                            leaf ingress-hit-byte {
                                type yang:zero-based-counter64;
                                description
                                    "The value of this object indicates the number of bytes of
                                     all ingress packets that matched this entry.";
                            }

                            leaf egress-hit-pkt {
                                type yang:zero-based-counter64;
                                description
                                    "This object indicates the number of times an egress packet
                                     matched this entry.";
                            }

                            leaf egress-hit-byte {
                                type yang:zero-based-counter64;
                                description
                                    "This object indicates the number of bytes of all egress
                                     packets that matched this entry.";
                            }

                        } // container statistics

                    } // list entry

                } // list li-ip-filter

                list li-ipv6-filter {
                    key "li-filter-name";
                    description "Enter the li-ipv6-filter list instance";

                    leaf li-filter-name {
                        type types-sros:named-item;
                        description "LI filter name";
                    }

                    list entry {
                        key "li-entry-id";
                        description "Enter the entry list instance";

                        leaf li-entry-id {
                            type types-filter:limited-entry-id;
                            description "LI filter entry ID";
                        }

                        container statistics {
                            description "Enter the statistics context";

                            leaf ingress-hit-pkt {
                                type yang:zero-based-counter64;
                                description
                                    "This object indicates the number of times an ingress packet
                                     matched this entry.";
                            }

                            leaf ingress-hit-byte {
                                type yang:zero-based-counter64;
                                description
                                    "The value of this object indicates the number of bytes of
                                     all ingress packets that matched this entry.";
                            }

                            leaf egress-hit-pkt {
                                type yang:zero-based-counter64;
                                description
                                    "This object indicates the number of times an egress packet
                                     matched this entry.";
                            }

                            leaf egress-hit-byte {
                                type yang:zero-based-counter64;
                                description
                                    "This object indicates the number of bytes of all egress
                                     packets that matched this entry.";
                            }

                        } // container statistics

                    } // list entry

                } // list li-ipv6-filter

                list li-mac-filter {
                    key "li-filter-name";
                    description "Enter the li-mac-filter list instance";

                    leaf li-filter-name {
                        type types-sros:named-item;
                        description "LI filter name";
                    }

                    list entry {
                        key "li-entry-id";
                        description "Enter the entry list instance";

                        leaf li-entry-id {
                            type types-filter:limited-entry-id;
                            description "LI filter entry ID";
                        }

                        container statistics {
                            description "Enter the statistics context";

                            leaf ingress-hit-pkt {
                                type yang:zero-based-counter64;
                                description
                                    "This object indicates the number of times an ingress packet
                                     matched this entry.";
                            }

                            leaf ingress-hit-byte {
                                type yang:zero-based-counter64;
                                description
                                    "The value of this object indicates the number of bytes of
                                     all ingress packets that matched this entry.";
                            }

                            leaf egress-hit-pkt {
                                type yang:zero-based-counter64;
                                description
                                    "This object indicates the number of times an egress packet
                                     matched this entry.";
                            }

                            leaf egress-hit-byte {
                                type yang:zero-based-counter64;
                                description
                                    "This object indicates the number of bytes of all egress
                                     packets that matched this entry.";
                            }

                        } // container statistics

                    } // list entry

                } // list li-mac-filter

            } // container li-filter


            list li-source {
                key "service-name";
                description "Enter the li-source list instance";

                leaf service-name {
                    type types-services:service-name;
                    description "Administrative service name";
                }

                list port {
                    key "port-id";
                    description "Enter the port list instance";

                    leaf port-id {
                        type types-services:mirror-source-port-lag-key;
                        description "Port ID";
                    }

                    leaf license-state {
                        type enumeration {
                            enum "unknown"                      { value 0; }
                            enum "ok"                           { value 1; }
                            enum "insufficient"                 { value 2; }
                            enum "violation"                    { value 3; }
                        }
                        description "license state for li-source port support";
                    }

                } // list port

                container nat {
                    description "Enter the nat context";

                    list nat44 {
                        key "router-instance ip";
                        description "Enter the nat44 list instance";

                        leaf router-instance {
                            type types-services:service-name;
                            description "Name of the service";
                        }

                        leaf ip {
                            type types-sros:ipv4-address;
                            description "IP address of the subscriber";
                        }

                        leaf oper-state {
                            type types-sros:oper-state;
                            description "Operational state of the subscriber";
                        }

                    } // list nat44

                    list dslite {
                        key "router-instance b4";
                        description "Enter the dslite list instance";

                        leaf router-instance {
                            type types-services:service-name;
                            description "Name of the service";
                        }

                        leaf b4 {
                            type types-sros:ipv6-prefix;
                            description "B4 prefix of the subscriber";
                        }

                        leaf oper-state {
                            type types-sros:oper-state;
                            description "Operational state of the subscriber";
                        }

                    } // list dslite

                    list nat64 {
                        key "router-instance ip";
                        description "Enter the nat64 list instance";

                        leaf router-instance {
                            type types-services:service-name;
                            description "Name of the service";
                        }

                        leaf ip {
                            type types-sros:ipv6-prefix;
                            description "IP prefix of the subscriber";
                        }

                        leaf oper-state {
                            type types-sros:oper-state;
                            description "Operational state of the subscriber";
                        }

                    } // list nat64

                    list l2-aware {
                        key "subscriber-id";
                        description "Enter the l2-aware list instance";

                        leaf subscriber-id {
                            type types-submgt:subscriber-id;
                            description "The string identifying the subscribe";
                        }

                        leaf oper-state {
                            type types-sros:oper-state;
                            description "Operational state of the subscriber";
                        }

                    } // list l2-aware

                } // container nat

            } // list li-source


            container log {
                description "Enter the log context";

                list log-id {
                    key "name";
                    description "Enter the log-id list instance";

                    leaf name {
                        type types-log:li-log-name;
                        description "Log ID";
                    }

                    leaf oper-state {
                        type types-sros:oper-state;
                        description "Operational state";
                    }

                    leaf wrapped {
                        type boolean;
                        description "The sequence-number for this log has wrapped";
                    }

                    leaf next-event {
                        type yang:counter64;
                        description
                            "The value of the this object is the count of the number
                             of events that have been forwarded to this logs's
                             destination.";
                    }

                    container statistics {
                        description "Enter the statistics context";

                        leaf logged-events {
                            type yang:counter64;
                            description
                                "The value of the this object is the count of the number
                                 of events that have been forwarded to this logs's
                                 destination.";
                        }

                        leaf dropped-events {
                            type yang:counter64;
                            description
                                "The value of the this object is the count of the number
                                 of events that have been sent to this logs source(s) and
                                 that have not been forwarded to the log destination
                                 because they were filtered out by the log filter.";
                        }

                    } // container statistics

                    list event {
                        key "sequence-number";
                        description "Enter the event list instance";

                        leaf sequence-number {
                            type uint64;
                            description
                                "A sequence number to indicate the ordering of log
                                 events in the log-id. If the event is replayed,
                                 the sequence number is replayed as well.";
                        }

                        leaf time {
                            type yang:date-and-time;
                            description "Time when the event was generated";
                        }

                        leaf severity {
                            type types-log:severity-level;
                            description "The severity level of the log event";
                        }

                        leaf application {
                            type types-log:application-state;
                            description "The name of the application that reports the log event";
                        }

                        leaf event-id {
                            type uint32 {
                                range "1..max";
                            }
                            description
                                "The id the event that was generated.

                                 Each log event type has a unique identifying number.
                                 This number is unique within a particular software
                                 application, such as IP, MPLS, OSPF, etc. but it is not
                                 necessarily unique across different software applications.
                                 That is MPLS event #1001 may be different from OSPF
                                 event #1001.";
                        }

                        leaf event-name {
                            type types-sros:named-item;
                            description "The name of the log event that was generated";
                        }

                        leaf vrtr-name {
                            type types-log:vrtr-name;
                            description "The router context name that generated the log event";
                        }

                        leaf subject {
                            type string {
                                length "0..32";
                            }
                            description
                                "The router context name that generated the log event.

                                 The subject is the entity that originated the event,
                                 such as the Port ID.";
                        }

                        leaf message {
                            type string {
                                length "1..4100";
                            }
                            description "The log event message";
                        }

                    } // list event

                } // list log-id

            } // container log


            container x-interfaces {
                description "Enter the x-interfaces context";

                container x1 {
                    description "Enter the x1 context";

                    leaf oper-state {
                        type enumeration {
                            enum "unknown"                      { value 1; }
                            enum "up"                           { value 2; }
                            enum "down"                         { value 3; }
                            enum "transition"                   { value 4; }
                            enum "wait-persistence"             { value 5; }
                        }
                        description "The operational state of the X interface.";
                    }

                    list lic {
                        key "name";
                        description "Enter the lic list instance";

                        leaf name {
                            type types-sros:named-item;
                            description "LIC name";
                        }

                        container statistics {
                            description "Enter the statistics context";

                            leaf received-message-count {
                                type yang:zero-based-counter32;
                                description "Indicates the number of messages received on the interface.";
                            }

                            leaf transmitted-message-count {
                                type yang:zero-based-counter32;
                                description "Indicates the number of messages transmitted on the interface.";
                            }

                            leaf received-bytes {
                                type yang:zero-based-counter64;
                                units "bytes";
                                description "Indicates the number of bytes received on the interface.";
                            }

                            leaf transmitted-bytes {
                                type yang:zero-based-counter64;
                                units "bytes";
                                description "Indicates the number of bytes transmitted on the interface.";
                            }

                        } // container statistics

                        list connection {
                            key "local-address local-port";
                            description "Enter the connection list instance";

                            leaf local-address {
                                type types-sros:ip-address;
                                description "The local (BNG) IP address used for the connection to the LIC.";
                            }

                            leaf local-port {
                                type inet:port-number;
                                description "The local (BNG) TCP port used for the connection to the LIC.";
                            }

                            leaf remote-address {
                                type types-sros:ip-address;
                                description "The remote (LIC) IP address used for the connection.";
                            }

                            leaf remote-port {
                                type inet:port-number;
                                description "The remote (LIC) TCP port used for the connection.";
                            }

                            leaf state {
                                type enumeration {
                                    enum "none"                         { value 0; }
                                    enum "listening"                    { value 1; }
                                    enum "established"                  { value 2; }
                                }
                                description "The state of the connection.";
                            }

                        } // list connection

                    } // list lic

                } // container x1

                container x2 {
                    description "Enter the x2 context";

                    leaf oper-state {
                        type enumeration {
                            enum "unknown"                      { value 1; }
                            enum "up"                           { value 2; }
                            enum "down"                         { value 3; }
                            enum "transition"                   { value 4; }
                            enum "wait-persistence"             { value 5; }
                        }
                        description "The operational state of the X interface.";
                    }

                    list lic {
                        key "name";
                        description "Enter the lic list instance";

                        leaf name {
                            type types-sros:named-item;
                            description "LIC name";
                        }

                        container statistics {
                            description "Enter the statistics context";

                            leaf received-message-count {
                                type yang:zero-based-counter32;
                                description "Indicates the number of messages received on the interface.";
                            }

                            leaf transmitted-message-count {
                                type yang:zero-based-counter32;
                                description "Indicates the number of messages transmitted on the interface.";
                            }

                            leaf received-bytes {
                                type yang:zero-based-counter64;
                                units "bytes";
                                description "Indicates the number of bytes received on the interface.";
                            }

                            leaf transmitted-bytes {
                                type yang:zero-based-counter64;
                                units "bytes";
                                description "Indicates the number of bytes transmitted on the interface.";
                            }

                        } // container statistics

                        list connection {
                            key "local-address local-port";
                            description "Enter the connection list instance";

                            leaf local-address {
                                type types-sros:ip-address;
                                description "The local (BNG) IP address used for the connection to the LIC.";
                            }

                            leaf local-port {
                                type inet:port-number;
                                description "The local (BNG) TCP port used for the connection to the LIC.";
                            }

                            leaf remote-address {
                                type types-sros:ip-address;
                                description "The remote (LIC) IP address used for the connection.";
                            }

                            leaf remote-port {
                                type inet:port-number;
                                description "The remote (LIC) TCP port used for the connection.";
                            }

                            leaf state {
                                type enumeration {
                                    enum "none"                         { value 0; }
                                    enum "listening"                    { value 1; }
                                    enum "established"                  { value 2; }
                                }
                                description "The state of the connection.";
                            }

                        } // list connection

                    } // list lic

                } // container x2

                container x3 {
                    description "Enter the x3 context";

                    leaf oper-state {
                        type enumeration {
                            enum "unknown"                      { value 1; }
                            enum "up"                           { value 2; }
                            enum "down"                         { value 3; }
                            enum "transition"                   { value 4; }
                            enum "wait-persistence"             { value 5; }
                        }
                        description "The operational state of the X interface.";
                    }

                    list lic {
                        key "name";
                        description "Enter the lic list instance";

                        leaf name {
                            type types-sros:named-item;
                            description "LIC name";
                        }

                        container statistics {
                            description "Enter the statistics context";

                            leaf received-message-count {
                                type yang:zero-based-counter32;
                                description "Indicates the number of messages received on the interface.";
                            }

                            leaf transmitted-message-count {
                                type yang:zero-based-counter32;
                                description "Indicates the number of messages transmitted on the interface.";
                            }

                            leaf received-bytes {
                                type yang:zero-based-counter64;
                                units "bytes";
                                description "Indicates the number of bytes received on the interface.";
                            }

                            leaf transmitted-bytes {
                                type yang:zero-based-counter64;
                                units "bytes";
                                description "Indicates the number of bytes transmitted on the interface.";
                            }

                            leaf lic-attempt-count {
                                type yang:zero-based-counter32;
                                description
                                    "Indicates the number of times the system has attempted to
                                     set up a tunnel with this X3 peer LIC.";
                            }

                            leaf lic-success-count {
                                type yang:zero-based-counter32;
                                description
                                    "Indicates the number of times the system has successfully
                                     set up a tunnel with this X3 peer LIC";
                            }

                        } // container statistics

                        list connection {
                            key "local-address local-port";
                            description "Enter the connection list instance";

                            leaf local-address {
                                type types-sros:ip-address;
                                description "The local (BNG) IP address used for the connection to the LIC.";
                            }

                            leaf local-port {
                                type inet:port-number;
                                description "The local (BNG) TCP port used for the connection to the LIC.";
                            }

                            leaf remote-address {
                                type types-sros:ip-address;
                                description "The remote (LIC) IP address used for the connection.";
                            }

                            leaf remote-port {
                                type inet:port-number;
                                description "The remote (LIC) TCP port used for the connection.";
                            }

                            leaf state {
                                type enumeration {
                                    enum "none"                         { value 0; }
                                    enum "listening"                    { value 1; }
                                    enum "established"                  { value 2; }
                                }
                                description "The state of the connection.";
                            }

                        } // list connection

                    } // list lic

                } // container x3

            } // container x-interfaces


        } // container li

    }
}
