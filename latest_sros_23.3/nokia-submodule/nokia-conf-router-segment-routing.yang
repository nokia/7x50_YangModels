submodule nokia-conf-router-segment-routing {

    yang-version "1.1";

    belongs-to nokia-conf { prefix "conf"; }

    import nokia-sros-yang-extensions     { prefix "sros-ext"; }
    import nokia-types-sr-mpls            { prefix "types-sr-mpls"; }
    import nokia-types-sros               { prefix "types-sros"; }

    include nokia-conf-bfd;
    include nokia-conf-groups;
    include nokia-conf-pxc;
    include nokia-conf-router;


    sros-ext:sros-major-release "rel23";

    organization "Nokia";

    contact
        "Nokia SR OS Support
         Web: <http://www.nokia.com>";

    description
        "Nokia YANG Data model to configure segment routing management on SR OS based routers.

         Copyright 2016 Nokia. All rights reserved. Reproduction of this document
         is authorized on the condition that the foregoing copyright notice is included.

         This nokia-conf-router-segment-routing YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";

    revision "2023-02-01";

    grouping conf-router-segment-routing {
        container segment-routing {
            when "../router-name = 'Base'";
            description "Enter the segment-routing context";

            leaf-list apply-groups {
                type leafref {
                    path "../../../groups/group/name";
                }
                max-elements 8;
                ordered-by user;
                description "Apply a configuration group at this level";
            }

            leaf-list apply-groups-exclude {
                type leafref {
                    path "../../../groups/group/name";
                }
                max-elements 8;
                ordered-by user;
                description "Exclude a configuration group at this level";
            }

            list maintenance-policy {
                key "policy-name";
                description "Enter the maintenance-policy list instance";

                leaf policy-name {
                    type types-sros:named-item;
                    description "Maintenance policy name";
                }

                leaf admin-state {
                    type types-sros:admin-state;
                    default "disable";
                    description "Administrative state of the maintenance policy";
                }

                leaf bfd-liveness {
                    type boolean;
                    sros-ext:auto-restart-to-modify;
                    default "false";
                    description "Enable seamless BFD for segment lists of candidate path";
                }

                leaf bfd-template {
                    type leafref {
                        path "../../../../bfd/bfd-template/name";
                    }
                    sros-ext:auto-restart-to-modify;
                    description "BFD template to be used by seamless BFD";
                }

                leaf mode {
                    type enumeration {
                        enum "none"                         { value 0; }
                        enum "ecmp-protected"               { value 1; }
                        enum "linear"                       { value 2; }
                    }
                    sros-ext:auto-restart-to-modify;
                    default "none";
                    description "Protection mode for SR policy candidate paths";
                }

                leaf threshold {
                    type uint32 {
                        range "1..32";
                    }
                    sros-ext:auto-restart-to-modify;
                    default "1";
                    description "Minimum number of up S-BFD sessions for up path status";
                }

                leaf hold-down-timer {
                    type uint32 {
                        range "0..5000";
                    }
                    units "deciseconds";
                    sros-ext:auto-restart-to-modify;
                    default "0";
                    description "Hold down timer for SR policy candidate paths";
                }

                leaf revert-timer {
                    type uint32 {
                        range "0..4320";
                    }
                    units "minutes";
                    description "Revert timer for SR policy candidate paths";
                }

                leaf return-path-label {
                    type uint32 {
                        range "32..1048512";
                    }
                    sros-ext:auto-restart-to-modify;
                    description "S-BFD return-path label";
                }

                leaf-list apply-groups {
                    type leafref {
                        path "../../../../groups/group/name";
                    }
                    max-elements 8;
                    ordered-by user;
                    description "Apply a configuration group at this level";
                }

                leaf-list apply-groups-exclude {
                    type leafref {
                        path "../../../../groups/group/name";
                    }
                    max-elements 8;
                    ordered-by user;
                    description "Exclude a configuration group at this level";
                }

            } // list maintenance-policy

            container sr-mpls {
                description "Enter the sr-mpls context";

                leaf-list apply-groups {
                    type leafref {
                        path "../../../../groups/group/name";
                    }
                    max-elements 8;
                    ordered-by user;
                    description "Apply a configuration group at this level";
                }

                leaf-list apply-groups-exclude {
                    type leafref {
                        path "../../../../groups/group/name";
                    }
                    max-elements 8;
                    ordered-by user;
                    description "Exclude a configuration group at this level";
                }

                list prefix-sids {
                    key "interface-name";
                    description "Enter the prefix-sids list instance";

                    leaf interface-name {
                        type leafref {
                            path "../../../../interface/interface-name";
                        }
                        description "Loopback interface name that owns the prefix to be advertised";
                    }

                    leaf node-sid {
                        type boolean;
                        default "true";
                        description "Assign a node SID to the prefix referencing the router";
                    }

                    leaf-list apply-groups {
                        type leafref {
                            path "../../../../../groups/group/name";
                        }
                        max-elements 8;
                        ordered-by user;
                        description "Apply a configuration group at this level";
                    }

                    leaf-list apply-groups-exclude {
                        type leafref {
                            path "../../../../../groups/group/name";
                        }
                        max-elements 8;
                        ordered-by user;
                        description "Exclude a configuration group at this level";
                    }

                    container ipv4-sid {
                        presence "Enable the ipv4-sid context";
                        description "Enter the ipv4-sid context";

                        choice type {
                            case label {

                                leaf label {
                                    type int64 {
                                        range "32..1048575";
                                    }
                                    description "Label value for the node SID";
                                }

                            }
                            case index {

                                leaf index {
                                    type int64 {
                                        range "0..4294967295";
                                    }
                                    description "Node SID index for the interface";
                                }

                            }
                        }
                    } // container ipv4-sid

                    container ipv6-sid {
                        presence "Enable the ipv6-sid context";
                        description "Enter the ipv6-sid context";

                        choice type {
                            case label {

                                leaf label {
                                    type int64 {
                                        range "32..1048575";
                                    }
                                    description "Label value for the node SID";
                                }

                            }
                            case index {

                                leaf index {
                                    type int64 {
                                        range "0..4294967295";
                                    }
                                    description "Node SID index for the interface";
                                }

                            }
                        }
                    } // container ipv6-sid

                } // list prefix-sids

            } // container sr-mpls

            container sr-policies {
                description "Enter the sr-policies context";

                leaf admin-state {
                    type types-sros:admin-state;
                    default "disable";
                    description "Administrative state of segment routing policies";
                }

                leaf reserved-label-block {
                    type leafref {
                        path "../../../mpls-labels/reserved-label-block/label-block-name";
                    }
                    sros-ext:auto-restart-to-modify;
                    description "Reserved local block for segment routing policies";
                }

                leaf-list apply-groups {
                    type leafref {
                        path "../../../../groups/group/name";
                    }
                    max-elements 8;
                    ordered-by user;
                    description "Apply a configuration group at this level";
                }

                leaf-list apply-groups-exclude {
                    type leafref {
                        path "../../../../groups/group/name";
                    }
                    max-elements 8;
                    ordered-by user;
                    description "Exclude a configuration group at this level";
                }

                container ingress-statistics {
                    presence "Enable the ingress-statistics context";
                    description "Enter the ingress-statistics context";

                    leaf admin-state {
                        type types-sros:admin-state;
                        default "disable";
                        description "Administrative state of the traffic statistics";
                    }

                    leaf-list apply-groups {
                        type leafref {
                            path "../../../../../groups/group/name";
                        }
                        max-elements 8;
                        ordered-by user;
                        description "Apply a configuration group at this level";
                    }

                    leaf-list apply-groups-exclude {
                        type leafref {
                            path "../../../../../groups/group/name";
                        }
                        max-elements 8;
                        ordered-by user;
                        description "Exclude a configuration group at this level";
                    }

                } // container ingress-statistics

                container egress-statistics {
                    presence "Enable the egress-statistics context";
                    description "Enter the egress-statistics context";

                    leaf admin-state {
                        type types-sros:admin-state;
                        default "disable";
                        description "Administrative state of the traffic statistics";
                    }

                    leaf-list apply-groups {
                        type leafref {
                            path "../../../../../groups/group/name";
                        }
                        max-elements 8;
                        ordered-by user;
                        description "Apply a configuration group at this level";
                    }

                    leaf-list apply-groups-exclude {
                        type leafref {
                            path "../../../../../groups/group/name";
                        }
                        max-elements 8;
                        ordered-by user;
                        description "Exclude a configuration group at this level";
                    }

                } // container egress-statistics

                list static-policy {
                    key "name";
                    max-elements 8192;
                    description "Enter the static-policy list instance";

                    leaf name {
                        type types-sros:named-item-64;
                        description "Name for the segment routing static policy";
                    }

                    leaf admin-state {
                        type types-sros:admin-state;
                        default "disable";
                        description "Administrative state of segment routing static policy";
                    }

                    leaf color {
                        type int64 {
                            range "0..4294967295";
                        }
                        sros-ext:auto-restart-to-modify;
                        description "Traffic flows to be steered by this policy";
                    }

                    leaf endpoint {
                        type types-sros:ip-address;
                        sros-ext:auto-restart-to-modify;
                        description "Destination of the source-routed path";
                    }

                    leaf preference {
                        type uint32;
                        sros-ext:auto-restart-to-modify;
                        default "100";
                        description "Preference value of this static policy";
                    }

                    leaf head-end {
                        type union {
                            type types-sros:ip-address;
                            type enumeration {
                                enum "local"                        { value 1; }
                            }
                        }
                        sros-ext:auto-restart-to-modify;
                        description "Head end address for this static policy";
                    }

                    leaf binding-sid {
                        type types-sros:mpls-label-or-zero;
                        description "Segment ID that opaquely represents an SR policy to upstream routers";
                    }

                    leaf distinguisher {
                        type uint32 {
                            range "1..max";
                        }
                        sros-ext:auto-restart-to-modify;
                        description "Unique value for a policy";
                    }

                    leaf maintenance-policy {
                        type leafref {
                            path "../../../maintenance-policy/policy-name";
                        }
                        sros-ext:auto-restart-to-modify;
                        description "Policy name";
                    }

                    leaf prefer-transport-frr {
                        type boolean;
                        sros-ext:auto-restart-to-modify;
                        default "false";
                        description "Enable transport FRR preference";
                    }

                    leaf type {
                        type enumeration {
                            enum "sr-mpls"                      { value 1; }
                            enum "srv6"                         { value 2; }
                        }
                        default "sr-mpls";
                        description "Static policy type";
                    }

                    leaf-list apply-groups {
                        type leafref {
                            path "../../../../../groups/group/name";
                        }
                        max-elements 8;
                        ordered-by user;
                        description "Apply a configuration group at this level";
                    }

                    leaf-list apply-groups-exclude {
                        type leafref {
                            path "../../../../../groups/group/name";
                        }
                        max-elements 8;
                        ordered-by user;
                        description "Exclude a configuration group at this level";
                    }

                    container segment-routing-v6 {
                        presence "Enable the segment-routing-v6 context";
                        sros-ext:auto-restart-to-modify;
                        description "Enter the segment-routing-v6 context";

                        leaf return-path-bfd-sid {
                            type types-sros:ipv6-address;
                            description "BFD controlled return path for SRv6";
                        }

                        list binding-sid {
                            key "index";
                            max-elements 1;
                            description "Enter the binding-sid list instance";

                            leaf index {
                                type uint32 {
                                    range "1";
                                }
                                description "Binding SID index";
                            }

                            leaf-list apply-groups {
                                type leafref {
                                    path "../../../../../../../groups/group/name";
                                }
                                max-elements 8;
                                ordered-by user;
                                description "Apply a configuration group at this level";
                            }

                            leaf-list apply-groups-exclude {
                                type leafref {
                                    path "../../../../../../../groups/group/name";
                                }
                                max-elements 8;
                                ordered-by user;
                                description "Exclude a configuration group at this level";
                            }

                            choice binding-sid-type {
                                case remote-binding-sid {

                                    leaf ip-address {
                                        type types-sros:ipv6-address;
                                        description "Remote SRv6 binding SID";
                                    }

                                }
                                case local-binding-sid {

                                    container locator {
                                        presence "Enable the locator context";
                                        description "Enter the locator context";

                                        leaf locator-name {
                                            type leafref {
                                                path "../../../../../../../../router/segment-routing/segment-routing-v6/locator/locator-name";
                                            }
                                            mandatory true;
                                            description "Local SRv6 binding SID locator name";
                                        }

                                        leaf function {
                                            type enumeration {
                                                enum "end-b6-encaps-red"            { value 1; }
                                            }
                                            mandatory true;
                                            description "Local SRv6 binding SID locator function";
                                        }

                                        leaf function-value {
                                            type uint32 {
                                                range "1..1048575";
                                            }
                                            description "Local SRv6 binding SID locator function value";
                                        }

                                    } // container locator

                                }
                            }
                        } // list binding-sid

                    } // container segment-routing-v6

                    list segment-list {
                        key "seg-list-index";
                        max-elements 32;
                        description "Enter the segment-list list instance";

                        leaf seg-list-index {
                            type uint32 {
                                range "1..32";
                            }
                            description "Index for identifying a particular segment list";
                        }

                        leaf admin-state {
                            type types-sros:admin-state;
                            default "disable";
                            description "Administrative state of segment list for static policy";
                        }

                        leaf weight {
                            type uint32;
                            sros-ext:auto-restart-to-modify;
                            default "1";
                            description "Weight of this segment list";
                        }

                        leaf-list apply-groups {
                            type leafref {
                                path "../../../../../../groups/group/name";
                            }
                            max-elements 8;
                            ordered-by user;
                            sros-ext:auto-restart-to-modify;
                            description "Apply a configuration group at this level";
                        }

                        leaf-list apply-groups-exclude {
                            type leafref {
                                path "../../../../../../groups/group/name";
                            }
                            max-elements 8;
                            ordered-by user;
                            sros-ext:auto-restart-to-modify;
                            description "Exclude a configuration group at this level";
                        }

                        list segment {
                            key "segment-index";
                            max-elements 11;
                            description "Enter the segment list instance";

                            leaf segment-index {
                                type uint32 {
                                    range "1..11";
                                }
                                description "Index for identifying a particular segment list";
                            }

                            leaf mpls-label {
                                type uint32 {
                                    range "0..1048575";
                                }
                                description "Value for the MPLS label";
                            }

                            leaf srv6-sid {
                                type types-sros:ipv6-address;
                                description "Segment ID for segment routing IPv6";
                            }

                            leaf-list apply-groups {
                                type leafref {
                                    path "../../../../../../../groups/group/name";
                                }
                                max-elements 8;
                                ordered-by user;
                                description "Apply a configuration group at this level";
                            }

                            leaf-list apply-groups-exclude {
                                type leafref {
                                    path "../../../../../../../groups/group/name";
                                }
                                max-elements 8;
                                ordered-by user;
                                description "Exclude a configuration group at this level";
                            }

                        } // list segment

                    } // list segment-list

                } // list static-policy

            } // container sr-policies

            container segment-routing-v6 {
                presence "Enable the segment-routing-v6 context";
                description "Enter the segment-routing-v6 context";

                leaf-list origination-fpe {
                    type leafref {
                        path "../../../../fwd-path-ext/fpe/fpe-id";
                    }
                    max-elements 1;
                    description "List of the SRv6 origination FPEs";
                }

                leaf source-address {
                    type types-sros:ipv6-unicast-address;
                    description "Source address used in the SRv6 packet";
                }

                leaf-list apply-groups {
                    type leafref {
                        path "../../../../groups/group/name";
                    }
                    max-elements 8;
                    ordered-by user;
                    description "Apply a configuration group at this level";
                }

                leaf-list apply-groups-exclude {
                    type leafref {
                        path "../../../../groups/group/name";
                    }
                    max-elements 8;
                    ordered-by user;
                    description "Exclude a configuration group at this level";
                }

                list locator {
                    key "locator-name";
                    max-elements 16;
                    description "Enter the locator list instance";

                    leaf locator-name {
                        type types-sros:named-item-64 {
                            pattern "[^@]*" {
                                error-message "locator name cannot contain @";
                            }
                        }
                        description "SRv6 locator name";
                    }

                    leaf block-length {
                        type types-sros:prefix-length {
                            range "0..96";
                        }
                        sros-ext:auto-restart-to-modify;
                        default "0";
                        description "SRv6 locator block address length";
                    }

                    leaf function-length {
                        type types-sros:prefix-length {
                            range "16|20..96";
                        }
                        sros-ext:auto-restart-to-modify;
                        description "Function length";
                    }

                    leaf-list termination-fpe {
                        type leafref {
                            path "../../../../../fwd-path-ext/fpe/fpe-id";
                        }
                        max-elements 1;
                        description "List of the SRv6 termination FPE";
                    }

                    leaf label-block {
                        type leafref {
                            path "../../../../../router/mpls-labels/reserved-label-block/label-block-name";
                        }
                        sros-ext:auto-restart-to-modify;
                        description "Reserved label block name for service termination";
                    }

                    leaf admin-state {
                        type types-sros:admin-state;
                        default "disable";
                        description "Administrative state of the locator";
                    }

                    leaf algorithm {
                        type uint32 {
                            range "128..255";
                        }
                        sros-ext:auto-restart-to-modify;
                        description "IGP flexible algorithm ID";
                    }

                    leaf-list apply-groups {
                        type leafref {
                            path "../../../../../groups/group/name";
                        }
                        max-elements 8;
                        ordered-by user;
                        description "Apply a configuration group at this level";
                    }

                    leaf-list apply-groups-exclude {
                        type leafref {
                            path "../../../../../groups/group/name";
                        }
                        max-elements 8;
                        ordered-by user;
                        description "Exclude a configuration group at this level";
                    }

                    container prefix {
                        description "Enter the prefix context";

                        leaf ip-prefix {
                            type types-sros:ipv6-unicast-prefix;
                            sros-ext:auto-restart-to-modify;
                            description "SRv6 locator prefix";
                        }

                    } // container prefix

                    container static-function {
                        description "Enter the static-function context";

                        leaf max-entries {
                            type uint32 {
                                range "1..1048575";
                            }
                            sros-ext:auto-restart-to-modify;
                            default "1";
                            description "Maximum number of static SID functions";
                        }

                        leaf label-block {
                            type leafref {
                                path "../../../../../mpls-labels/reserved-label-block/label-block-name";
                            }
                            sros-ext:auto-restart-to-modify;
                            description "Label block for the service SIDs of the SRv6 locator";
                        }

                    } // container static-function

                } // list locator

                container micro-segment {
                    presence "Enable the micro-segment context";
                    description "Enter the micro-segment context";

                    leaf block-length {
                        type uint8 {
                            range "8|16|24|32|40|48|56|64";
                        }
                        default "32";
                        description "Micro-SID block length";
                    }

                    leaf global-sid-entries {
                        type uint8 {
                            range "4..60";
                        }
                        default "16";
                        description "Maximum number of micro-segment locators network wide";
                    }

                    leaf sid-length {
                        type uint8 {
                            range "16";
                        }
                        default "16";
                        description "Micro-SID length";
                    }

                    leaf-list apply-groups {
                        type leafref {
                            path "../../../../../groups/group/name";
                        }
                        max-elements 8;
                        ordered-by user;
                        description "Apply a configuration group at this level";
                    }

                    leaf-list apply-groups-exclude {
                        type leafref {
                            path "../../../../../groups/group/name";
                        }
                        max-elements 8;
                        ordered-by user;
                        description "Exclude a configuration group at this level";
                    }

                    list block {
                        key "block-name";
                        max-elements 16;
                        description "Enter the block list instance";

                        leaf block-name {
                            type types-sros:named-item-64 {
                                pattern "[^@]*" {
                                    error-message "Block name cannot contain @";
                                }
                            }
                            description "Micro-SID block name";
                        }

                        leaf admin-state {
                            type types-sros:admin-state;
                            default "disable";
                            description "Administrative state of micro-SID block";
                        }

                        leaf-list termination-fpe {
                            type leafref {
                                path "../../../../../../fwd-path-ext/fpe/fpe-id";
                            }
                            max-elements 1;
                            description "FPE ID for SRv6 termination";
                        }

                        leaf label-block {
                            type leafref {
                                path "../../../../../../router/mpls-labels/reserved-label-block/label-block-name";
                            }
                            sros-ext:auto-restart-to-modify;
                            description "Reserved label block";
                        }

                        leaf-list apply-groups {
                            type leafref {
                                path "../../../../../../groups/group/name";
                            }
                            max-elements 8;
                            ordered-by user;
                            description "Apply a configuration group at this level";
                        }

                        leaf-list apply-groups-exclude {
                            type leafref {
                                path "../../../../../../groups/group/name";
                            }
                            max-elements 8;
                            ordered-by user;
                            description "Exclude a configuration group at this level";
                        }

                        container prefix {
                            description "Enter the prefix context";

                            leaf ip-prefix {
                                type types-sros:ipv6-unicast-prefix;
                                sros-ext:auto-restart-to-modify;
                                description "SRv6 locator prefix";
                            }

                        } // container prefix

                        container static-function {
                            description "Enter the static-function context";

                            leaf max-entries {
                                type uint32 {
                                    range "1..1048575";
                                }
                                sros-ext:auto-restart-to-modify;
                                default "1";
                                description "Maximum number of static SID functions";
                            }

                        } // container static-function

                    } // list block

                } // container micro-segment

                list micro-segment-locator {
                    key "locator-name";
                    max-elements 16;
                    description "Enter the micro-segment-locator list instance";

                    leaf locator-name {
                        type types-sros:named-item-64 {
                            pattern "[^@]*" {
                                error-message "locator name cannot contain @";
                            }
                        }
                        description "SRv6 locator name";
                    }

                    leaf admin-state {
                        type types-sros:admin-state;
                        default "disable";
                        description "Administrative state of the locator";
                    }

                    leaf algorithm {
                        type uint32 {
                            range "128..255";
                        }
                        sros-ext:auto-restart-to-modify;
                        description "IGP flexible algorithm ID";
                    }

                    leaf block {
                        type leafref {
                            path "../../../../../router/segment-routing/segment-routing-v6/micro-segment/block/block-name";
                        }
                        sros-ext:auto-restart-to-modify;
                        description "Pre-defined micro-SID block";
                    }

                    leaf-list apply-groups {
                        type leafref {
                            path "../../../../../groups/group/name";
                        }
                        max-elements 8;
                        ordered-by user;
                        description "Apply a configuration group at this level";
                    }

                    leaf-list apply-groups-exclude {
                        type leafref {
                            path "../../../../../groups/group/name";
                        }
                        max-elements 8;
                        ordered-by user;
                        description "Exclude a configuration group at this level";
                    }

                    container un {
                        description "Enter the un context";

                        leaf srh-mode {
                            type types-sr-mpls:srh-mode;
                            sros-ext:auto-restart-to-modify;
                            default "psp";
                            description "Segment Routing Header (SRH) mode";
                        }

                        leaf value {
                            type uint32 {
                                range "1..1048575";
                            }
                            sros-ext:auto-restart-to-modify;
                            description "SRv6 function value";
                        }

                    } // container un

                } // list micro-segment-locator

                container base-routing-instance {
                    description "Enter the base-routing-instance context";

                    leaf-list apply-groups {
                        type leafref {
                            path "../../../../../groups/group/name";
                        }
                        max-elements 8;
                        ordered-by user;
                        description "Apply a configuration group at this level";
                    }

                    leaf-list apply-groups-exclude {
                        type leafref {
                            path "../../../../../groups/group/name";
                        }
                        max-elements 8;
                        ordered-by user;
                        description "Exclude a configuration group at this level";
                    }

                    list locator {
                        key "locator-name";
                        description "Enter the locator list instance";

                        leaf locator-name {
                            type leafref {
                                path "../../../locator/locator-name";
                            }
                            description "SRv6 locator name";
                        }

                        leaf-list apply-groups {
                            type leafref {
                                path "../../../../../../groups/group/name";
                            }
                            max-elements 8;
                            ordered-by user;
                            description "Apply a configuration group at this level";
                        }

                        leaf-list apply-groups-exclude {
                            type leafref {
                                path "../../../../../../groups/group/name";
                            }
                            max-elements 8;
                            ordered-by user;
                            description "Exclude a configuration group at this level";
                        }

                        container function {
                            description "Enter the function context";

                            list end {
                                key "value";
                                max-elements 8;
                                description "Enter the end list instance";

                                leaf value {
                                    type uint32 {
                                        range "1..1048575";
                                    }
                                    description "SRv6 SID function value";
                                }

                                leaf srh-mode {
                                    type types-sr-mpls:srh-mode;
                                    default "psp";
                                    description "Segment Routing Header (SRH) mode";
                                }

                                leaf-list apply-groups {
                                    type leafref {
                                        path "../../../../../../../../groups/group/name";
                                    }
                                    max-elements 8;
                                    ordered-by user;
                                    description "Apply a configuration group at this level";
                                }

                                leaf-list apply-groups-exclude {
                                    type leafref {
                                        path "../../../../../../../../groups/group/name";
                                    }
                                    max-elements 8;
                                    ordered-by user;
                                    description "Exclude a configuration group at this level";
                                }

                            } // list end

                            list end-x {
                                key "value";
                                description "Enter the end-x list instance";

                                leaf value {
                                    type uint32 {
                                        range "1..1048575";
                                    }
                                    description "SRv6 SID function value";
                                }

                                leaf srh-mode {
                                    type types-sr-mpls:srh-mode;
                                    default "psp";
                                    description "Segment Routing Header (SRH) mode";
                                }

                                leaf protection {
                                    type enumeration {
                                        enum "unprotected"                  { value 0; }
                                        enum "protected"                    { value 1; }
                                    }
                                    default "protected";
                                    description "Adjacency protection for SID function";
                                }

                                leaf interface-name {
                                    type leafref {
                                        path "../../../../../../../interface/interface-name";
                                    }
                                    description "Interface name";
                                }

                                leaf-list apply-groups {
                                    type leafref {
                                        path "../../../../../../../../groups/group/name";
                                    }
                                    max-elements 8;
                                    ordered-by user;
                                    description "Apply a configuration group at this level";
                                }

                                leaf-list apply-groups-exclude {
                                    type leafref {
                                        path "../../../../../../../../groups/group/name";
                                    }
                                    max-elements 8;
                                    ordered-by user;
                                    description "Exclude a configuration group at this level";
                                }

                            } // list end-x

                            list end-x-auto-allocate {
                                key "srh-mode protection";
                                max-elements 2;
                                description "Enter the end-x-auto-allocate list instance";

                                leaf srh-mode {
                                    type types-sr-mpls:srh-mode;
                                    description "Segment Routing Header (SRH) mode";
                                }

                                leaf protection {
                                    type enumeration {
                                        enum "unprotected"                  { value 0; }
                                        enum "protected"                    { value 1; }
                                    }
                                    description "Adjacency protection for automatic SID function";
                                }

                            } // list end-x-auto-allocate

                            container end-dt4 {
                                presence "Enable the end-dt4 context";
                                description "Enter the end-dt4 context";

                                leaf value {
                                    type uint32 {
                                        range "1..1048575";
                                    }
                                    description "SRv6 function value";
                                }

                            } // container end-dt4

                            container end-dt6 {
                                presence "Enable the end-dt6 context";
                                description "Enter the end-dt6 context";

                                leaf value {
                                    type uint32 {
                                        range "1..1048575";
                                    }
                                    description "SRv6 function value";
                                }

                            } // container end-dt6

                            container end-dt46 {
                                presence "Enable the end-dt46 context";
                                description "Enter the end-dt46 context";

                                leaf value {
                                    type uint32 {
                                        range "1..1048575";
                                    }
                                    description "SRv6 function value";
                                }

                            } // container end-dt46

                        } // container function

                    } // list locator

                    list micro-segment-locator {
                        key "locator-name";
                        description "Enter the micro-segment-locator list instance";

                        leaf locator-name {
                            type leafref {
                                path "../../../../../../router/segment-routing/segment-routing-v6/micro-segment-locator/locator-name";
                            }
                            description "SRv6 micro-segment locator name";
                        }

                        leaf-list apply-groups {
                            type leafref {
                                path "../../../../../../groups/group/name";
                            }
                            max-elements 8;
                            ordered-by user;
                            description "Apply a configuration group at this level";
                        }

                        leaf-list apply-groups-exclude {
                            type leafref {
                                path "../../../../../../groups/group/name";
                            }
                            max-elements 8;
                            ordered-by user;
                            description "Exclude a configuration group at this level";
                        }

                        container function {
                            description "Enter the function context";

                            list ua {
                                key "value";
                                description "Enter the ua list instance";

                                leaf value {
                                    type uint32 {
                                        range "1..1048575";
                                    }
                                    description "SRv6 SID function value";
                                }

                                leaf srh-mode {
                                    type types-sr-mpls:srh-mode;
                                    default "psp";
                                    description "Segment Routing Header (SRH) mode";
                                }

                                leaf protection {
                                    type enumeration {
                                        enum "unprotected"                  { value 0; }
                                        enum "protected"                    { value 1; }
                                    }
                                    default "protected";
                                    description "Adjacency protection for SID function";
                                }

                                leaf interface-name {
                                    type leafref {
                                        path "../../../../../../../../router/interface/interface-name";
                                    }
                                    description "Interface name";
                                }

                                leaf-list apply-groups {
                                    type leafref {
                                        path "../../../../../../../../groups/group/name";
                                    }
                                    max-elements 8;
                                    ordered-by user;
                                    description "Apply a configuration group at this level";
                                }

                                leaf-list apply-groups-exclude {
                                    type leafref {
                                        path "../../../../../../../../groups/group/name";
                                    }
                                    max-elements 8;
                                    ordered-by user;
                                    description "Exclude a configuration group at this level";
                                }

                            } // list ua

                            list ua-auto-allocate {
                                key "srh-mode protection";
                                max-elements 2;
                                description "Enter the ua-auto-allocate list instance";

                                leaf srh-mode {
                                    type types-sr-mpls:srh-mode;
                                    description "Segment Routing Header (SRH) mode";
                                }

                                leaf protection {
                                    type enumeration {
                                        enum "unprotected"                  { value 0; }
                                        enum "protected"                    { value 1; }
                                    }
                                    description "Adjacency protection for automatic SID function";
                                }

                            } // list ua-auto-allocate

                            container udt4 {
                                presence "Enable the udt4 context";
                                description "Enter the udt4 context";

                                leaf value {
                                    type uint32 {
                                        range "1..1048575";
                                    }
                                    description "SRv6 function value";
                                }

                            } // container udt4

                            container udt6 {
                                presence "Enable the udt6 context";
                                description "Enter the udt6 context";

                                leaf value {
                                    type uint32 {
                                        range "1..1048575";
                                    }
                                    description "SRv6 function value";
                                }

                            } // container udt6

                            container udt46 {
                                presence "Enable the udt46 context";
                                description "Enter the udt46 context";

                                leaf value {
                                    type uint32 {
                                        range "1..1048575";
                                    }
                                    description "SRv6 function value";
                                }

                            } // container udt46

                        } // container function

                    } // list micro-segment-locator

                } // container base-routing-instance

            } // container segment-routing-v6

        } // container segment-routing

    } // grouping conf-router-segment-routing

}
