submodule nokia-state-log {

    yang-version "1.1";

    belongs-to nokia-state { prefix "state"; }

    import ietf-yang-types                { prefix "yang"; }
    import nokia-sros-yang-extensions     { prefix "sros-ext"; }
    import nokia-types-application-assurance { prefix "types-aa"; }
    import nokia-types-card               { prefix "types-card"; }
    import nokia-types-log                { prefix "types-log"; }
    import nokia-types-services           { prefix "types-services"; }
    import nokia-types-sros               { prefix "types-sros"; }

    include nokia-state-test-oam;
    include nokia-state-testoam-service-activation-testhead;


    sros-ext:sros-major-release "rel23";

    organization "Nokia";

    contact
        "Nokia SR OS Support
         Web: <http://www.nokia.com>";

    description
        "Nokia YANG Data model with operational state for event stream logging on SR OS based routers.

         Copyright 2016 Nokia. All rights reserved. Reproduction of this document
         is authorized on the condition that the foregoing copyright notice is included.

         This nokia-state-log YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";

    revision "2023-04-14";

    grouping state-log {
        container log {
            description "Enter the log context";

            list accounting-policy {
                key "policy-id";
                description "Enter the accounting-policy list instance";

                leaf policy-id {
                    type types-log:log-policy-id;
                    description "Accounting policy unique ID";
                }

                leaf oper-state {
                    type types-sros:oper-state;
                    description
                        "The value of the this object indicates the operational
                         state of the accounting policy.";
                }

                leaf port-type {
                    type types-log:accounting-port-type;
                    description
                        "Indicates the type of facility associated with the specified
                         accounting policy's record type.";
                }

                leaf data-loss-count {
                    type yang:counter32;
                    description
                        "Indicates the number of times a log accounting data loss trap was
                         raised against this application policy.";
                }

                leaf last-data-loss-time {
                    type yang:date-and-time;
                    description
                        "Indicates the last time, since system startup that log accounting
                         data loss trap was raised against this application policy.";
                }

                container associations {
                    description "Enter the associations context";

                    list access {
                        key "service-name sap-id";
                        description "Enter the access list instance";

                        leaf service-name {
                            type types-sros:named-item-64;
                            description "Acc-policy is associated with service-name";
                        }

                        leaf sap-id {
                            type types-sros:sap;
                            description "Acc-policy is associated with the SAP ID.";
                        }

                    } // list access

                    list network {
                        key "port-id";
                        description "Enter the network list instance";

                        leaf port-id {
                            type types-sros:port;
                            description "The host port of the PXC.";
                        }

                    } // list network

                    list sdp {
                        key "sdp-id";
                        description "Enter the sdp list instance";

                        leaf sdp-id {
                            type types-services:sdp-id;
                            description "Service Distribution Point (SDP) identifier.";
                        }

                    } // list sdp

                    list sdp-bind {
                        key "service-name sdp-bind-id";
                        description "Enter the sdp-bind list instance";

                        leaf service-name {
                            type types-sros:named-item-64;
                            description "Acc-policy is associated with service-name";
                        }

                        leaf sdp-bind-id {
                            type types-services:sdp-bind-id;
                            description "Acc-policy is associated with the SDP ID.";
                        }

                    } // list sdp-bind

                    list subscriber {
                        key "profile-name";
                        description "Enter the subscriber list instance";

                        leaf profile-name {
                            type types-sros:named-item;
                            description "Acc-policy is associated with profile";
                        }

                    } // list subscriber

                    list aa-performance {
                        key "aa-assur-isa-group-id";
                        description "Enter the aa-performance list instance";

                        leaf aa-assur-isa-group-id {
                            type uint32;
                            description "Acc-policy is associated with the isa.";
                        }

                    } // list aa-performance

                    list application-assurance {
                        key "aa-group-id aa-partition-id category-name";
                        description "Enter the application-assurance list instance";

                        leaf aa-group-id {
                            type types-aa:isa-aa-grp-id;
                            description "Specifies an identfifer that uniquely identifies an AA group within the system.";
                        }

                        leaf aa-partition-id {
                            type types-aa:aa-grp-part-id;
                            description "The identifier which uniquely identifies the partition within the parent AA group.";
                        }

                        leaf category-name {
                            type types-aa:partition-stats-category;
                            description
                                "Specifies an identifier which uniquely identifies a statistics category
                                 within a AA partition";
                        }

                    } // list application-assurance

                    list qgrp-ingress {
                        key "port-id group-name";
                        description "Enter the qgrp-ingress list instance";

                        leaf port-id {
                            type types-sros:port;
                            description "Acc-policy is associated with qgrp with port";
                        }

                        leaf group-name {
                            type types-sros:named-item;
                            description "Acc-policy is associated with qgrp with group name";
                        }

                        leaf mode {
                            type types-log:access-network;
                            description "Acc-policy is associated with qgrp with mode";
                        }

                    } // list qgrp-ingress

                    list qgrp-egress {
                        key "port-id group-name instance-id";
                        description "Enter the qgrp-egress list instance";

                        leaf port-id {
                            type types-sros:port;
                            description "Acc-policy is associated with qgrp with port";
                        }

                        leaf group-name {
                            type types-sros:named-item;
                            description "Acc-policy is associated with qgrp with group name";
                        }

                        leaf instance-id {
                            type uint16 {
                                range "1..65535";
                            }
                            description "Specifies the instance identifier.";
                        }

                        leaf mode {
                            type types-log:access-network;
                            description "Acc-policy is associated with qgrp with mode";
                        }

                    } // list qgrp-egress

                    list qgrp-net-egress {
                        key "port-id group-name instance-id";
                        description "Enter the qgrp-net-egress list instance";

                        leaf port-id {
                            type types-sros:port;
                            description "Acc-policy is associated with qgrp with port";
                        }

                        leaf group-name {
                            type types-sros:named-item;
                            description "Acc-policy is associated with qgrp with group name";
                        }

                        leaf instance-id {
                            type uint16 {
                                range "1..65535";
                            }
                            description "Specifies the instance identifier.";
                        }

                        leaf mode {
                            type types-log:access-network;
                            description "Acc-policy is associated with qgrp with mode";
                        }

                    } // list qgrp-net-egress

                    list qgrp-card-acc {
                        key "slot-number fp-number group-name instance-id";
                        description "Enter the qgrp-card-acc list instance";

                        leaf slot-number {
                            type types-card:iom-card-slot;
                            description "Acc-policy is associated with qgrp with cardId";
                        }

                        leaf fp-number {
                            type uint32;
                            description "Acc-policy is associated with qgrp with fp number.";
                        }

                        leaf group-name {
                            type types-sros:named-item;
                            description "Acc-policy is associated with qgrp with group name";
                        }

                        leaf instance-id {
                            type uint32;
                            description "Acc-policy is associated with qgrp with instance Id.";
                        }

                        leaf mode {
                            type types-log:access-network;
                            description "Acc-policy is associated with qgrp with mode";
                        }

                    } // list qgrp-card-acc

                    list qgrp-card-net {
                        key "slot-number fp-number group-name instance-id";
                        description "Enter the qgrp-card-net list instance";

                        leaf slot-number {
                            type types-card:iom-card-slot;
                            description "Acc-policy is associated with qgrp with cardId";
                        }

                        leaf fp-number {
                            type uint32;
                            description "Acc-policy is associated with qgrp with fp number.";
                        }

                        leaf group-name {
                            type types-sros:named-item;
                            description "Acc-policy is associated with qgrp with group name";
                        }

                        leaf instance-id {
                            type uint32;
                            description "Acc-policy is associated with qgrp with instance Id.";
                        }

                        leaf mode {
                            type types-log:access-network;
                            description "Acc-policy is associated with qgrp with mode";
                        }

                    } // list qgrp-card-net

                    list saa {
                        key "owner test";
                        description "Enter the saa list instance";

                        leaf owner {
                            type types-sros:named-item;
                            description "Acc-policy is associated with saa with owner name";
                        }

                        leaf test {
                            type types-sros:named-item;
                            description "Acc-policy is associated with saa with test name";
                        }

                    } // list saa

                    list ldp-lsp-egress {
                        key "router-instance fec-prefix";
                        description "Enter the ldp-lsp-egress list instance";

                        leaf router-instance {
                            type types-sros:named-item-64;
                            description
                                "The administrative name for this virtual router.

                                 The router name must be unique among all virtual routers in the system.";
                        }

                        leaf fec-prefix {
                            type types-sros:ip-prefix;
                            description "Configure ip-prefix.";
                        }

                    } // list ldp-lsp-egress

                    list mpls-lsp-ingress {
                        key "router-instance sender lsp-name";
                        description "Enter the mpls-lsp-ingress list instance";

                        leaf router-instance {
                            type types-sros:named-item-64;
                            description
                                "The administrative name for this virtual router.

                                 The router name must be unique among all virtual routers in the system.";
                        }

                        leaf sender {
                            type types-sros:ip-address;
                            description "Sender-address of mpls-lsp-ingress";
                        }

                        leaf lsp-name {
                            type types-sros:named-item-64;
                            description "Lsp-name for mpls";
                        }

                    } // list mpls-lsp-ingress

                    list mpls-lsp-egress {
                        key "router-instance lsp-name";
                        description "Enter the mpls-lsp-egress list instance";

                        leaf router-instance {
                            type types-sros:named-item-64;
                            description
                                "The administrative name for this virtual router.

                                 The router name must be unique among all virtual routers in the system.";
                        }

                        leaf lsp-name {
                            type types-sros:named-item-64;
                            description "Lsp-name for mpls";
                        }

                    } // list mpls-lsp-egress

                    list mpls-srte-egress {
                        key "router-instance lsp-name";
                        description "Enter the mpls-srte-egress list instance";

                        leaf router-instance {
                            type types-sros:named-item-64;
                            description
                                "The administrative name for this virtual router.

                                 The router name must be unique among all virtual routers in the system.";
                        }

                        leaf lsp-name {
                            type types-sros:named-item-64;
                            description "Lsp-name for mpls";
                        }

                    } // list mpls-srte-egress

                    list video {
                        key "service-name interface-name";
                        description "Enter the video list instance";

                        leaf service-name {
                            type types-sros:named-item-64;
                            description "Acc-policy is associated with service-name";
                        }

                        leaf interface-name {
                            type types-sros:interface-name {
                                length "1..29";
                            }
                            description "[29 chars max] (must start with a letter).";
                        }

                    } // list video

                    list ethernet {
                        key "port-id";
                        description "Enter the ethernet list instance";

                        leaf port-id {
                            type types-sros:port;
                            description "The host port of the PXC.";
                        }

                    } // list ethernet

                    list oam-pm {
                        key "session-name measurment-interval-duration";
                        description "Enter the oam-pm list instance";

                        leaf session-name {
                            type types-sros:named-item;
                            description "Acc-policy is associated with oam pm with sesion name";
                        }

                        leaf measurment-interval-duration {
                            type types-log:measurment-interval-duration;
                            description "Acc-policy is associated with oam pm with measurment interval duration";
                        }

                    } // list oam-pm

                    list oam-service-activation-testhead {
                        key "service-test-name";
                        description "Enter the oam-service-activation-testhead list instance";

                        leaf service-test-name {
                            type leafref {
                                path "../../../../../test-oam/service-activation-testhead/service-test/test-name";
                            }
                            description
                                "Accounting policy that is associated with a Service
                                 Activation TestHead Service Test";
                        }

                    } // list oam-service-activation-testhead

                } // container associations

            } // list accounting-policy

            container log-events {
                description "Enter the log-events context";

                list adp {
                    key "event";
                    description "Enter the adp list instance";

                    leaf event {
                        type types-log:adp-events;
                        description "Log event as a trigger for one or more EHS handlers";
                    }

                    leaf event-id {
                        type types-log:log-event-id;
                        description
                            "Unique arbitrary identifier for indexing event type entries within
                             an event generator application.";
                    }

                    leaf-list parameters {
                        type types-sros:named-item;
                        description
                            "Indicates an event's specific parameters. These parameters can
                             be passed from a triggering event to its triggered EHS script.";
                    }

                    container statistics {
                        description "Enter the statistics context";

                        leaf count {
                            type yang:counter32;
                            description "Number of times an event of this type has been generated.";
                        }

                        leaf drop {
                            type yang:counter32;
                            description "Indicates the number of times an event of this type has been dropped.";
                        }

                    } // container statistics

                } // list adp

                list anysec {
                    key "event";
                    description "Enter the anysec list instance";

                    leaf event {
                        type types-log:anysec-events;
                        description "ANYSec module event";
                    }

                    leaf event-id {
                        type types-log:log-event-id;
                        description
                            "Unique arbitrary identifier for indexing event type entries within
                             an event generator application.";
                    }

                    leaf-list parameters {
                        type types-sros:named-item;
                        description
                            "Indicates an event's specific parameters. These parameters can
                             be passed from a triggering event to its triggered EHS script.";
                    }

                    container statistics {
                        description "Enter the statistics context";

                        leaf count {
                            type yang:counter32;
                            description "Number of times an event of this type has been generated.";
                        }

                        leaf drop {
                            type yang:counter32;
                            description "Indicates the number of times an event of this type has been dropped.";
                        }

                    } // container statistics

                } // list anysec

                list application-assurance {
                    key "event";
                    description "Enter the application-assurance list instance";

                    leaf event {
                        type types-log:application-assurance-events;
                        description "Log event as a trigger for one or more EHS handlers";
                    }

                    leaf event-id {
                        type types-log:log-event-id;
                        description
                            "Unique arbitrary identifier for indexing event type entries within
                             an event generator application.";
                    }

                    leaf-list parameters {
                        type types-sros:named-item;
                        description
                            "Indicates an event's specific parameters. These parameters can
                             be passed from a triggering event to its triggered EHS script.";
                    }

                    container statistics {
                        description "Enter the statistics context";

                        leaf count {
                            type yang:counter32;
                            description "Number of times an event of this type has been generated.";
                        }

                        leaf drop {
                            type yang:counter32;
                            description "Indicates the number of times an event of this type has been dropped.";
                        }

                    } // container statistics

                } // list application-assurance

                list aps {
                    key "event";
                    description "Enter the aps list instance";

                    leaf event {
                        type types-log:aps-events;
                        description "Log event as a trigger for one or more EHS handlers";
                    }

                    leaf event-id {
                        type types-log:log-event-id;
                        description
                            "Unique arbitrary identifier for indexing event type entries within
                             an event generator application.";
                    }

                    leaf-list parameters {
                        type types-sros:named-item;
                        description
                            "Indicates an event's specific parameters. These parameters can
                             be passed from a triggering event to its triggered EHS script.";
                    }

                    container statistics {
                        description "Enter the statistics context";

                        leaf count {
                            type yang:counter32;
                            description "Number of times an event of this type has been generated.";
                        }

                        leaf drop {
                            type yang:counter32;
                            description "Indicates the number of times an event of this type has been dropped.";
                        }

                    } // container statistics

                } // list aps

                list auto-prov {
                    key "event";
                    description "Enter the auto-prov list instance";

                    leaf event {
                        type types-log:auto-prov-events;
                        description "Log event as a trigger for one or more EHS handlers";
                    }

                    leaf event-id {
                        type types-log:log-event-id;
                        description
                            "Unique arbitrary identifier for indexing event type entries within
                             an event generator application.";
                    }

                    leaf-list parameters {
                        type types-sros:named-item;
                        description
                            "Indicates an event's specific parameters. These parameters can
                             be passed from a triggering event to its triggered EHS script.";
                    }

                    container statistics {
                        description "Enter the statistics context";

                        leaf count {
                            type yang:counter32;
                            description "Number of times an event of this type has been generated.";
                        }

                        leaf drop {
                            type yang:counter32;
                            description "Indicates the number of times an event of this type has been dropped.";
                        }

                    } // container statistics

                } // list auto-prov

                list bfd {
                    key "event";
                    description "Enter the bfd list instance";

                    leaf event {
                        type types-log:bfd-events;
                        description "Log event as a trigger for one or more EHS handlers";
                    }

                    leaf event-id {
                        type types-log:log-event-id;
                        description
                            "Unique arbitrary identifier for indexing event type entries within
                             an event generator application.";
                    }

                    leaf-list parameters {
                        type types-sros:named-item;
                        description
                            "Indicates an event's specific parameters. These parameters can
                             be passed from a triggering event to its triggered EHS script.";
                    }

                    container statistics {
                        description "Enter the statistics context";

                        leaf count {
                            type yang:counter32;
                            description "Number of times an event of this type has been generated.";
                        }

                        leaf drop {
                            type yang:counter32;
                            description "Indicates the number of times an event of this type has been dropped.";
                        }

                    } // container statistics

                } // list bfd

                list bgp {
                    key "event";
                    description "Enter the bgp list instance";

                    leaf event {
                        type types-log:bgp-events;
                        description "Log event as a trigger for one or more EHS handlers";
                    }

                    leaf event-id {
                        type types-log:log-event-id;
                        description
                            "Unique arbitrary identifier for indexing event type entries within
                             an event generator application.";
                    }

                    leaf-list parameters {
                        type types-sros:named-item;
                        description
                            "Indicates an event's specific parameters. These parameters can
                             be passed from a triggering event to its triggered EHS script.";
                    }

                    container statistics {
                        description "Enter the statistics context";

                        leaf count {
                            type yang:counter32;
                            description "Number of times an event of this type has been generated.";
                        }

                        leaf drop {
                            type yang:counter32;
                            description "Indicates the number of times an event of this type has been dropped.";
                        }

                    } // container statistics

                } // list bgp

                list bier {
                    key "event";
                    description "Enter the bier list instance";

                    leaf event {
                        type types-log:bier-events;
                        description "Log event as a trigger for one or more EHS handlers";
                    }

                    leaf event-id {
                        type types-log:log-event-id;
                        description
                            "Unique arbitrary identifier for indexing event type entries within
                             an event generator application.";
                    }

                    leaf-list parameters {
                        type types-sros:named-item;
                        description
                            "Indicates an event's specific parameters. These parameters can
                             be passed from a triggering event to its triggered EHS script.";
                    }

                    container statistics {
                        description "Enter the statistics context";

                        leaf count {
                            type yang:counter32;
                            description "Number of times an event of this type has been generated.";
                        }

                        leaf drop {
                            type yang:counter32;
                            description "Indicates the number of times an event of this type has been dropped.";
                        }

                    } // container statistics

                } // list bier

                list calltrace {
                    key "event";
                    description "Enter the calltrace list instance";

                    leaf event {
                        type types-log:calltrace-events;
                        description "Log event as a trigger for one or more EHS handlers";
                    }

                    leaf event-id {
                        type types-log:log-event-id;
                        description
                            "Unique arbitrary identifier for indexing event type entries within
                             an event generator application.";
                    }

                    leaf-list parameters {
                        type types-sros:named-item;
                        description
                            "Indicates an event's specific parameters. These parameters can
                             be passed from a triggering event to its triggered EHS script.";
                    }

                    container statistics {
                        description "Enter the statistics context";

                        leaf count {
                            type yang:counter32;
                            description "Number of times an event of this type has been generated.";
                        }

                        leaf drop {
                            type yang:counter32;
                            description "Indicates the number of times an event of this type has been dropped.";
                        }

                    } // container statistics

                } // list calltrace

                list cflowd {
                    key "event";
                    description "Enter the cflowd list instance";

                    leaf event {
                        type types-log:cflowd-events;
                        description "Log event as a trigger for one or more EHS handlers";
                    }

                    leaf event-id {
                        type types-log:log-event-id;
                        description
                            "Unique arbitrary identifier for indexing event type entries within
                             an event generator application.";
                    }

                    leaf-list parameters {
                        type types-sros:named-item;
                        description
                            "Indicates an event's specific parameters. These parameters can
                             be passed from a triggering event to its triggered EHS script.";
                    }

                    container statistics {
                        description "Enter the statistics context";

                        leaf count {
                            type yang:counter32;
                            description "Number of times an event of this type has been generated.";
                        }

                        leaf drop {
                            type yang:counter32;
                            description "Indicates the number of times an event of this type has been dropped.";
                        }

                    } // container statistics

                } // list cflowd

                list chassis {
                    key "event";
                    description "Enter the chassis list instance";

                    leaf event {
                        type types-log:chassis-events;
                        description "Log event as a trigger for one or more EHS handlers";
                    }

                    leaf event-id {
                        type types-log:log-event-id;
                        description
                            "Unique arbitrary identifier for indexing event type entries within
                             an event generator application.";
                    }

                    leaf-list parameters {
                        type types-sros:named-item;
                        description
                            "Indicates an event's specific parameters. These parameters can
                             be passed from a triggering event to its triggered EHS script.";
                    }

                    container statistics {
                        description "Enter the statistics context";

                        leaf count {
                            type yang:counter32;
                            description "Number of times an event of this type has been generated.";
                        }

                        leaf drop {
                            type yang:counter32;
                            description "Indicates the number of times an event of this type has been dropped.";
                        }

                    } // container statistics

                } // list chassis

                list debug {
                    key "event";
                    description "Enter the debug list instance";

                    leaf event {
                        type types-log:debug-events;
                        description "Log event as a trigger for one or more EHS handlers";
                    }

                    leaf event-id {
                        type types-log:log-event-id;
                        description
                            "Unique arbitrary identifier for indexing event type entries within
                             an event generator application.";
                    }

                    leaf-list parameters {
                        type types-sros:named-item;
                        description
                            "Indicates an event's specific parameters. These parameters can
                             be passed from a triggering event to its triggered EHS script.";
                    }

                    container statistics {
                        description "Enter the statistics context";

                        leaf count {
                            type yang:counter32;
                            description "Number of times an event of this type has been generated.";
                        }

                        leaf drop {
                            type yang:counter32;
                            description "Indicates the number of times an event of this type has been dropped.";
                        }

                    } // container statistics

                } // list debug

                list dhcp {
                    key "event";
                    description "Enter the dhcp list instance";

                    leaf event {
                        type types-log:dhcp-events;
                        description "Log event as a trigger for one or more EHS handlers";
                    }

                    leaf event-id {
                        type types-log:log-event-id;
                        description
                            "Unique arbitrary identifier for indexing event type entries within
                             an event generator application.";
                    }

                    leaf-list parameters {
                        type types-sros:named-item;
                        description
                            "Indicates an event's specific parameters. These parameters can
                             be passed from a triggering event to its triggered EHS script.";
                    }

                    container statistics {
                        description "Enter the statistics context";

                        leaf count {
                            type yang:counter32;
                            description "Number of times an event of this type has been generated.";
                        }

                        leaf drop {
                            type yang:counter32;
                            description "Indicates the number of times an event of this type has been dropped.";
                        }

                    } // container statistics

                } // list dhcp

                list dhcps {
                    key "event";
                    description "Enter the dhcps list instance";

                    leaf event {
                        type types-log:dhcps-events;
                        description "Log event as a trigger for one or more EHS handlers";
                    }

                    leaf event-id {
                        type types-log:log-event-id;
                        description
                            "Unique arbitrary identifier for indexing event type entries within
                             an event generator application.";
                    }

                    leaf-list parameters {
                        type types-sros:named-item;
                        description
                            "Indicates an event's specific parameters. These parameters can
                             be passed from a triggering event to its triggered EHS script.";
                    }

                    container statistics {
                        description "Enter the statistics context";

                        leaf count {
                            type yang:counter32;
                            description "Number of times an event of this type has been generated.";
                        }

                        leaf drop {
                            type yang:counter32;
                            description "Indicates the number of times an event of this type has been dropped.";
                        }

                    } // container statistics

                } // list dhcps

                list diameter {
                    key "event";
                    description "Enter the diameter list instance";

                    leaf event {
                        type types-log:diameter-events;
                        description "Log event as a trigger for one or more EHS handlers";
                    }

                    leaf event-id {
                        type types-log:log-event-id;
                        description
                            "Unique arbitrary identifier for indexing event type entries within
                             an event generator application.";
                    }

                    leaf-list parameters {
                        type types-sros:named-item;
                        description
                            "Indicates an event's specific parameters. These parameters can
                             be passed from a triggering event to its triggered EHS script.";
                    }

                    container statistics {
                        description "Enter the statistics context";

                        leaf count {
                            type yang:counter32;
                            description "Number of times an event of this type has been generated.";
                        }

                        leaf drop {
                            type yang:counter32;
                            description "Indicates the number of times an event of this type has been dropped.";
                        }

                    } // container statistics

                } // list diameter

                list dot1x {
                    key "event";
                    description "Enter the dot1x list instance";

                    leaf event {
                        type types-log:dot1x-events;
                        description "Events for dynsvc module.";
                    }

                    leaf event-id {
                        type types-log:log-event-id;
                        description
                            "Unique arbitrary identifier for indexing event type entries within
                             an event generator application.";
                    }

                    leaf-list parameters {
                        type types-sros:named-item;
                        description
                            "Indicates an event's specific parameters. These parameters can
                             be passed from a triggering event to its triggered EHS script.";
                    }

                    container statistics {
                        description "Enter the statistics context";

                        leaf count {
                            type yang:counter32;
                            description "Number of times an event of this type has been generated.";
                        }

                        leaf drop {
                            type yang:counter32;
                            description "Indicates the number of times an event of this type has been dropped.";
                        }

                    } // container statistics

                } // list dot1x

                list dynsvc {
                    key "event";
                    description "Enter the dynsvc list instance";

                    leaf event {
                        type types-log:dynsvc-events;
                        description "Log event as a trigger for one or more EHS handlers";
                    }

                    leaf event-id {
                        type types-log:log-event-id;
                        description
                            "Unique arbitrary identifier for indexing event type entries within
                             an event generator application.";
                    }

                    leaf-list parameters {
                        type types-sros:named-item;
                        description
                            "Indicates an event's specific parameters. These parameters can
                             be passed from a triggering event to its triggered EHS script.";
                    }

                    container statistics {
                        description "Enter the statistics context";

                        leaf count {
                            type yang:counter32;
                            description "Number of times an event of this type has been generated.";
                        }

                        leaf drop {
                            type yang:counter32;
                            description "Indicates the number of times an event of this type has been dropped.";
                        }

                    } // container statistics

                } // list dynsvc

                list efm-oam {
                    key "event";
                    description "Enter the efm-oam list instance";

                    leaf event {
                        type types-log:efm-oam-events;
                        description "Log event as a trigger for one or more EHS handlers";
                    }

                    leaf event-id {
                        type types-log:log-event-id;
                        description
                            "Unique arbitrary identifier for indexing event type entries within
                             an event generator application.";
                    }

                    leaf-list parameters {
                        type types-sros:named-item;
                        description
                            "Indicates an event's specific parameters. These parameters can
                             be passed from a triggering event to its triggered EHS script.";
                    }

                    container statistics {
                        description "Enter the statistics context";

                        leaf count {
                            type yang:counter32;
                            description "Number of times an event of this type has been generated.";
                        }

                        leaf drop {
                            type yang:counter32;
                            description "Indicates the number of times an event of this type has been dropped.";
                        }

                    } // container statistics

                } // list efm-oam

                list elmi {
                    key "event";
                    description "Enter the elmi list instance";

                    leaf event {
                        type types-log:elmi-events;
                        description "Log event as a trigger for one or more EHS handlers";
                    }

                    leaf event-id {
                        type types-log:log-event-id;
                        description
                            "Unique arbitrary identifier for indexing event type entries within
                             an event generator application.";
                    }

                    leaf-list parameters {
                        type types-sros:named-item;
                        description
                            "Indicates an event's specific parameters. These parameters can
                             be passed from a triggering event to its triggered EHS script.";
                    }

                    container statistics {
                        description "Enter the statistics context";

                        leaf count {
                            type yang:counter32;
                            description "Number of times an event of this type has been generated.";
                        }

                        leaf drop {
                            type yang:counter32;
                            description "Indicates the number of times an event of this type has been dropped.";
                        }

                    } // container statistics

                } // list elmi

                list ering {
                    key "event";
                    description "Enter the ering list instance";

                    leaf event {
                        type types-log:ethring-events;
                        description "Log event as a trigger for one or more EHS handlers";
                    }

                    leaf event-id {
                        type types-log:log-event-id;
                        description
                            "Unique arbitrary identifier for indexing event type entries within
                             an event generator application.";
                    }

                    leaf-list parameters {
                        type types-sros:named-item;
                        description
                            "Indicates an event's specific parameters. These parameters can
                             be passed from a triggering event to its triggered EHS script.";
                    }

                    container statistics {
                        description "Enter the statistics context";

                        leaf count {
                            type yang:counter32;
                            description "Number of times an event of this type has been generated.";
                        }

                        leaf drop {
                            type yang:counter32;
                            description "Indicates the number of times an event of this type has been dropped.";
                        }

                    } // container statistics

                } // list ering

                list eth-cfm {
                    key "event";
                    description "Enter the eth-cfm list instance";

                    leaf event {
                        type types-log:ethcfm-events;
                        description "Log event as a trigger for one or more EHS handlers";
                    }

                    leaf event-id {
                        type types-log:log-event-id;
                        description
                            "Unique arbitrary identifier for indexing event type entries within
                             an event generator application.";
                    }

                    leaf-list parameters {
                        type types-sros:named-item;
                        description
                            "Indicates an event's specific parameters. These parameters can
                             be passed from a triggering event to its triggered EHS script.";
                    }

                    container statistics {
                        description "Enter the statistics context";

                        leaf count {
                            type yang:counter32;
                            description "Number of times an event of this type has been generated.";
                        }

                        leaf drop {
                            type yang:counter32;
                            description "Indicates the number of times an event of this type has been dropped.";
                        }

                    } // container statistics

                } // list eth-cfm

                list etun {
                    key "event";
                    description "Enter the etun list instance";

                    leaf event {
                        type types-log:etun-events;
                        description "Log event as a trigger for one or more EHS handlers";
                    }

                    leaf event-id {
                        type types-log:log-event-id;
                        description
                            "Unique arbitrary identifier for indexing event type entries within
                             an event generator application.";
                    }

                    leaf-list parameters {
                        type types-sros:named-item;
                        description
                            "Indicates an event's specific parameters. These parameters can
                             be passed from a triggering event to its triggered EHS script.";
                    }

                    container statistics {
                        description "Enter the statistics context";

                        leaf count {
                            type yang:counter32;
                            description "Number of times an event of this type has been generated.";
                        }

                        leaf drop {
                            type yang:counter32;
                            description "Indicates the number of times an event of this type has been dropped.";
                        }

                    } // container statistics

                } // list etun

                list filter {
                    key "event";
                    description "Enter the filter list instance";

                    leaf event {
                        type types-log:filter-events;
                        description "Log event as a trigger for one or more EHS handlers";
                    }

                    leaf event-id {
                        type types-log:log-event-id;
                        description
                            "Unique arbitrary identifier for indexing event type entries within
                             an event generator application.";
                    }

                    leaf-list parameters {
                        type types-sros:named-item;
                        description
                            "Indicates an event's specific parameters. These parameters can
                             be passed from a triggering event to its triggered EHS script.";
                    }

                    container statistics {
                        description "Enter the statistics context";

                        leaf count {
                            type yang:counter32;
                            description "Number of times an event of this type has been generated.";
                        }

                        leaf drop {
                            type yang:counter32;
                            description "Indicates the number of times an event of this type has been dropped.";
                        }

                    } // container statistics

                } // list filter

                list gsmp {
                    key "event";
                    description "Enter the gsmp list instance";

                    leaf event {
                        type types-log:gsmp-events;
                        description "Log event as a trigger for one or more EHS handlers";
                    }

                    leaf event-id {
                        type types-log:log-event-id;
                        description
                            "Unique arbitrary identifier for indexing event type entries within
                             an event generator application.";
                    }

                    leaf-list parameters {
                        type types-sros:named-item;
                        description
                            "Indicates an event's specific parameters. These parameters can
                             be passed from a triggering event to its triggered EHS script.";
                    }

                    container statistics {
                        description "Enter the statistics context";

                        leaf count {
                            type yang:counter32;
                            description "Number of times an event of this type has been generated.";
                        }

                        leaf drop {
                            type yang:counter32;
                            description "Indicates the number of times an event of this type has been dropped.";
                        }

                    } // container statistics

                } // list gsmp

                list igmp {
                    key "event";
                    description "Enter the igmp list instance";

                    leaf event {
                        type types-log:igmp-events;
                        description "Log event as a trigger for one or more EHS handlers";
                    }

                    leaf event-id {
                        type types-log:log-event-id;
                        description
                            "Unique arbitrary identifier for indexing event type entries within
                             an event generator application.";
                    }

                    leaf-list parameters {
                        type types-sros:named-item;
                        description
                            "Indicates an event's specific parameters. These parameters can
                             be passed from a triggering event to its triggered EHS script.";
                    }

                    container statistics {
                        description "Enter the statistics context";

                        leaf count {
                            type yang:counter32;
                            description "Number of times an event of this type has been generated.";
                        }

                        leaf drop {
                            type yang:counter32;
                            description "Indicates the number of times an event of this type has been dropped.";
                        }

                    } // container statistics

                } // list igmp

                list igmp-snooping {
                    key "event";
                    description "Enter the igmp-snooping list instance";

                    leaf event {
                        type types-log:igmp-snooping-events;
                        description "Log event as a trigger for one or more EHS handlers";
                    }

                    leaf event-id {
                        type types-log:log-event-id;
                        description
                            "Unique arbitrary identifier for indexing event type entries within
                             an event generator application.";
                    }

                    leaf-list parameters {
                        type types-sros:named-item;
                        description
                            "Indicates an event's specific parameters. These parameters can
                             be passed from a triggering event to its triggered EHS script.";
                    }

                    container statistics {
                        description "Enter the statistics context";

                        leaf count {
                            type yang:counter32;
                            description "Number of times an event of this type has been generated.";
                        }

                        leaf drop {
                            type yang:counter32;
                            description "Indicates the number of times an event of this type has been dropped.";
                        }

                    } // container statistics

                } // list igmp-snooping

                list ip {
                    key "event";
                    description "Enter the ip list instance";

                    leaf event {
                        type types-log:ip-events;
                        description "Log event as a trigger for one or more EHS handlers";
                    }

                    leaf event-id {
                        type types-log:log-event-id;
                        description
                            "Unique arbitrary identifier for indexing event type entries within
                             an event generator application.";
                    }

                    leaf-list parameters {
                        type types-sros:named-item;
                        description
                            "Indicates an event's specific parameters. These parameters can
                             be passed from a triggering event to its triggered EHS script.";
                    }

                    container statistics {
                        description "Enter the statistics context";

                        leaf count {
                            type yang:counter32;
                            description "Number of times an event of this type has been generated.";
                        }

                        leaf drop {
                            type yang:counter32;
                            description "Indicates the number of times an event of this type has been dropped.";
                        }

                    } // container statistics

                } // list ip

                list ipsec {
                    key "event";
                    description "Enter the ipsec list instance";

                    leaf event {
                        type types-log:ipsec-events;
                        description "Log event as a trigger for one or more EHS handlers";
                    }

                    leaf event-id {
                        type types-log:log-event-id;
                        description
                            "Unique arbitrary identifier for indexing event type entries within
                             an event generator application.";
                    }

                    leaf-list parameters {
                        type types-sros:named-item;
                        description
                            "Indicates an event's specific parameters. These parameters can
                             be passed from a triggering event to its triggered EHS script.";
                    }

                    container statistics {
                        description "Enter the statistics context";

                        leaf count {
                            type yang:counter32;
                            description "Number of times an event of this type has been generated.";
                        }

                        leaf drop {
                            type yang:counter32;
                            description "Indicates the number of times an event of this type has been dropped.";
                        }

                    } // container statistics

                } // list ipsec

                list isis {
                    key "event";
                    description "Enter the isis list instance";

                    leaf event {
                        type types-log:isis-events;
                        description "Log event as a trigger for one or more EHS handlers";
                    }

                    leaf event-id {
                        type types-log:log-event-id;
                        description
                            "Unique arbitrary identifier for indexing event type entries within
                             an event generator application.";
                    }

                    leaf-list parameters {
                        type types-sros:named-item;
                        description
                            "Indicates an event's specific parameters. These parameters can
                             be passed from a triggering event to its triggered EHS script.";
                    }

                    container statistics {
                        description "Enter the statistics context";

                        leaf count {
                            type yang:counter32;
                            description "Number of times an event of this type has been generated.";
                        }

                        leaf drop {
                            type yang:counter32;
                            description "Indicates the number of times an event of this type has been dropped.";
                        }

                    } // container statistics

                } // list isis

                list l2tp {
                    key "event";
                    description "Enter the l2tp list instance";

                    leaf event {
                        type types-log:l2tp-events;
                        description "Log event as a trigger for one or more EHS handlers";
                    }

                    leaf event-id {
                        type types-log:log-event-id;
                        description
                            "Unique arbitrary identifier for indexing event type entries within
                             an event generator application.";
                    }

                    leaf-list parameters {
                        type types-sros:named-item;
                        description
                            "Indicates an event's specific parameters. These parameters can
                             be passed from a triggering event to its triggered EHS script.";
                    }

                    container statistics {
                        description "Enter the statistics context";

                        leaf count {
                            type yang:counter32;
                            description "Number of times an event of this type has been generated.";
                        }

                        leaf drop {
                            type yang:counter32;
                            description "Indicates the number of times an event of this type has been dropped.";
                        }

                    } // container statistics

                } // list l2tp

                list lag {
                    key "event";
                    description "Enter the lag list instance";

                    leaf event {
                        type types-log:lag-events;
                        description "Log event as a trigger for one or more EHS handlers";
                    }

                    leaf event-id {
                        type types-log:log-event-id;
                        description
                            "Unique arbitrary identifier for indexing event type entries within
                             an event generator application.";
                    }

                    leaf-list parameters {
                        type types-sros:named-item;
                        description
                            "Indicates an event's specific parameters. These parameters can
                             be passed from a triggering event to its triggered EHS script.";
                    }

                    container statistics {
                        description "Enter the statistics context";

                        leaf count {
                            type yang:counter32;
                            description "Number of times an event of this type has been generated.";
                        }

                        leaf drop {
                            type yang:counter32;
                            description "Indicates the number of times an event of this type has been dropped.";
                        }

                    } // container statistics

                } // list lag

                list ldap {
                    key "event";
                    description "Enter the ldap list instance";

                    leaf event {
                        type types-log:ldap-events;
                        description "Log event as a trigger for one or more EHS handlers";
                    }

                    leaf event-id {
                        type types-log:log-event-id;
                        description
                            "Unique arbitrary identifier for indexing event type entries within
                             an event generator application.";
                    }

                    leaf-list parameters {
                        type types-sros:named-item;
                        description
                            "Indicates an event's specific parameters. These parameters can
                             be passed from a triggering event to its triggered EHS script.";
                    }

                    container statistics {
                        description "Enter the statistics context";

                        leaf count {
                            type yang:counter32;
                            description "Number of times an event of this type has been generated.";
                        }

                        leaf drop {
                            type yang:counter32;
                            description "Indicates the number of times an event of this type has been dropped.";
                        }

                    } // container statistics

                } // list ldap

                list ldp {
                    key "event";
                    description "Enter the ldp list instance";

                    leaf event {
                        type types-log:ldp-events;
                        description "Log event as a trigger for one or more EHS handlers";
                    }

                    leaf event-id {
                        type types-log:log-event-id;
                        description
                            "Unique arbitrary identifier for indexing event type entries within
                             an event generator application.";
                    }

                    leaf-list parameters {
                        type types-sros:named-item;
                        description
                            "Indicates an event's specific parameters. These parameters can
                             be passed from a triggering event to its triggered EHS script.";
                    }

                    container statistics {
                        description "Enter the statistics context";

                        leaf count {
                            type yang:counter32;
                            description "Number of times an event of this type has been generated.";
                        }

                        leaf drop {
                            type yang:counter32;
                            description "Indicates the number of times an event of this type has been dropped.";
                        }

                    } // container statistics

                } // list ldp

                list li {
                    key "event";
                    description "Enter the li list instance";

                    leaf event {
                        type types-log:li-events;
                        description "Log event as a trigger for one or more EHS handlers";
                    }

                    leaf event-id {
                        type types-log:log-event-id;
                        description
                            "Unique arbitrary identifier for indexing event type entries within
                             an event generator application.";
                    }

                    leaf-list parameters {
                        type types-sros:named-item;
                        description
                            "Indicates an event's specific parameters. These parameters can
                             be passed from a triggering event to its triggered EHS script.";
                    }

                    container statistics {
                        description "Enter the statistics context";

                        leaf count {
                            type yang:counter32;
                            description "Number of times an event of this type has been generated.";
                        }

                        leaf drop {
                            type yang:counter32;
                            description "Indicates the number of times an event of this type has been dropped.";
                        }

                    } // container statistics

                } // list li

                list lldp {
                    key "event";
                    description "Enter the lldp list instance";

                    leaf event {
                        type types-log:lldp-events;
                        description "Log event as a trigger for one or more EHS handlers";
                    }

                    leaf event-id {
                        type types-log:log-event-id;
                        description
                            "Unique arbitrary identifier for indexing event type entries within
                             an event generator application.";
                    }

                    leaf-list parameters {
                        type types-sros:named-item;
                        description
                            "Indicates an event's specific parameters. These parameters can
                             be passed from a triggering event to its triggered EHS script.";
                    }

                    container statistics {
                        description "Enter the statistics context";

                        leaf count {
                            type yang:counter32;
                            description "Number of times an event of this type has been generated.";
                        }

                        leaf drop {
                            type yang:counter32;
                            description "Indicates the number of times an event of this type has been dropped.";
                        }

                    } // container statistics

                } // list lldp

                list logger {
                    key "event";
                    description "Enter the logger list instance";

                    leaf event {
                        type types-log:logger-events;
                        description "Log event as a trigger for one or more EHS handlers";
                    }

                    leaf event-id {
                        type types-log:log-event-id;
                        description
                            "Unique arbitrary identifier for indexing event type entries within
                             an event generator application.";
                    }

                    leaf-list parameters {
                        type types-sros:named-item;
                        description
                            "Indicates an event's specific parameters. These parameters can
                             be passed from a triggering event to its triggered EHS script.";
                    }

                    container statistics {
                        description "Enter the statistics context";

                        leaf count {
                            type yang:counter32;
                            description "Number of times an event of this type has been generated.";
                        }

                        leaf drop {
                            type yang:counter32;
                            description "Indicates the number of times an event of this type has been dropped.";
                        }

                    } // container statistics

                } // list logger

                list macsec {
                    key "event";
                    description "Enter the macsec list instance";

                    leaf event {
                        type types-log:macsec-events;
                        description "Log event as a trigger for one or more EHS handlers";
                    }

                    leaf event-id {
                        type types-log:log-event-id;
                        description
                            "Unique arbitrary identifier for indexing event type entries within
                             an event generator application.";
                    }

                    leaf-list parameters {
                        type types-sros:named-item;
                        description
                            "Indicates an event's specific parameters. These parameters can
                             be passed from a triggering event to its triggered EHS script.";
                    }

                    container statistics {
                        description "Enter the statistics context";

                        leaf count {
                            type yang:counter32;
                            description "Number of times an event of this type has been generated.";
                        }

                        leaf drop {
                            type yang:counter32;
                            description "Indicates the number of times an event of this type has been dropped.";
                        }

                    } // container statistics

                } // list macsec

                list mcpath {
                    key "event";
                    description "Enter the mcpath list instance";

                    leaf event {
                        type types-log:mcpath-events;
                        description "Log event as a trigger for one or more EHS handlers";
                    }

                    leaf event-id {
                        type types-log:log-event-id;
                        description
                            "Unique arbitrary identifier for indexing event type entries within
                             an event generator application.";
                    }

                    leaf-list parameters {
                        type types-sros:named-item;
                        description
                            "Indicates an event's specific parameters. These parameters can
                             be passed from a triggering event to its triggered EHS script.";
                    }

                    container statistics {
                        description "Enter the statistics context";

                        leaf count {
                            type yang:counter32;
                            description "Number of times an event of this type has been generated.";
                        }

                        leaf drop {
                            type yang:counter32;
                            description "Indicates the number of times an event of this type has been dropped.";
                        }

                    } // container statistics

                } // list mcpath

                list mc-redundancy {
                    key "event";
                    description "Enter the mc-redundancy list instance";

                    leaf event {
                        type types-log:mc-redundancy-events;
                        description "Log event as a trigger for one or more EHS handlers";
                    }

                    leaf event-id {
                        type types-log:log-event-id;
                        description
                            "Unique arbitrary identifier for indexing event type entries within
                             an event generator application.";
                    }

                    leaf-list parameters {
                        type types-sros:named-item;
                        description
                            "Indicates an event's specific parameters. These parameters can
                             be passed from a triggering event to its triggered EHS script.";
                    }

                    container statistics {
                        description "Enter the statistics context";

                        leaf count {
                            type yang:counter32;
                            description "Number of times an event of this type has been generated.";
                        }

                        leaf drop {
                            type yang:counter32;
                            description "Indicates the number of times an event of this type has been dropped.";
                        }

                    } // container statistics

                } // list mc-redundancy

                list mgmt-core {
                    key "event";
                    description "Enter the mgmt-core list instance";

                    leaf event {
                        type types-log:mgmt-core-events;
                        description "Log event as a trigger for one or more EHS handlers";
                    }

                    leaf event-id {
                        type types-log:log-event-id;
                        description
                            "Unique arbitrary identifier for indexing event type entries within
                             an event generator application.";
                    }

                    leaf-list parameters {
                        type types-sros:named-item;
                        description
                            "Indicates an event's specific parameters. These parameters can
                             be passed from a triggering event to its triggered EHS script.";
                    }

                    container statistics {
                        description "Enter the statistics context";

                        leaf count {
                            type yang:counter32;
                            description "Number of times an event of this type has been generated.";
                        }

                        leaf drop {
                            type yang:counter32;
                            description "Indicates the number of times an event of this type has been dropped.";
                        }

                    } // container statistics

                } // list mgmt-core

                list mirror {
                    key "event";
                    description "Enter the mirror list instance";

                    leaf event {
                        type types-log:mirror-events;
                        description "Log event as a trigger for one or more EHS handlers";
                    }

                    leaf event-id {
                        type types-log:log-event-id;
                        description
                            "Unique arbitrary identifier for indexing event type entries within
                             an event generator application.";
                    }

                    leaf-list parameters {
                        type types-sros:named-item;
                        description
                            "Indicates an event's specific parameters. These parameters can
                             be passed from a triggering event to its triggered EHS script.";
                    }

                    container statistics {
                        description "Enter the statistics context";

                        leaf count {
                            type yang:counter32;
                            description "Number of times an event of this type has been generated.";
                        }

                        leaf drop {
                            type yang:counter32;
                            description "Indicates the number of times an event of this type has been dropped.";
                        }

                    } // container statistics

                } // list mirror

                list mld {
                    key "event";
                    description "Enter the mld list instance";

                    leaf event {
                        type types-log:mld-events;
                        description "Log event as a trigger for one or more EHS handlers";
                    }

                    leaf event-id {
                        type types-log:log-event-id;
                        description
                            "Unique arbitrary identifier for indexing event type entries within
                             an event generator application.";
                    }

                    leaf-list parameters {
                        type types-sros:named-item;
                        description
                            "Indicates an event's specific parameters. These parameters can
                             be passed from a triggering event to its triggered EHS script.";
                    }

                    container statistics {
                        description "Enter the statistics context";

                        leaf count {
                            type yang:counter32;
                            description "Number of times an event of this type has been generated.";
                        }

                        leaf drop {
                            type yang:counter32;
                            description "Indicates the number of times an event of this type has been dropped.";
                        }

                    } // container statistics

                } // list mld

                list mld-snooping {
                    key "event";
                    description "Enter the mld-snooping list instance";

                    leaf event {
                        type types-log:mld-snooping-events;
                        description "Log event as a trigger for one or more EHS handlers";
                    }

                    leaf event-id {
                        type types-log:log-event-id;
                        description
                            "Unique arbitrary identifier for indexing event type entries within
                             an event generator application.";
                    }

                    leaf-list parameters {
                        type types-sros:named-item;
                        description
                            "Indicates an event's specific parameters. These parameters can
                             be passed from a triggering event to its triggered EHS script.";
                    }

                    container statistics {
                        description "Enter the statistics context";

                        leaf count {
                            type yang:counter32;
                            description "Number of times an event of this type has been generated.";
                        }

                        leaf drop {
                            type yang:counter32;
                            description "Indicates the number of times an event of this type has been dropped.";
                        }

                    } // container statistics

                } // list mld-snooping

                list mpls {
                    key "event";
                    description "Enter the mpls list instance";

                    leaf event {
                        type types-log:mpls-events;
                        description "Log event as a trigger for one or more EHS handlers";
                    }

                    leaf event-id {
                        type types-log:log-event-id;
                        description
                            "Unique arbitrary identifier for indexing event type entries within
                             an event generator application.";
                    }

                    leaf-list parameters {
                        type types-sros:named-item;
                        description
                            "Indicates an event's specific parameters. These parameters can
                             be passed from a triggering event to its triggered EHS script.";
                    }

                    container statistics {
                        description "Enter the statistics context";

                        leaf count {
                            type yang:counter32;
                            description "Number of times an event of this type has been generated.";
                        }

                        leaf drop {
                            type yang:counter32;
                            description "Indicates the number of times an event of this type has been dropped.";
                        }

                    } // container statistics

                } // list mpls

                list mpls-tp {
                    key "event";
                    description "Enter the mpls-tp list instance";

                    leaf event {
                        type types-log:mpls-tp-events;
                        description "Log event as a trigger for one or more EHS handlers";
                    }

                    leaf event-id {
                        type types-log:log-event-id;
                        description
                            "Unique arbitrary identifier for indexing event type entries within
                             an event generator application.";
                    }

                    leaf-list parameters {
                        type types-sros:named-item;
                        description
                            "Indicates an event's specific parameters. These parameters can
                             be passed from a triggering event to its triggered EHS script.";
                    }

                    container statistics {
                        description "Enter the statistics context";

                        leaf count {
                            type yang:counter32;
                            description "Number of times an event of this type has been generated.";
                        }

                        leaf drop {
                            type yang:counter32;
                            description "Indicates the number of times an event of this type has been dropped.";
                        }

                    } // container statistics

                } // list mpls-tp

                list msdp {
                    key "event";
                    description "Enter the msdp list instance";

                    leaf event {
                        type types-log:msdp-events;
                        description "Log event as a trigger for one or more EHS handlers";
                    }

                    leaf event-id {
                        type types-log:log-event-id;
                        description
                            "Unique arbitrary identifier for indexing event type entries within
                             an event generator application.";
                    }

                    leaf-list parameters {
                        type types-sros:named-item;
                        description
                            "Indicates an event's specific parameters. These parameters can
                             be passed from a triggering event to its triggered EHS script.";
                    }

                    container statistics {
                        description "Enter the statistics context";

                        leaf count {
                            type yang:counter32;
                            description "Number of times an event of this type has been generated.";
                        }

                        leaf drop {
                            type yang:counter32;
                            description "Indicates the number of times an event of this type has been dropped.";
                        }

                    } // container statistics

                } // list msdp

                list nat {
                    key "event";
                    description "Enter the nat list instance";

                    leaf event {
                        type types-log:nat-events;
                        description "Log event as a trigger for one or more EHS handlers";
                    }

                    leaf event-id {
                        type types-log:log-event-id;
                        description
                            "Unique arbitrary identifier for indexing event type entries within
                             an event generator application.";
                    }

                    leaf-list parameters {
                        type types-sros:named-item;
                        description
                            "Indicates an event's specific parameters. These parameters can
                             be passed from a triggering event to its triggered EHS script.";
                    }

                    container statistics {
                        description "Enter the statistics context";

                        leaf count {
                            type yang:counter32;
                            description "Number of times an event of this type has been generated.";
                        }

                        leaf drop {
                            type yang:counter32;
                            description "Indicates the number of times an event of this type has been dropped.";
                        }

                    } // container statistics

                } // list nat

                list ntp {
                    key "event";
                    description "Enter the ntp list instance";

                    leaf event {
                        type types-log:ntp-events;
                        description "Log event as a trigger for one or more EHS handlers";
                    }

                    leaf event-id {
                        type types-log:log-event-id;
                        description
                            "Unique arbitrary identifier for indexing event type entries within
                             an event generator application.";
                    }

                    leaf-list parameters {
                        type types-sros:named-item;
                        description
                            "Indicates an event's specific parameters. These parameters can
                             be passed from a triggering event to its triggered EHS script.";
                    }

                    container statistics {
                        description "Enter the statistics context";

                        leaf count {
                            type yang:counter32;
                            description "Number of times an event of this type has been generated.";
                        }

                        leaf drop {
                            type yang:counter32;
                            description "Indicates the number of times an event of this type has been dropped.";
                        }

                    } // container statistics

                } // list ntp

                list oam {
                    key "event";
                    description "Enter the oam list instance";

                    leaf event {
                        type types-log:oam-events;
                        description "Log event as a trigger for one or more EHS handlers";
                    }

                    leaf event-id {
                        type types-log:log-event-id;
                        description
                            "Unique arbitrary identifier for indexing event type entries within
                             an event generator application.";
                    }

                    leaf-list parameters {
                        type types-sros:named-item;
                        description
                            "Indicates an event's specific parameters. These parameters can
                             be passed from a triggering event to its triggered EHS script.";
                    }

                    container statistics {
                        description "Enter the statistics context";

                        leaf count {
                            type yang:counter32;
                            description "Number of times an event of this type has been generated.";
                        }

                        leaf drop {
                            type yang:counter32;
                            description "Indicates the number of times an event of this type has been dropped.";
                        }

                    } // container statistics

                } // list oam

                list openflow {
                    key "event";
                    description "Enter the openflow list instance";

                    leaf event {
                        type types-log:openflow-events;
                        description "Log event as a trigger for one or more EHS handlers";
                    }

                    leaf event-id {
                        type types-log:log-event-id;
                        description
                            "Unique arbitrary identifier for indexing event type entries within
                             an event generator application.";
                    }

                    leaf-list parameters {
                        type types-sros:named-item;
                        description
                            "Indicates an event's specific parameters. These parameters can
                             be passed from a triggering event to its triggered EHS script.";
                    }

                    container statistics {
                        description "Enter the statistics context";

                        leaf count {
                            type yang:counter32;
                            description "Number of times an event of this type has been generated.";
                        }

                        leaf drop {
                            type yang:counter32;
                            description "Indicates the number of times an event of this type has been dropped.";
                        }

                    } // container statistics

                } // list openflow

                list ospf {
                    key "event";
                    description "Enter the ospf list instance";

                    leaf event {
                        type types-log:ospf-events;
                        description "Log event as a trigger for one or more EHS handlers";
                    }

                    leaf event-id {
                        type types-log:log-event-id;
                        description
                            "Unique arbitrary identifier for indexing event type entries within
                             an event generator application.";
                    }

                    leaf-list parameters {
                        type types-sros:named-item;
                        description
                            "Indicates an event's specific parameters. These parameters can
                             be passed from a triggering event to its triggered EHS script.";
                    }

                    container statistics {
                        description "Enter the statistics context";

                        leaf count {
                            type yang:counter32;
                            description "Number of times an event of this type has been generated.";
                        }

                        leaf drop {
                            type yang:counter32;
                            description "Indicates the number of times an event of this type has been dropped.";
                        }

                    } // container statistics

                } // list ospf

                list pcap {
                    key "event";
                    description "Enter the pcap list instance";

                    leaf event {
                        type types-log:pcap-events;
                        description "Log event as a trigger for one or more EHS handlers";
                    }

                    leaf event-id {
                        type types-log:log-event-id;
                        description
                            "Unique arbitrary identifier for indexing event type entries within
                             an event generator application.";
                    }

                    leaf-list parameters {
                        type types-sros:named-item;
                        description
                            "Indicates an event's specific parameters. These parameters can
                             be passed from a triggering event to its triggered EHS script.";
                    }

                    container statistics {
                        description "Enter the statistics context";

                        leaf count {
                            type yang:counter32;
                            description "Number of times an event of this type has been generated.";
                        }

                        leaf drop {
                            type yang:counter32;
                            description "Indicates the number of times an event of this type has been dropped.";
                        }

                    } // container statistics

                } // list pcap

                list pcep {
                    key "event";
                    description "Enter the pcep list instance";

                    leaf event {
                        type types-log:pcep-events;
                        description "PCEP module events";
                    }

                    leaf event-id {
                        type types-log:log-event-id;
                        description
                            "Unique arbitrary identifier for indexing event type entries within
                             an event generator application.";
                    }

                    leaf-list parameters {
                        type types-sros:named-item;
                        description
                            "Indicates an event's specific parameters. These parameters can
                             be passed from a triggering event to its triggered EHS script.";
                    }

                    container statistics {
                        description "Enter the statistics context";

                        leaf count {
                            type yang:counter32;
                            description "Number of times an event of this type has been generated.";
                        }

                        leaf drop {
                            type yang:counter32;
                            description "Indicates the number of times an event of this type has been dropped.";
                        }

                    } // container statistics

                } // list pcep

                list pfcp {
                    key "event";
                    description "Enter the pfcp list instance";

                    leaf event {
                        type types-log:pfcp-events;
                        description "PFCP events";
                    }

                    leaf event-id {
                        type types-log:log-event-id;
                        description
                            "Unique arbitrary identifier for indexing event type entries within
                             an event generator application.";
                    }

                    leaf-list parameters {
                        type types-sros:named-item;
                        description
                            "Indicates an event's specific parameters. These parameters can
                             be passed from a triggering event to its triggered EHS script.";
                    }

                    container statistics {
                        description "Enter the statistics context";

                        leaf count {
                            type yang:counter32;
                            description "Number of times an event of this type has been generated.";
                        }

                        leaf drop {
                            type yang:counter32;
                            description "Indicates the number of times an event of this type has been dropped.";
                        }

                    } // container statistics

                } // list pfcp

                list pim {
                    key "event";
                    description "Enter the pim list instance";

                    leaf event {
                        type types-log:pim-events;
                        description "Log event as a trigger for one or more EHS handlers";
                    }

                    leaf event-id {
                        type types-log:log-event-id;
                        description
                            "Unique arbitrary identifier for indexing event type entries within
                             an event generator application.";
                    }

                    leaf-list parameters {
                        type types-sros:named-item;
                        description
                            "Indicates an event's specific parameters. These parameters can
                             be passed from a triggering event to its triggered EHS script.";
                    }

                    container statistics {
                        description "Enter the statistics context";

                        leaf count {
                            type yang:counter32;
                            description "Number of times an event of this type has been generated.";
                        }

                        leaf drop {
                            type yang:counter32;
                            description "Indicates the number of times an event of this type has been dropped.";
                        }

                    } // container statistics

                } // list pim

                list pim-snooping {
                    key "event";
                    description "Enter the pim-snooping list instance";

                    leaf event {
                        type types-log:pim-snooping-events;
                        description "Log event as a trigger for one or more EHS handlers";
                    }

                    leaf event-id {
                        type types-log:log-event-id;
                        description
                            "Unique arbitrary identifier for indexing event type entries within
                             an event generator application.";
                    }

                    leaf-list parameters {
                        type types-sros:named-item;
                        description
                            "Indicates an event's specific parameters. These parameters can
                             be passed from a triggering event to its triggered EHS script.";
                    }

                    container statistics {
                        description "Enter the statistics context";

                        leaf count {
                            type yang:counter32;
                            description "Number of times an event of this type has been generated.";
                        }

                        leaf drop {
                            type yang:counter32;
                            description "Indicates the number of times an event of this type has been dropped.";
                        }

                    } // container statistics

                } // list pim-snooping

                list port {
                    key "event";
                    description "Enter the port list instance";

                    leaf event {
                        type types-log:port-events;
                        description "Log event as a trigger for one or more EHS handlers";
                    }

                    leaf event-id {
                        type types-log:log-event-id;
                        description
                            "Unique arbitrary identifier for indexing event type entries within
                             an event generator application.";
                    }

                    leaf-list parameters {
                        type types-sros:named-item;
                        description
                            "Indicates an event's specific parameters. These parameters can
                             be passed from a triggering event to its triggered EHS script.";
                    }

                    container statistics {
                        description "Enter the statistics context";

                        leaf count {
                            type yang:counter32;
                            description "Number of times an event of this type has been generated.";
                        }

                        leaf drop {
                            type yang:counter32;
                            description "Indicates the number of times an event of this type has been dropped.";
                        }

                    } // container statistics

                } // list port

                list pppoe {
                    key "event";
                    description "Enter the pppoe list instance";

                    leaf event {
                        type types-log:pppoe-events;
                        description "Log event as a trigger for one or more EHS handlers";
                    }

                    leaf event-id {
                        type types-log:log-event-id;
                        description
                            "Unique arbitrary identifier for indexing event type entries within
                             an event generator application.";
                    }

                    leaf-list parameters {
                        type types-sros:named-item;
                        description
                            "Indicates an event's specific parameters. These parameters can
                             be passed from a triggering event to its triggered EHS script.";
                    }

                    container statistics {
                        description "Enter the statistics context";

                        leaf count {
                            type yang:counter32;
                            description "Number of times an event of this type has been generated.";
                        }

                        leaf drop {
                            type yang:counter32;
                            description "Indicates the number of times an event of this type has been dropped.";
                        }

                    } // container statistics

                } // list pppoe

                list pppoe-clnt {
                    key "event";
                    description "Enter the pppoe-clnt list instance";

                    leaf event {
                        type types-log:pppoe-clnt-events;
                        description "Log event as a trigger for one or more EHS handlers";
                    }

                    leaf event-id {
                        type types-log:log-event-id;
                        description
                            "Unique arbitrary identifier for indexing event type entries within
                             an event generator application.";
                    }

                    leaf-list parameters {
                        type types-sros:named-item;
                        description
                            "Indicates an event's specific parameters. These parameters can
                             be passed from a triggering event to its triggered EHS script.";
                    }

                    container statistics {
                        description "Enter the statistics context";

                        leaf count {
                            type yang:counter32;
                            description "Number of times an event of this type has been generated.";
                        }

                        leaf drop {
                            type yang:counter32;
                            description "Indicates the number of times an event of this type has been dropped.";
                        }

                    } // container statistics

                } // list pppoe-clnt

                list ptp {
                    key "event";
                    description "Enter the ptp list instance";

                    leaf event {
                        type types-log:ptp-events;
                        description "Log event as a trigger for one or more EHS handlers";
                    }

                    leaf event-id {
                        type types-log:log-event-id;
                        description
                            "Unique arbitrary identifier for indexing event type entries within
                             an event generator application.";
                    }

                    leaf-list parameters {
                        type types-sros:named-item;
                        description
                            "Indicates an event's specific parameters. These parameters can
                             be passed from a triggering event to its triggered EHS script.";
                    }

                    container statistics {
                        description "Enter the statistics context";

                        leaf count {
                            type yang:counter32;
                            description "Number of times an event of this type has been generated.";
                        }

                        leaf drop {
                            type yang:counter32;
                            description "Indicates the number of times an event of this type has been dropped.";
                        }

                    } // container statistics

                } // list ptp

                list python {
                    key "event";
                    description "Enter the python list instance";

                    leaf event {
                        type types-log:python-events;
                        description "Python module events";
                    }

                    leaf event-id {
                        type types-log:log-event-id;
                        description
                            "Unique arbitrary identifier for indexing event type entries within
                             an event generator application.";
                    }

                    leaf-list parameters {
                        type types-sros:named-item;
                        description
                            "Indicates an event's specific parameters. These parameters can
                             be passed from a triggering event to its triggered EHS script.";
                    }

                    container statistics {
                        description "Enter the statistics context";

                        leaf count {
                            type yang:counter32;
                            description "Number of times an event of this type has been generated.";
                        }

                        leaf drop {
                            type yang:counter32;
                            description "Indicates the number of times an event of this type has been dropped.";
                        }

                    } // container statistics

                } // list python

                list radius {
                    key "event";
                    description "Enter the radius list instance";

                    leaf event {
                        type types-log:radius-events;
                        description "Log event as a trigger for one or more EHS handlers";
                    }

                    leaf event-id {
                        type types-log:log-event-id;
                        description
                            "Unique arbitrary identifier for indexing event type entries within
                             an event generator application.";
                    }

                    leaf-list parameters {
                        type types-sros:named-item;
                        description
                            "Indicates an event's specific parameters. These parameters can
                             be passed from a triggering event to its triggered EHS script.";
                    }

                    container statistics {
                        description "Enter the statistics context";

                        leaf count {
                            type yang:counter32;
                            description "Number of times an event of this type has been generated.";
                        }

                        leaf drop {
                            type yang:counter32;
                            description "Indicates the number of times an event of this type has been dropped.";
                        }

                    } // container statistics

                } // list radius

                list rip {
                    key "event";
                    description "Enter the rip list instance";

                    leaf event {
                        type types-log:rip-events;
                        description "Log event as a trigger for one or more EHS handlers";
                    }

                    leaf event-id {
                        type types-log:log-event-id;
                        description
                            "Unique arbitrary identifier for indexing event type entries within
                             an event generator application.";
                    }

                    leaf-list parameters {
                        type types-sros:named-item;
                        description
                            "Indicates an event's specific parameters. These parameters can
                             be passed from a triggering event to its triggered EHS script.";
                    }

                    container statistics {
                        description "Enter the statistics context";

                        leaf count {
                            type yang:counter32;
                            description "Number of times an event of this type has been generated.";
                        }

                        leaf drop {
                            type yang:counter32;
                            description "Indicates the number of times an event of this type has been dropped.";
                        }

                    } // container statistics

                } // list rip

                list ripng {
                    key "event";
                    description "Enter the ripng list instance";

                    leaf event {
                        type types-log:ripng-events;
                        description "Log event as a trigger for one or more EHS handlers";
                    }

                    leaf event-id {
                        type types-log:log-event-id;
                        description
                            "Unique arbitrary identifier for indexing event type entries within
                             an event generator application.";
                    }

                    leaf-list parameters {
                        type types-sros:named-item;
                        description
                            "Indicates an event's specific parameters. These parameters can
                             be passed from a triggering event to its triggered EHS script.";
                    }

                    container statistics {
                        description "Enter the statistics context";

                        leaf count {
                            type yang:counter32;
                            description "Number of times an event of this type has been generated.";
                        }

                        leaf drop {
                            type yang:counter32;
                            description "Indicates the number of times an event of this type has been dropped.";
                        }

                    } // container statistics

                } // list ripng

                list route-policy {
                    key "event";
                    description "Enter the route-policy list instance";

                    leaf event {
                        type types-log:route-policy-events;
                        description "Log event as a trigger for one or more EHS handlers";
                    }

                    leaf event-id {
                        type types-log:log-event-id;
                        description
                            "Unique arbitrary identifier for indexing event type entries within
                             an event generator application.";
                    }

                    leaf-list parameters {
                        type types-sros:named-item;
                        description
                            "Indicates an event's specific parameters. These parameters can
                             be passed from a triggering event to its triggered EHS script.";
                    }

                    container statistics {
                        description "Enter the statistics context";

                        leaf count {
                            type yang:counter32;
                            description "Number of times an event of this type has been generated.";
                        }

                        leaf drop {
                            type yang:counter32;
                            description "Indicates the number of times an event of this type has been dropped.";
                        }

                    } // container statistics

                } // list route-policy

                list rpki {
                    key "event";
                    description "Enter the rpki list instance";

                    leaf event {
                        type types-log:rpki-events;
                        description "Log event as a trigger for one or more EHS handlers";
                    }

                    leaf event-id {
                        type types-log:log-event-id;
                        description
                            "Unique arbitrary identifier for indexing event type entries within
                             an event generator application.";
                    }

                    leaf-list parameters {
                        type types-sros:named-item;
                        description
                            "Indicates an event's specific parameters. These parameters can
                             be passed from a triggering event to its triggered EHS script.";
                    }

                    container statistics {
                        description "Enter the statistics context";

                        leaf count {
                            type yang:counter32;
                            description "Number of times an event of this type has been generated.";
                        }

                        leaf drop {
                            type yang:counter32;
                            description "Indicates the number of times an event of this type has been dropped.";
                        }

                    } // container statistics

                } // list rpki

                list rsvp {
                    key "event";
                    description "Enter the rsvp list instance";

                    leaf event {
                        type types-log:rsvp-events;
                        description "Log event as a trigger for one or more EHS handlers";
                    }

                    leaf event-id {
                        type types-log:log-event-id;
                        description
                            "Unique arbitrary identifier for indexing event type entries within
                             an event generator application.";
                    }

                    leaf-list parameters {
                        type types-sros:named-item;
                        description
                            "Indicates an event's specific parameters. These parameters can
                             be passed from a triggering event to its triggered EHS script.";
                    }

                    container statistics {
                        description "Enter the statistics context";

                        leaf count {
                            type yang:counter32;
                            description "Number of times an event of this type has been generated.";
                        }

                        leaf drop {
                            type yang:counter32;
                            description "Indicates the number of times an event of this type has been dropped.";
                        }

                    } // container statistics

                } // list rsvp

                list satellite {
                    key "event";
                    description "Enter the satellite list instance";

                    leaf event {
                        type types-log:satellite-events;
                        description "Log event as a trigger for one or more EHS handlers";
                    }

                    leaf event-id {
                        type types-log:log-event-id;
                        description
                            "Unique arbitrary identifier for indexing event type entries within
                             an event generator application.";
                    }

                    leaf-list parameters {
                        type types-sros:named-item;
                        description
                            "Indicates an event's specific parameters. These parameters can
                             be passed from a triggering event to its triggered EHS script.";
                    }

                    container statistics {
                        description "Enter the statistics context";

                        leaf count {
                            type yang:counter32;
                            description "Number of times an event of this type has been generated.";
                        }

                        leaf drop {
                            type yang:counter32;
                            description "Indicates the number of times an event of this type has been dropped.";
                        }

                    } // container statistics

                } // list satellite

                list security {
                    key "event";
                    description "Enter the security list instance";

                    leaf event {
                        type types-log:security-events;
                        description "Log event as a trigger for one or more EHS handlers";
                    }

                    leaf event-id {
                        type types-log:log-event-id;
                        description
                            "Unique arbitrary identifier for indexing event type entries within
                             an event generator application.";
                    }

                    leaf-list parameters {
                        type types-sros:named-item;
                        description
                            "Indicates an event's specific parameters. These parameters can
                             be passed from a triggering event to its triggered EHS script.";
                    }

                    container statistics {
                        description "Enter the statistics context";

                        leaf count {
                            type yang:counter32;
                            description "Number of times an event of this type has been generated.";
                        }

                        leaf drop {
                            type yang:counter32;
                            description "Indicates the number of times an event of this type has been dropped.";
                        }

                    } // container statistics

                } // list security

                list sflow {
                    key "event";
                    description "Enter the sflow list instance";

                    leaf event {
                        type types-log:sflow-events;
                        description "Log event as a trigger for one or more EHS handlers";
                    }

                    leaf event-id {
                        type types-log:log-event-id;
                        description
                            "Unique arbitrary identifier for indexing event type entries within
                             an event generator application.";
                    }

                    leaf-list parameters {
                        type types-sros:named-item;
                        description
                            "Indicates an event's specific parameters. These parameters can
                             be passed from a triggering event to its triggered EHS script.";
                    }

                    container statistics {
                        description "Enter the statistics context";

                        leaf count {
                            type yang:counter32;
                            description "Number of times an event of this type has been generated.";
                        }

                        leaf drop {
                            type yang:counter32;
                            description "Indicates the number of times an event of this type has been dropped.";
                        }

                    } // container statistics

                } // list sflow

                list snmp {
                    key "event";
                    description "Enter the snmp list instance";

                    leaf event {
                        type types-log:snmp-events;
                        description "Log event as a trigger for one or more EHS handlers";
                    }

                    leaf event-id {
                        type types-log:log-event-id;
                        description
                            "Unique arbitrary identifier for indexing event type entries within
                             an event generator application.";
                    }

                    leaf-list parameters {
                        type types-sros:named-item;
                        description
                            "Indicates an event's specific parameters. These parameters can
                             be passed from a triggering event to its triggered EHS script.";
                    }

                    container statistics {
                        description "Enter the statistics context";

                        leaf count {
                            type yang:counter32;
                            description "Number of times an event of this type has been generated.";
                        }

                        leaf drop {
                            type yang:counter32;
                            description "Indicates the number of times an event of this type has been dropped.";
                        }

                    } // container statistics

                } // list snmp

                list sr-mpls {
                    key "event";
                    description "Enter the sr-mpls list instance";

                    leaf event {
                        type types-log:sr-mpls-events;
                        description "SR MPLS event";
                    }

                    leaf event-id {
                        type types-log:log-event-id;
                        description
                            "Unique arbitrary identifier for indexing event type entries within
                             an event generator application.";
                    }

                    leaf-list parameters {
                        type types-sros:named-item;
                        description
                            "Indicates an event's specific parameters. These parameters can
                             be passed from a triggering event to its triggered EHS script.";
                    }

                    container statistics {
                        description "Enter the statistics context";

                        leaf count {
                            type yang:counter32;
                            description "Number of times an event of this type has been generated.";
                        }

                        leaf drop {
                            type yang:counter32;
                            description "Indicates the number of times an event of this type has been dropped.";
                        }

                    } // container statistics

                } // list sr-mpls

                list srv6 {
                    key "event";
                    description "Enter the srv6 list instance";

                    leaf event {
                        type types-log:srv6-events;
                        description "Log event as a trigger for one or more EHS handlers";
                    }

                    leaf event-id {
                        type types-log:log-event-id;
                        description
                            "Unique arbitrary identifier for indexing event type entries within
                             an event generator application.";
                    }

                    leaf-list parameters {
                        type types-sros:named-item;
                        description
                            "Indicates an event's specific parameters. These parameters can
                             be passed from a triggering event to its triggered EHS script.";
                    }

                    container statistics {
                        description "Enter the statistics context";

                        leaf count {
                            type yang:counter32;
                            description "Number of times an event of this type has been generated.";
                        }

                        leaf drop {
                            type yang:counter32;
                            description "Indicates the number of times an event of this type has been dropped.";
                        }

                    } // container statistics

                } // list srv6

                list stp {
                    key "event";
                    description "Enter the stp list instance";

                    leaf event {
                        type types-log:stp-events;
                        description "Log event as a trigger for one or more EHS handlers";
                    }

                    leaf event-id {
                        type types-log:log-event-id;
                        description
                            "Unique arbitrary identifier for indexing event type entries within
                             an event generator application.";
                    }

                    leaf-list parameters {
                        type types-sros:named-item;
                        description
                            "Indicates an event's specific parameters. These parameters can
                             be passed from a triggering event to its triggered EHS script.";
                    }

                    container statistics {
                        description "Enter the statistics context";

                        leaf count {
                            type yang:counter32;
                            description "Number of times an event of this type has been generated.";
                        }

                        leaf drop {
                            type yang:counter32;
                            description "Indicates the number of times an event of this type has been dropped.";
                        }

                    } // container statistics

                } // list stp

                list svcmgr {
                    key "event";
                    description "Enter the svcmgr list instance";

                    leaf event {
                        type types-log:svcmgr-events;
                        description "Log event as a trigger for one or more EHS handlers";
                    }

                    leaf event-id {
                        type types-log:log-event-id;
                        description
                            "Unique arbitrary identifier for indexing event type entries within
                             an event generator application.";
                    }

                    leaf-list parameters {
                        type types-sros:named-item;
                        description
                            "Indicates an event's specific parameters. These parameters can
                             be passed from a triggering event to its triggered EHS script.";
                    }

                    container statistics {
                        description "Enter the statistics context";

                        leaf count {
                            type yang:counter32;
                            description "Number of times an event of this type has been generated.";
                        }

                        leaf drop {
                            type yang:counter32;
                            description "Indicates the number of times an event of this type has been dropped.";
                        }

                    } // container statistics

                } // list svcmgr

                list system {
                    key "event";
                    description "Enter the system list instance";

                    leaf event {
                        type types-log:system-events;
                        description "Log event as a trigger for one or more EHS handlers";
                    }

                    leaf event-id {
                        type types-log:log-event-id;
                        description
                            "Unique arbitrary identifier for indexing event type entries within
                             an event generator application.";
                    }

                    leaf-list parameters {
                        type types-sros:named-item;
                        description
                            "Indicates an event's specific parameters. These parameters can
                             be passed from a triggering event to its triggered EHS script.";
                    }

                    container statistics {
                        description "Enter the statistics context";

                        leaf count {
                            type yang:counter32;
                            description "Number of times an event of this type has been generated.";
                        }

                        leaf drop {
                            type yang:counter32;
                            description "Indicates the number of times an event of this type has been dropped.";
                        }

                    } // container statistics

                } // list system

                list tls {
                    key "event";
                    description "Enter the tls list instance";

                    leaf event {
                        type types-log:tls-events;
                        description "Log event as a trigger for one or more EHS handlers";
                    }

                    leaf event-id {
                        type types-log:log-event-id;
                        description
                            "Unique arbitrary identifier for indexing event type entries within
                             an event generator application.";
                    }

                    leaf-list parameters {
                        type types-sros:named-item;
                        description
                            "Indicates an event's specific parameters. These parameters can
                             be passed from a triggering event to its triggered EHS script.";
                    }

                    container statistics {
                        description "Enter the statistics context";

                        leaf count {
                            type yang:counter32;
                            description "Number of times an event of this type has been generated.";
                        }

                        leaf drop {
                            type yang:counter32;
                            description "Indicates the number of times an event of this type has been dropped.";
                        }

                    } // container statistics

                } // list tls

                list tree-sid {
                    key "event";
                    description "Enter the tree-sid list instance";

                    leaf event {
                        type types-log:treesid-events;
                        description "Log event as a trigger for one or more EHS handlers";
                    }

                    leaf event-id {
                        type types-log:log-event-id;
                        description
                            "Unique arbitrary identifier for indexing event type entries within
                             an event generator application.";
                    }

                    leaf-list parameters {
                        type types-sros:named-item;
                        description
                            "Indicates an event's specific parameters. These parameters can
                             be passed from a triggering event to its triggered EHS script.";
                    }

                    container statistics {
                        description "Enter the statistics context";

                        leaf count {
                            type yang:counter32;
                            description "Number of times an event of this type has been generated.";
                        }

                        leaf drop {
                            type yang:counter32;
                            description "Indicates the number of times an event of this type has been dropped.";
                        }

                    } // container statistics

                } // list tree-sid

                list user {
                    key "event";
                    description "Enter the user list instance";

                    leaf event {
                        type types-log:user-events;
                        description "Log event as a trigger for one or more EHS handlers";
                    }

                    leaf event-id {
                        type types-log:log-event-id;
                        description
                            "Unique arbitrary identifier for indexing event type entries within
                             an event generator application.";
                    }

                    leaf-list parameters {
                        type types-sros:named-item;
                        description
                            "Indicates an event's specific parameters. These parameters can
                             be passed from a triggering event to its triggered EHS script.";
                    }

                    container statistics {
                        description "Enter the statistics context";

                        leaf count {
                            type yang:counter32;
                            description "Number of times an event of this type has been generated.";
                        }

                        leaf drop {
                            type yang:counter32;
                            description "Indicates the number of times an event of this type has been dropped.";
                        }

                    } // container statistics

                } // list user

                list video {
                    key "event";
                    description "Enter the video list instance";

                    leaf event {
                        type types-log:video-events;
                        description "Log event as a trigger for one or more EHS handlers";
                    }

                    leaf event-id {
                        type types-log:log-event-id;
                        description
                            "Unique arbitrary identifier for indexing event type entries within
                             an event generator application.";
                    }

                    leaf-list parameters {
                        type types-sros:named-item;
                        description
                            "Indicates an event's specific parameters. These parameters can
                             be passed from a triggering event to its triggered EHS script.";
                    }

                    container statistics {
                        description "Enter the statistics context";

                        leaf count {
                            type yang:counter32;
                            description "Number of times an event of this type has been generated.";
                        }

                        leaf drop {
                            type yang:counter32;
                            description "Indicates the number of times an event of this type has been dropped.";
                        }

                    } // container statistics

                } // list video

                list vrrp {
                    key "event";
                    description "Enter the vrrp list instance";

                    leaf event {
                        type types-log:vrrp-events;
                        description "Log event as a trigger for one or more EHS handlers";
                    }

                    leaf event-id {
                        type types-log:log-event-id;
                        description
                            "Unique arbitrary identifier for indexing event type entries within
                             an event generator application.";
                    }

                    leaf-list parameters {
                        type types-sros:named-item;
                        description
                            "Indicates an event's specific parameters. These parameters can
                             be passed from a triggering event to its triggered EHS script.";
                    }

                    container statistics {
                        description "Enter the statistics context";

                        leaf count {
                            type yang:counter32;
                            description "Number of times an event of this type has been generated.";
                        }

                        leaf drop {
                            type yang:counter32;
                            description "Indicates the number of times an event of this type has been dropped.";
                        }

                    } // container statistics

                } // list vrrp

                list vrtr {
                    key "event";
                    description "Enter the vrtr list instance";

                    leaf event {
                        type types-log:vrtr-events;
                        description "Log event as a trigger for one or more EHS handlers";
                    }

                    leaf event-id {
                        type types-log:log-event-id;
                        description
                            "Unique arbitrary identifier for indexing event type entries within
                             an event generator application.";
                    }

                    leaf-list parameters {
                        type types-sros:named-item;
                        description
                            "Indicates an event's specific parameters. These parameters can
                             be passed from a triggering event to its triggered EHS script.";
                    }

                    container statistics {
                        description "Enter the statistics context";

                        leaf count {
                            type yang:counter32;
                            description "Number of times an event of this type has been generated.";
                        }

                        leaf drop {
                            type yang:counter32;
                            description "Indicates the number of times an event of this type has been dropped.";
                        }

                    } // container statistics

                } // list vrtr

                list wlan-gw {
                    key "event";
                    description "Enter the wlan-gw list instance";

                    leaf event {
                        type types-log:wlan-gw-events;
                        description "Log event as a trigger for one or more EHS handlers";
                    }

                    leaf event-id {
                        type types-log:log-event-id;
                        description
                            "Unique arbitrary identifier for indexing event type entries within
                             an event generator application.";
                    }

                    leaf-list parameters {
                        type types-sros:named-item;
                        description
                            "Indicates an event's specific parameters. These parameters can
                             be passed from a triggering event to its triggered EHS script.";
                    }

                    container statistics {
                        description "Enter the statistics context";

                        leaf count {
                            type yang:counter32;
                            description "Number of times an event of this type has been generated.";
                        }

                        leaf drop {
                            type yang:counter32;
                            description "Indicates the number of times an event of this type has been dropped.";
                        }

                    } // container statistics

                } // list wlan-gw

                list wpp {
                    key "event";
                    description "Enter the wpp list instance";

                    leaf event {
                        type types-log:wpp-events;
                        description "Log event as a trigger for one or more EHS handlers";
                    }

                    leaf event-id {
                        type types-log:log-event-id;
                        description
                            "Unique arbitrary identifier for indexing event type entries within
                             an event generator application.";
                    }

                    leaf-list parameters {
                        type types-sros:named-item;
                        description
                            "Indicates an event's specific parameters. These parameters can
                             be passed from a triggering event to its triggered EHS script.";
                    }

                    container statistics {
                        description "Enter the statistics context";

                        leaf count {
                            type yang:counter32;
                            description "Number of times an event of this type has been generated.";
                        }

                        leaf drop {
                            type yang:counter32;
                            description "Indicates the number of times an event of this type has been dropped.";
                        }

                    } // container statistics

                } // list wpp

            } // container log-events

            container event-handling {
                description "Enter the event-handling context";

                container summary-statistics {
                    description "Enter the summary-statistics context";

                    leaf success {
                        type yang:counter32;
                        description
                            "Indicates the number of times the EHS system triggers a handler,
                             which can take corresponding action specified in handler's entries.";
                    }

                    leaf error-no-entry {
                        type yang:counter32;
                        description
                            "Indicates the number of times the EHS system triggers a handler,
                             which can not take corresponding action as there is no handler's entry
                             specifying an operation to perform.";
                    }

                    leaf error-admin-state {
                        type yang:counter32;
                        description
                            "Indicates the number of times the EHS system triggers a handler,
                             which can not take corresponding action due handler may be out-of-service.";
                    }

                    leaf total {
                        type yang:counter32;
                        description "Sum of success + error-no-entry + error-admin-state.";
                    }

                } // container summary-statistics

                list handler {
                    key "name";
                    description "Enter the handler list instance";

                    leaf name {
                        type types-sros:named-item;
                        description "EHS handler name";
                    }

                    leaf oper-state {
                        type types-sros:oper-state;
                        description "Indicates the operational state of the EHS Event Handler.";
                    }

                    container statistics {
                        description "Enter the statistics context";

                        leaf success {
                            type yang:counter32;
                            description
                                "Indicates the number of times the EHS system triggers the handler,
                                 which can take corresponding action specified in handler's entries.";
                        }

                        leaf error-no-entry {
                            type yang:counter32;
                            description
                                "Indicates the number of times the EHS system triggers the handler,
                                 which can not take corresponding action as there is no handler's entry
                                 specifying an operation to perform.";
                        }

                        leaf error-admin-state {
                            type yang:counter32;
                            description
                                "Indicates the number of times the EHS system triggers the handler,
                                 which can not take corresponding action due handler may be out-of-service.";
                        }

                        leaf total {
                            type yang:counter32;
                            description "Sum of success + error-no-entry + error-admin-state.";
                        }

                    } // container statistics

                    container summary-entry-statistics {
                        description "Enter the summary-entry-statistics context";

                        leaf success {
                            type yang:counter32;
                            description "Indicates the global number of successfully queued scripts by EHS handler entries.";
                        }

                        leaf error-min-delay {
                            type yang:counter32;
                            description "Indicates the global number of cancelled script executions due to min-delay.";
                        }

                        leaf error-launch-failure {
                            type yang:counter32;
                            description "Indicates the global number of cancelled script executions due to launch failure.";
                        }

                        leaf error-admin-state {
                            type yang:counter32;
                            description "Indicates the global number of cancelled script executions due to handler entry may be out-of-service.";
                        }

                    } // container summary-entry-statistics

                    list entry {
                        key "id";
                        description "Enter the entry list instance";

                        leaf id {
                            type uint32 {
                                range "1..1500";
                            }
                            description "EHS handler entry ID";
                        }

                        leaf oper-state {
                            type types-sros:oper-state;
                            description "Indicates the operational state of the EHS Event Handler Entry.";
                        }

                        leaf last-data-loss-time {
                            type yang:date-and-time;
                            description "Indicates the time when handler entry launch execution of action.";
                        }

                        container statistics {
                            description "Enter the statistics context";

                            leaf success {
                                type yang:counter32;
                                description "Indicates the number of successfully queued scripts by EHS handler entry.";
                            }

                            leaf error-min-delay {
                                type yang:counter32;
                                description "Indicates the number of cancelled script executions due to min-delay.";
                            }

                            leaf error-launch-failure {
                                type yang:counter32;
                                description "Indicates the number of cancelled script executions due to launch failure.";
                            }

                            leaf error-admin-state {
                                type yang:counter32;
                                description "Indicates the number of cancelled script executions due to handler entry may be out-of-service.";
                            }

                        } // container statistics

                    } // list entry

                } // list handler

            } // container event-handling

            container event-trigger {
                description "Enter the event-trigger context";

                container summary-statistics {
                    description "Enter the summary-statistics context";

                    leaf success {
                        type yang:counter32;
                        description
                            "Indicates the number of not ignored logger event occurrences
                             associated with all EHS triggers.";
                    }

                    leaf error-no-entry {
                        type yang:counter32;
                        description
                            "Indicates the number of ignored logger event occurrences associated
                             with all EHS triggers.

                             Event is ignored due to no trigger entry configured for a trigger.";
                    }

                    leaf error-admin-state {
                        type yang:counter32;
                        description
                            "Indicates the number of ignored logger event occurrences associated
                             with all EHS triggers.

                             Event is ignored due to a trigger may be out-of-service.";
                    }

                    leaf total {
                        type yang:counter32;
                        description "Sum of success + error-no-entry + error-admin-state.";
                    }

                } // container summary-statistics

                list adp {
                    key "event";
                    description "Enter the adp list instance";

                    leaf event {
                        type types-log:adp-events;
                        description "Log event as a trigger for one or more EHS handlers";
                    }

                    leaf oper-state {
                        type types-sros:oper-state;
                        description "Indicates the operational state of the EHS Event Trigger.";
                    }

                    container statistics {
                        description "Enter the statistics context";

                        leaf success {
                            type yang:counter32;
                            description
                                "Indicates the number of not ignored logger event occurrences
                                 associated with EHS trigger.";
                        }

                        leaf error-no-entry {
                            type yang:counter32;
                            description
                                "Indicates the number of ignored logger event occurrences associated
                                 with EHS trigger.

                                 Event is ignored due to no trigger entry configured for this trigger.";
                        }

                        leaf error-admin-state {
                            type yang:counter32;
                            description
                                "Indicates the number of ignored logger event occurrences associated
                                 with EHS trigger.

                                 Event is ignored due to trigger may be out-of-service.";
                        }

                        leaf total {
                            type yang:counter32;
                            description "Sum of success + error-no-entry + error-admin-state.";
                        }

                    } // container statistics

                    container summary-entry-statistics {
                        description "Enter the summary-entry-statistics context";

                        leaf filter-match {
                            type yang:counter32;
                            description "Indicates the number of times a filter matches an logger event.";
                        }

                        leaf filter-fail {
                            type yang:counter32;
                            description "Indicates the number of times a filter does not match an logger event.";
                        }

                        leaf error-admin-state {
                            type yang:counter32;
                            description
                                "Indicates the number of times the logger event will be ignored due to
                                 admin state of EHS trigger entries is out-of-service.";
                        }

                        leaf error-filter {
                            type yang:counter32;
                            description
                                "Indicates the number of times the logger event will be ignored due to filter
                                 is not operational or is not configured in EHS trigger entries.";
                        }

                        leaf error-handler {
                            type yang:counter32;
                            description
                                "Indicates the number of times the logger event will be ignored due to handler
                                 is not operational or is not configured in EHS trigger entries.";
                        }

                        leaf trigger-count {
                            type yang:counter32;
                            description "Indicates the number of times script execution is triggered after filter match.";
                        }

                        leaf debounce-count {
                            type yang:counter32;
                            description "Indicates the number of times script is not executed due to debounce rule.";
                        }

                    } // container summary-entry-statistics

                    list entry {
                        key "id";
                        description "Enter the entry list instance";

                        leaf id {
                            type uint32 {
                                range "1..1500";
                            }
                            description "ID of the EHS event trigger entry";
                        }

                        leaf oper-state {
                            type types-sros:oper-state;
                            description "Indicates the operational state of the EHS Event Trigger Entry.";
                        }

                        container statistics {
                            description "Enter the statistics context";

                            leaf filter-match {
                                type yang:counter32;
                                description
                                    "Indicates the number of times a filter, for the specified trigger entry,
                                     matches an logger event.";
                            }

                            leaf filter-fail {
                                type yang:counter32;
                                description
                                    "Indicates the number of times a filter, for the specified trigger entry,
                                     does not match an logger event.";
                            }

                            leaf error-admin-state {
                                type yang:counter32;
                                description
                                    "Indicates the number of times the logger event will be ignored due to
                                     admin state of EHS trigger entry is out-of-service.";
                            }

                            leaf error-filter {
                                type yang:counter32;
                                description
                                    "Indicates the number of times the logger event will be ignored due to filter
                                     is not operational or is not configured in EHS trigger entry.";
                            }

                            leaf error-handler {
                                type yang:counter32;
                                description
                                    "Indicates the number of times the logger event will be ignored due to handler
                                     is not operational or is not configured in EHS trigger entry.";
                            }

                            leaf trigger-count {
                                type yang:counter32;
                                description
                                    "Indicates the number of times script execution is triggered after filter match
                                     for the specified trigger entry.";
                            }

                            leaf debounce-count {
                                type yang:counter32;
                                description
                                    "Indicates the number of times script is not executed due to debounce rule
                                     for the specified trigger entry.";
                            }

                        } // container statistics

                    } // list entry

                } // list adp

                list anysec {
                    key "event";
                    description "Enter the anysec list instance";

                    leaf event {
                        type types-log:anysec-events;
                        description "ANYSec module event";
                    }

                    leaf oper-state {
                        type types-sros:oper-state;
                        description "Indicates the operational state of the EHS Event Trigger.";
                    }

                    container statistics {
                        description "Enter the statistics context";

                        leaf success {
                            type yang:counter32;
                            description
                                "Indicates the number of not ignored logger event occurrences
                                 associated with EHS trigger.";
                        }

                        leaf error-no-entry {
                            type yang:counter32;
                            description
                                "Indicates the number of ignored logger event occurrences associated
                                 with EHS trigger.

                                 Event is ignored due to no trigger entry configured for this trigger.";
                        }

                        leaf error-admin-state {
                            type yang:counter32;
                            description
                                "Indicates the number of ignored logger event occurrences associated
                                 with EHS trigger.

                                 Event is ignored due to trigger may be out-of-service.";
                        }

                        leaf total {
                            type yang:counter32;
                            description "Sum of success + error-no-entry + error-admin-state.";
                        }

                    } // container statistics

                    container summary-entry-statistics {
                        description "Enter the summary-entry-statistics context";

                        leaf filter-match {
                            type yang:counter32;
                            description "Indicates the number of times a filter matches an logger event.";
                        }

                        leaf filter-fail {
                            type yang:counter32;
                            description "Indicates the number of times a filter does not match an logger event.";
                        }

                        leaf error-admin-state {
                            type yang:counter32;
                            description
                                "Indicates the number of times the logger event will be ignored due to
                                 admin state of EHS trigger entries is out-of-service.";
                        }

                        leaf error-filter {
                            type yang:counter32;
                            description
                                "Indicates the number of times the logger event will be ignored due to filter
                                 is not operational or is not configured in EHS trigger entries.";
                        }

                        leaf error-handler {
                            type yang:counter32;
                            description
                                "Indicates the number of times the logger event will be ignored due to handler
                                 is not operational or is not configured in EHS trigger entries.";
                        }

                        leaf trigger-count {
                            type yang:counter32;
                            description "Indicates the number of times script execution is triggered after filter match.";
                        }

                        leaf debounce-count {
                            type yang:counter32;
                            description "Indicates the number of times script is not executed due to debounce rule.";
                        }

                    } // container summary-entry-statistics

                    list entry {
                        key "id";
                        description "Enter the entry list instance";

                        leaf id {
                            type uint32 {
                                range "1..1500";
                            }
                            description "ID of the EHS event trigger entry";
                        }

                        leaf oper-state {
                            type types-sros:oper-state;
                            description "Indicates the operational state of the EHS Event Trigger Entry.";
                        }

                        container statistics {
                            description "Enter the statistics context";

                            leaf filter-match {
                                type yang:counter32;
                                description
                                    "Indicates the number of times a filter, for the specified trigger entry,
                                     matches an logger event.";
                            }

                            leaf filter-fail {
                                type yang:counter32;
                                description
                                    "Indicates the number of times a filter, for the specified trigger entry,
                                     does not match an logger event.";
                            }

                            leaf error-admin-state {
                                type yang:counter32;
                                description
                                    "Indicates the number of times the logger event will be ignored due to
                                     admin state of EHS trigger entry is out-of-service.";
                            }

                            leaf error-filter {
                                type yang:counter32;
                                description
                                    "Indicates the number of times the logger event will be ignored due to filter
                                     is not operational or is not configured in EHS trigger entry.";
                            }

                            leaf error-handler {
                                type yang:counter32;
                                description
                                    "Indicates the number of times the logger event will be ignored due to handler
                                     is not operational or is not configured in EHS trigger entry.";
                            }

                            leaf trigger-count {
                                type yang:counter32;
                                description
                                    "Indicates the number of times script execution is triggered after filter match
                                     for the specified trigger entry.";
                            }

                            leaf debounce-count {
                                type yang:counter32;
                                description
                                    "Indicates the number of times script is not executed due to debounce rule
                                     for the specified trigger entry.";
                            }

                        } // container statistics

                    } // list entry

                } // list anysec

                list application-assurance {
                    key "event";
                    description "Enter the application-assurance list instance";

                    leaf event {
                        type types-log:application-assurance-events;
                        description "Log event as a trigger for one or more EHS handlers";
                    }

                    leaf oper-state {
                        type types-sros:oper-state;
                        description "Indicates the operational state of the EHS Event Trigger.";
                    }

                    container statistics {
                        description "Enter the statistics context";

                        leaf success {
                            type yang:counter32;
                            description
                                "Indicates the number of not ignored logger event occurrences
                                 associated with EHS trigger.";
                        }

                        leaf error-no-entry {
                            type yang:counter32;
                            description
                                "Indicates the number of ignored logger event occurrences associated
                                 with EHS trigger.

                                 Event is ignored due to no trigger entry configured for this trigger.";
                        }

                        leaf error-admin-state {
                            type yang:counter32;
                            description
                                "Indicates the number of ignored logger event occurrences associated
                                 with EHS trigger.

                                 Event is ignored due to trigger may be out-of-service.";
                        }

                        leaf total {
                            type yang:counter32;
                            description "Sum of success + error-no-entry + error-admin-state.";
                        }

                    } // container statistics

                    container summary-entry-statistics {
                        description "Enter the summary-entry-statistics context";

                        leaf filter-match {
                            type yang:counter32;
                            description "Indicates the number of times a filter matches an logger event.";
                        }

                        leaf filter-fail {
                            type yang:counter32;
                            description "Indicates the number of times a filter does not match an logger event.";
                        }

                        leaf error-admin-state {
                            type yang:counter32;
                            description
                                "Indicates the number of times the logger event will be ignored due to
                                 admin state of EHS trigger entries is out-of-service.";
                        }

                        leaf error-filter {
                            type yang:counter32;
                            description
                                "Indicates the number of times the logger event will be ignored due to filter
                                 is not operational or is not configured in EHS trigger entries.";
                        }

                        leaf error-handler {
                            type yang:counter32;
                            description
                                "Indicates the number of times the logger event will be ignored due to handler
                                 is not operational or is not configured in EHS trigger entries.";
                        }

                        leaf trigger-count {
                            type yang:counter32;
                            description "Indicates the number of times script execution is triggered after filter match.";
                        }

                        leaf debounce-count {
                            type yang:counter32;
                            description "Indicates the number of times script is not executed due to debounce rule.";
                        }

                    } // container summary-entry-statistics

                    list entry {
                        key "id";
                        description "Enter the entry list instance";

                        leaf id {
                            type uint32 {
                                range "1..1500";
                            }
                            description "ID of the EHS event trigger entry";
                        }

                        leaf oper-state {
                            type types-sros:oper-state;
                            description "Indicates the operational state of the EHS Event Trigger Entry.";
                        }

                        container statistics {
                            description "Enter the statistics context";

                            leaf filter-match {
                                type yang:counter32;
                                description
                                    "Indicates the number of times a filter, for the specified trigger entry,
                                     matches an logger event.";
                            }

                            leaf filter-fail {
                                type yang:counter32;
                                description
                                    "Indicates the number of times a filter, for the specified trigger entry,
                                     does not match an logger event.";
                            }

                            leaf error-admin-state {
                                type yang:counter32;
                                description
                                    "Indicates the number of times the logger event will be ignored due to
                                     admin state of EHS trigger entry is out-of-service.";
                            }

                            leaf error-filter {
                                type yang:counter32;
                                description
                                    "Indicates the number of times the logger event will be ignored due to filter
                                     is not operational or is not configured in EHS trigger entry.";
                            }

                            leaf error-handler {
                                type yang:counter32;
                                description
                                    "Indicates the number of times the logger event will be ignored due to handler
                                     is not operational or is not configured in EHS trigger entry.";
                            }

                            leaf trigger-count {
                                type yang:counter32;
                                description
                                    "Indicates the number of times script execution is triggered after filter match
                                     for the specified trigger entry.";
                            }

                            leaf debounce-count {
                                type yang:counter32;
                                description
                                    "Indicates the number of times script is not executed due to debounce rule
                                     for the specified trigger entry.";
                            }

                        } // container statistics

                    } // list entry

                } // list application-assurance

                list aps {
                    key "event";
                    description "Enter the aps list instance";

                    leaf event {
                        type types-log:aps-events;
                        description "Log event as a trigger for one or more EHS handlers";
                    }

                    leaf oper-state {
                        type types-sros:oper-state;
                        description "Indicates the operational state of the EHS Event Trigger.";
                    }

                    container statistics {
                        description "Enter the statistics context";

                        leaf success {
                            type yang:counter32;
                            description
                                "Indicates the number of not ignored logger event occurrences
                                 associated with EHS trigger.";
                        }

                        leaf error-no-entry {
                            type yang:counter32;
                            description
                                "Indicates the number of ignored logger event occurrences associated
                                 with EHS trigger.

                                 Event is ignored due to no trigger entry configured for this trigger.";
                        }

                        leaf error-admin-state {
                            type yang:counter32;
                            description
                                "Indicates the number of ignored logger event occurrences associated
                                 with EHS trigger.

                                 Event is ignored due to trigger may be out-of-service.";
                        }

                        leaf total {
                            type yang:counter32;
                            description "Sum of success + error-no-entry + error-admin-state.";
                        }

                    } // container statistics

                    container summary-entry-statistics {
                        description "Enter the summary-entry-statistics context";

                        leaf filter-match {
                            type yang:counter32;
                            description "Indicates the number of times a filter matches an logger event.";
                        }

                        leaf filter-fail {
                            type yang:counter32;
                            description "Indicates the number of times a filter does not match an logger event.";
                        }

                        leaf error-admin-state {
                            type yang:counter32;
                            description
                                "Indicates the number of times the logger event will be ignored due to
                                 admin state of EHS trigger entries is out-of-service.";
                        }

                        leaf error-filter {
                            type yang:counter32;
                            description
                                "Indicates the number of times the logger event will be ignored due to filter
                                 is not operational or is not configured in EHS trigger entries.";
                        }

                        leaf error-handler {
                            type yang:counter32;
                            description
                                "Indicates the number of times the logger event will be ignored due to handler
                                 is not operational or is not configured in EHS trigger entries.";
                        }

                        leaf trigger-count {
                            type yang:counter32;
                            description "Indicates the number of times script execution is triggered after filter match.";
                        }

                        leaf debounce-count {
                            type yang:counter32;
                            description "Indicates the number of times script is not executed due to debounce rule.";
                        }

                    } // container summary-entry-statistics

                    list entry {
                        key "id";
                        description "Enter the entry list instance";

                        leaf id {
                            type uint32 {
                                range "1..1500";
                            }
                            description "ID of the EHS event trigger entry";
                        }

                        leaf oper-state {
                            type types-sros:oper-state;
                            description "Indicates the operational state of the EHS Event Trigger Entry.";
                        }

                        container statistics {
                            description "Enter the statistics context";

                            leaf filter-match {
                                type yang:counter32;
                                description
                                    "Indicates the number of times a filter, for the specified trigger entry,
                                     matches an logger event.";
                            }

                            leaf filter-fail {
                                type yang:counter32;
                                description
                                    "Indicates the number of times a filter, for the specified trigger entry,
                                     does not match an logger event.";
                            }

                            leaf error-admin-state {
                                type yang:counter32;
                                description
                                    "Indicates the number of times the logger event will be ignored due to
                                     admin state of EHS trigger entry is out-of-service.";
                            }

                            leaf error-filter {
                                type yang:counter32;
                                description
                                    "Indicates the number of times the logger event will be ignored due to filter
                                     is not operational or is not configured in EHS trigger entry.";
                            }

                            leaf error-handler {
                                type yang:counter32;
                                description
                                    "Indicates the number of times the logger event will be ignored due to handler
                                     is not operational or is not configured in EHS trigger entry.";
                            }

                            leaf trigger-count {
                                type yang:counter32;
                                description
                                    "Indicates the number of times script execution is triggered after filter match
                                     for the specified trigger entry.";
                            }

                            leaf debounce-count {
                                type yang:counter32;
                                description
                                    "Indicates the number of times script is not executed due to debounce rule
                                     for the specified trigger entry.";
                            }

                        } // container statistics

                    } // list entry

                } // list aps

                list auto-prov {
                    key "event";
                    description "Enter the auto-prov list instance";

                    leaf event {
                        type types-log:auto-prov-events;
                        description "Log event as a trigger for one or more EHS handlers";
                    }

                    leaf oper-state {
                        type types-sros:oper-state;
                        description "Indicates the operational state of the EHS Event Trigger.";
                    }

                    container statistics {
                        description "Enter the statistics context";

                        leaf success {
                            type yang:counter32;
                            description
                                "Indicates the number of not ignored logger event occurrences
                                 associated with EHS trigger.";
                        }

                        leaf error-no-entry {
                            type yang:counter32;
                            description
                                "Indicates the number of ignored logger event occurrences associated
                                 with EHS trigger.

                                 Event is ignored due to no trigger entry configured for this trigger.";
                        }

                        leaf error-admin-state {
                            type yang:counter32;
                            description
                                "Indicates the number of ignored logger event occurrences associated
                                 with EHS trigger.

                                 Event is ignored due to trigger may be out-of-service.";
                        }

                        leaf total {
                            type yang:counter32;
                            description "Sum of success + error-no-entry + error-admin-state.";
                        }

                    } // container statistics

                    container summary-entry-statistics {
                        description "Enter the summary-entry-statistics context";

                        leaf filter-match {
                            type yang:counter32;
                            description "Indicates the number of times a filter matches an logger event.";
                        }

                        leaf filter-fail {
                            type yang:counter32;
                            description "Indicates the number of times a filter does not match an logger event.";
                        }

                        leaf error-admin-state {
                            type yang:counter32;
                            description
                                "Indicates the number of times the logger event will be ignored due to
                                 admin state of EHS trigger entries is out-of-service.";
                        }

                        leaf error-filter {
                            type yang:counter32;
                            description
                                "Indicates the number of times the logger event will be ignored due to filter
                                 is not operational or is not configured in EHS trigger entries.";
                        }

                        leaf error-handler {
                            type yang:counter32;
                            description
                                "Indicates the number of times the logger event will be ignored due to handler
                                 is not operational or is not configured in EHS trigger entries.";
                        }

                        leaf trigger-count {
                            type yang:counter32;
                            description "Indicates the number of times script execution is triggered after filter match.";
                        }

                        leaf debounce-count {
                            type yang:counter32;
                            description "Indicates the number of times script is not executed due to debounce rule.";
                        }

                    } // container summary-entry-statistics

                    list entry {
                        key "id";
                        description "Enter the entry list instance";

                        leaf id {
                            type uint32 {
                                range "1..1500";
                            }
                            description "ID of the EHS event trigger entry";
                        }

                        leaf oper-state {
                            type types-sros:oper-state;
                            description "Indicates the operational state of the EHS Event Trigger Entry.";
                        }

                        container statistics {
                            description "Enter the statistics context";

                            leaf filter-match {
                                type yang:counter32;
                                description
                                    "Indicates the number of times a filter, for the specified trigger entry,
                                     matches an logger event.";
                            }

                            leaf filter-fail {
                                type yang:counter32;
                                description
                                    "Indicates the number of times a filter, for the specified trigger entry,
                                     does not match an logger event.";
                            }

                            leaf error-admin-state {
                                type yang:counter32;
                                description
                                    "Indicates the number of times the logger event will be ignored due to
                                     admin state of EHS trigger entry is out-of-service.";
                            }

                            leaf error-filter {
                                type yang:counter32;
                                description
                                    "Indicates the number of times the logger event will be ignored due to filter
                                     is not operational or is not configured in EHS trigger entry.";
                            }

                            leaf error-handler {
                                type yang:counter32;
                                description
                                    "Indicates the number of times the logger event will be ignored due to handler
                                     is not operational or is not configured in EHS trigger entry.";
                            }

                            leaf trigger-count {
                                type yang:counter32;
                                description
                                    "Indicates the number of times script execution is triggered after filter match
                                     for the specified trigger entry.";
                            }

                            leaf debounce-count {
                                type yang:counter32;
                                description
                                    "Indicates the number of times script is not executed due to debounce rule
                                     for the specified trigger entry.";
                            }

                        } // container statistics

                    } // list entry

                } // list auto-prov

                list bfd {
                    key "event";
                    description "Enter the bfd list instance";

                    leaf event {
                        type types-log:bfd-events;
                        description "Log event as a trigger for one or more EHS handlers";
                    }

                    leaf oper-state {
                        type types-sros:oper-state;
                        description "Indicates the operational state of the EHS Event Trigger.";
                    }

                    container statistics {
                        description "Enter the statistics context";

                        leaf success {
                            type yang:counter32;
                            description
                                "Indicates the number of not ignored logger event occurrences
                                 associated with EHS trigger.";
                        }

                        leaf error-no-entry {
                            type yang:counter32;
                            description
                                "Indicates the number of ignored logger event occurrences associated
                                 with EHS trigger.

                                 Event is ignored due to no trigger entry configured for this trigger.";
                        }

                        leaf error-admin-state {
                            type yang:counter32;
                            description
                                "Indicates the number of ignored logger event occurrences associated
                                 with EHS trigger.

                                 Event is ignored due to trigger may be out-of-service.";
                        }

                        leaf total {
                            type yang:counter32;
                            description "Sum of success + error-no-entry + error-admin-state.";
                        }

                    } // container statistics

                    container summary-entry-statistics {
                        description "Enter the summary-entry-statistics context";

                        leaf filter-match {
                            type yang:counter32;
                            description "Indicates the number of times a filter matches an logger event.";
                        }

                        leaf filter-fail {
                            type yang:counter32;
                            description "Indicates the number of times a filter does not match an logger event.";
                        }

                        leaf error-admin-state {
                            type yang:counter32;
                            description
                                "Indicates the number of times the logger event will be ignored due to
                                 admin state of EHS trigger entries is out-of-service.";
                        }

                        leaf error-filter {
                            type yang:counter32;
                            description
                                "Indicates the number of times the logger event will be ignored due to filter
                                 is not operational or is not configured in EHS trigger entries.";
                        }

                        leaf error-handler {
                            type yang:counter32;
                            description
                                "Indicates the number of times the logger event will be ignored due to handler
                                 is not operational or is not configured in EHS trigger entries.";
                        }

                        leaf trigger-count {
                            type yang:counter32;
                            description "Indicates the number of times script execution is triggered after filter match.";
                        }

                        leaf debounce-count {
                            type yang:counter32;
                            description "Indicates the number of times script is not executed due to debounce rule.";
                        }

                    } // container summary-entry-statistics

                    list entry {
                        key "id";
                        description "Enter the entry list instance";

                        leaf id {
                            type uint32 {
                                range "1..1500";
                            }
                            description "ID of the EHS event trigger entry";
                        }

                        leaf oper-state {
                            type types-sros:oper-state;
                            description "Indicates the operational state of the EHS Event Trigger Entry.";
                        }

                        container statistics {
                            description "Enter the statistics context";

                            leaf filter-match {
                                type yang:counter32;
                                description
                                    "Indicates the number of times a filter, for the specified trigger entry,
                                     matches an logger event.";
                            }

                            leaf filter-fail {
                                type yang:counter32;
                                description
                                    "Indicates the number of times a filter, for the specified trigger entry,
                                     does not match an logger event.";
                            }

                            leaf error-admin-state {
                                type yang:counter32;
                                description
                                    "Indicates the number of times the logger event will be ignored due to
                                     admin state of EHS trigger entry is out-of-service.";
                            }

                            leaf error-filter {
                                type yang:counter32;
                                description
                                    "Indicates the number of times the logger event will be ignored due to filter
                                     is not operational or is not configured in EHS trigger entry.";
                            }

                            leaf error-handler {
                                type yang:counter32;
                                description
                                    "Indicates the number of times the logger event will be ignored due to handler
                                     is not operational or is not configured in EHS trigger entry.";
                            }

                            leaf trigger-count {
                                type yang:counter32;
                                description
                                    "Indicates the number of times script execution is triggered after filter match
                                     for the specified trigger entry.";
                            }

                            leaf debounce-count {
                                type yang:counter32;
                                description
                                    "Indicates the number of times script is not executed due to debounce rule
                                     for the specified trigger entry.";
                            }

                        } // container statistics

                    } // list entry

                } // list bfd

                list bgp {
                    key "event";
                    description "Enter the bgp list instance";

                    leaf event {
                        type types-log:bgp-events;
                        description "Log event as a trigger for one or more EHS handlers";
                    }

                    leaf oper-state {
                        type types-sros:oper-state;
                        description "Indicates the operational state of the EHS Event Trigger.";
                    }

                    container statistics {
                        description "Enter the statistics context";

                        leaf success {
                            type yang:counter32;
                            description
                                "Indicates the number of not ignored logger event occurrences
                                 associated with EHS trigger.";
                        }

                        leaf error-no-entry {
                            type yang:counter32;
                            description
                                "Indicates the number of ignored logger event occurrences associated
                                 with EHS trigger.

                                 Event is ignored due to no trigger entry configured for this trigger.";
                        }

                        leaf error-admin-state {
                            type yang:counter32;
                            description
                                "Indicates the number of ignored logger event occurrences associated
                                 with EHS trigger.

                                 Event is ignored due to trigger may be out-of-service.";
                        }

                        leaf total {
                            type yang:counter32;
                            description "Sum of success + error-no-entry + error-admin-state.";
                        }

                    } // container statistics

                    container summary-entry-statistics {
                        description "Enter the summary-entry-statistics context";

                        leaf filter-match {
                            type yang:counter32;
                            description "Indicates the number of times a filter matches an logger event.";
                        }

                        leaf filter-fail {
                            type yang:counter32;
                            description "Indicates the number of times a filter does not match an logger event.";
                        }

                        leaf error-admin-state {
                            type yang:counter32;
                            description
                                "Indicates the number of times the logger event will be ignored due to
                                 admin state of EHS trigger entries is out-of-service.";
                        }

                        leaf error-filter {
                            type yang:counter32;
                            description
                                "Indicates the number of times the logger event will be ignored due to filter
                                 is not operational or is not configured in EHS trigger entries.";
                        }

                        leaf error-handler {
                            type yang:counter32;
                            description
                                "Indicates the number of times the logger event will be ignored due to handler
                                 is not operational or is not configured in EHS trigger entries.";
                        }

                        leaf trigger-count {
                            type yang:counter32;
                            description "Indicates the number of times script execution is triggered after filter match.";
                        }

                        leaf debounce-count {
                            type yang:counter32;
                            description "Indicates the number of times script is not executed due to debounce rule.";
                        }

                    } // container summary-entry-statistics

                    list entry {
                        key "id";
                        description "Enter the entry list instance";

                        leaf id {
                            type uint32 {
                                range "1..1500";
                            }
                            description "ID of the EHS event trigger entry";
                        }

                        leaf oper-state {
                            type types-sros:oper-state;
                            description "Indicates the operational state of the EHS Event Trigger Entry.";
                        }

                        container statistics {
                            description "Enter the statistics context";

                            leaf filter-match {
                                type yang:counter32;
                                description
                                    "Indicates the number of times a filter, for the specified trigger entry,
                                     matches an logger event.";
                            }

                            leaf filter-fail {
                                type yang:counter32;
                                description
                                    "Indicates the number of times a filter, for the specified trigger entry,
                                     does not match an logger event.";
                            }

                            leaf error-admin-state {
                                type yang:counter32;
                                description
                                    "Indicates the number of times the logger event will be ignored due to
                                     admin state of EHS trigger entry is out-of-service.";
                            }

                            leaf error-filter {
                                type yang:counter32;
                                description
                                    "Indicates the number of times the logger event will be ignored due to filter
                                     is not operational or is not configured in EHS trigger entry.";
                            }

                            leaf error-handler {
                                type yang:counter32;
                                description
                                    "Indicates the number of times the logger event will be ignored due to handler
                                     is not operational or is not configured in EHS trigger entry.";
                            }

                            leaf trigger-count {
                                type yang:counter32;
                                description
                                    "Indicates the number of times script execution is triggered after filter match
                                     for the specified trigger entry.";
                            }

                            leaf debounce-count {
                                type yang:counter32;
                                description
                                    "Indicates the number of times script is not executed due to debounce rule
                                     for the specified trigger entry.";
                            }

                        } // container statistics

                    } // list entry

                } // list bgp

                list bier {
                    key "event";
                    description "Enter the bier list instance";

                    leaf event {
                        type types-log:bier-events;
                        description "Log event as a trigger for one or more EHS handlers";
                    }

                    leaf oper-state {
                        type types-sros:oper-state;
                        description "Indicates the operational state of the EHS Event Trigger.";
                    }

                    container statistics {
                        description "Enter the statistics context";

                        leaf success {
                            type yang:counter32;
                            description
                                "Indicates the number of not ignored logger event occurrences
                                 associated with EHS trigger.";
                        }

                        leaf error-no-entry {
                            type yang:counter32;
                            description
                                "Indicates the number of ignored logger event occurrences associated
                                 with EHS trigger.

                                 Event is ignored due to no trigger entry configured for this trigger.";
                        }

                        leaf error-admin-state {
                            type yang:counter32;
                            description
                                "Indicates the number of ignored logger event occurrences associated
                                 with EHS trigger.

                                 Event is ignored due to trigger may be out-of-service.";
                        }

                        leaf total {
                            type yang:counter32;
                            description "Sum of success + error-no-entry + error-admin-state.";
                        }

                    } // container statistics

                    container summary-entry-statistics {
                        description "Enter the summary-entry-statistics context";

                        leaf filter-match {
                            type yang:counter32;
                            description "Indicates the number of times a filter matches an logger event.";
                        }

                        leaf filter-fail {
                            type yang:counter32;
                            description "Indicates the number of times a filter does not match an logger event.";
                        }

                        leaf error-admin-state {
                            type yang:counter32;
                            description
                                "Indicates the number of times the logger event will be ignored due to
                                 admin state of EHS trigger entries is out-of-service.";
                        }

                        leaf error-filter {
                            type yang:counter32;
                            description
                                "Indicates the number of times the logger event will be ignored due to filter
                                 is not operational or is not configured in EHS trigger entries.";
                        }

                        leaf error-handler {
                            type yang:counter32;
                            description
                                "Indicates the number of times the logger event will be ignored due to handler
                                 is not operational or is not configured in EHS trigger entries.";
                        }

                        leaf trigger-count {
                            type yang:counter32;
                            description "Indicates the number of times script execution is triggered after filter match.";
                        }

                        leaf debounce-count {
                            type yang:counter32;
                            description "Indicates the number of times script is not executed due to debounce rule.";
                        }

                    } // container summary-entry-statistics

                    list entry {
                        key "id";
                        description "Enter the entry list instance";

                        leaf id {
                            type uint32 {
                                range "1..1500";
                            }
                            description "ID of the EHS event trigger entry";
                        }

                        leaf oper-state {
                            type types-sros:oper-state;
                            description "Indicates the operational state of the EHS Event Trigger Entry.";
                        }

                        container statistics {
                            description "Enter the statistics context";

                            leaf filter-match {
                                type yang:counter32;
                                description
                                    "Indicates the number of times a filter, for the specified trigger entry,
                                     matches an logger event.";
                            }

                            leaf filter-fail {
                                type yang:counter32;
                                description
                                    "Indicates the number of times a filter, for the specified trigger entry,
                                     does not match an logger event.";
                            }

                            leaf error-admin-state {
                                type yang:counter32;
                                description
                                    "Indicates the number of times the logger event will be ignored due to
                                     admin state of EHS trigger entry is out-of-service.";
                            }

                            leaf error-filter {
                                type yang:counter32;
                                description
                                    "Indicates the number of times the logger event will be ignored due to filter
                                     is not operational or is not configured in EHS trigger entry.";
                            }

                            leaf error-handler {
                                type yang:counter32;
                                description
                                    "Indicates the number of times the logger event will be ignored due to handler
                                     is not operational or is not configured in EHS trigger entry.";
                            }

                            leaf trigger-count {
                                type yang:counter32;
                                description
                                    "Indicates the number of times script execution is triggered after filter match
                                     for the specified trigger entry.";
                            }

                            leaf debounce-count {
                                type yang:counter32;
                                description
                                    "Indicates the number of times script is not executed due to debounce rule
                                     for the specified trigger entry.";
                            }

                        } // container statistics

                    } // list entry

                } // list bier

                list calltrace {
                    key "event";
                    description "Enter the calltrace list instance";

                    leaf event {
                        type types-log:calltrace-events;
                        description "Log event as a trigger for one or more EHS handlers";
                    }

                    leaf oper-state {
                        type types-sros:oper-state;
                        description "Indicates the operational state of the EHS Event Trigger.";
                    }

                    container statistics {
                        description "Enter the statistics context";

                        leaf success {
                            type yang:counter32;
                            description
                                "Indicates the number of not ignored logger event occurrences
                                 associated with EHS trigger.";
                        }

                        leaf error-no-entry {
                            type yang:counter32;
                            description
                                "Indicates the number of ignored logger event occurrences associated
                                 with EHS trigger.

                                 Event is ignored due to no trigger entry configured for this trigger.";
                        }

                        leaf error-admin-state {
                            type yang:counter32;
                            description
                                "Indicates the number of ignored logger event occurrences associated
                                 with EHS trigger.

                                 Event is ignored due to trigger may be out-of-service.";
                        }

                        leaf total {
                            type yang:counter32;
                            description "Sum of success + error-no-entry + error-admin-state.";
                        }

                    } // container statistics

                    container summary-entry-statistics {
                        description "Enter the summary-entry-statistics context";

                        leaf filter-match {
                            type yang:counter32;
                            description "Indicates the number of times a filter matches an logger event.";
                        }

                        leaf filter-fail {
                            type yang:counter32;
                            description "Indicates the number of times a filter does not match an logger event.";
                        }

                        leaf error-admin-state {
                            type yang:counter32;
                            description
                                "Indicates the number of times the logger event will be ignored due to
                                 admin state of EHS trigger entries is out-of-service.";
                        }

                        leaf error-filter {
                            type yang:counter32;
                            description
                                "Indicates the number of times the logger event will be ignored due to filter
                                 is not operational or is not configured in EHS trigger entries.";
                        }

                        leaf error-handler {
                            type yang:counter32;
                            description
                                "Indicates the number of times the logger event will be ignored due to handler
                                 is not operational or is not configured in EHS trigger entries.";
                        }

                        leaf trigger-count {
                            type yang:counter32;
                            description "Indicates the number of times script execution is triggered after filter match.";
                        }

                        leaf debounce-count {
                            type yang:counter32;
                            description "Indicates the number of times script is not executed due to debounce rule.";
                        }

                    } // container summary-entry-statistics

                    list entry {
                        key "id";
                        description "Enter the entry list instance";

                        leaf id {
                            type uint32 {
                                range "1..1500";
                            }
                            description "ID of the EHS event trigger entry";
                        }

                        leaf oper-state {
                            type types-sros:oper-state;
                            description "Indicates the operational state of the EHS Event Trigger Entry.";
                        }

                        container statistics {
                            description "Enter the statistics context";

                            leaf filter-match {
                                type yang:counter32;
                                description
                                    "Indicates the number of times a filter, for the specified trigger entry,
                                     matches an logger event.";
                            }

                            leaf filter-fail {
                                type yang:counter32;
                                description
                                    "Indicates the number of times a filter, for the specified trigger entry,
                                     does not match an logger event.";
                            }

                            leaf error-admin-state {
                                type yang:counter32;
                                description
                                    "Indicates the number of times the logger event will be ignored due to
                                     admin state of EHS trigger entry is out-of-service.";
                            }

                            leaf error-filter {
                                type yang:counter32;
                                description
                                    "Indicates the number of times the logger event will be ignored due to filter
                                     is not operational or is not configured in EHS trigger entry.";
                            }

                            leaf error-handler {
                                type yang:counter32;
                                description
                                    "Indicates the number of times the logger event will be ignored due to handler
                                     is not operational or is not configured in EHS trigger entry.";
                            }

                            leaf trigger-count {
                                type yang:counter32;
                                description
                                    "Indicates the number of times script execution is triggered after filter match
                                     for the specified trigger entry.";
                            }

                            leaf debounce-count {
                                type yang:counter32;
                                description
                                    "Indicates the number of times script is not executed due to debounce rule
                                     for the specified trigger entry.";
                            }

                        } // container statistics

                    } // list entry

                } // list calltrace

                list cflowd {
                    key "event";
                    description "Enter the cflowd list instance";

                    leaf event {
                        type types-log:cflowd-events;
                        description "Log event as a trigger for one or more EHS handlers";
                    }

                    leaf oper-state {
                        type types-sros:oper-state;
                        description "Indicates the operational state of the EHS Event Trigger.";
                    }

                    container statistics {
                        description "Enter the statistics context";

                        leaf success {
                            type yang:counter32;
                            description
                                "Indicates the number of not ignored logger event occurrences
                                 associated with EHS trigger.";
                        }

                        leaf error-no-entry {
                            type yang:counter32;
                            description
                                "Indicates the number of ignored logger event occurrences associated
                                 with EHS trigger.

                                 Event is ignored due to no trigger entry configured for this trigger.";
                        }

                        leaf error-admin-state {
                            type yang:counter32;
                            description
                                "Indicates the number of ignored logger event occurrences associated
                                 with EHS trigger.

                                 Event is ignored due to trigger may be out-of-service.";
                        }

                        leaf total {
                            type yang:counter32;
                            description "Sum of success + error-no-entry + error-admin-state.";
                        }

                    } // container statistics

                    container summary-entry-statistics {
                        description "Enter the summary-entry-statistics context";

                        leaf filter-match {
                            type yang:counter32;
                            description "Indicates the number of times a filter matches an logger event.";
                        }

                        leaf filter-fail {
                            type yang:counter32;
                            description "Indicates the number of times a filter does not match an logger event.";
                        }

                        leaf error-admin-state {
                            type yang:counter32;
                            description
                                "Indicates the number of times the logger event will be ignored due to
                                 admin state of EHS trigger entries is out-of-service.";
                        }

                        leaf error-filter {
                            type yang:counter32;
                            description
                                "Indicates the number of times the logger event will be ignored due to filter
                                 is not operational or is not configured in EHS trigger entries.";
                        }

                        leaf error-handler {
                            type yang:counter32;
                            description
                                "Indicates the number of times the logger event will be ignored due to handler
                                 is not operational or is not configured in EHS trigger entries.";
                        }

                        leaf trigger-count {
                            type yang:counter32;
                            description "Indicates the number of times script execution is triggered after filter match.";
                        }

                        leaf debounce-count {
                            type yang:counter32;
                            description "Indicates the number of times script is not executed due to debounce rule.";
                        }

                    } // container summary-entry-statistics

                    list entry {
                        key "id";
                        description "Enter the entry list instance";

                        leaf id {
                            type uint32 {
                                range "1..1500";
                            }
                            description "ID of the EHS event trigger entry";
                        }

                        leaf oper-state {
                            type types-sros:oper-state;
                            description "Indicates the operational state of the EHS Event Trigger Entry.";
                        }

                        container statistics {
                            description "Enter the statistics context";

                            leaf filter-match {
                                type yang:counter32;
                                description
                                    "Indicates the number of times a filter, for the specified trigger entry,
                                     matches an logger event.";
                            }

                            leaf filter-fail {
                                type yang:counter32;
                                description
                                    "Indicates the number of times a filter, for the specified trigger entry,
                                     does not match an logger event.";
                            }

                            leaf error-admin-state {
                                type yang:counter32;
                                description
                                    "Indicates the number of times the logger event will be ignored due to
                                     admin state of EHS trigger entry is out-of-service.";
                            }

                            leaf error-filter {
                                type yang:counter32;
                                description
                                    "Indicates the number of times the logger event will be ignored due to filter
                                     is not operational or is not configured in EHS trigger entry.";
                            }

                            leaf error-handler {
                                type yang:counter32;
                                description
                                    "Indicates the number of times the logger event will be ignored due to handler
                                     is not operational or is not configured in EHS trigger entry.";
                            }

                            leaf trigger-count {
                                type yang:counter32;
                                description
                                    "Indicates the number of times script execution is triggered after filter match
                                     for the specified trigger entry.";
                            }

                            leaf debounce-count {
                                type yang:counter32;
                                description
                                    "Indicates the number of times script is not executed due to debounce rule
                                     for the specified trigger entry.";
                            }

                        } // container statistics

                    } // list entry

                } // list cflowd

                list chassis {
                    key "event";
                    description "Enter the chassis list instance";

                    leaf event {
                        type types-log:chassis-events;
                        description "Log event as a trigger for one or more EHS handlers";
                    }

                    leaf oper-state {
                        type types-sros:oper-state;
                        description "Indicates the operational state of the EHS Event Trigger.";
                    }

                    container statistics {
                        description "Enter the statistics context";

                        leaf success {
                            type yang:counter32;
                            description
                                "Indicates the number of not ignored logger event occurrences
                                 associated with EHS trigger.";
                        }

                        leaf error-no-entry {
                            type yang:counter32;
                            description
                                "Indicates the number of ignored logger event occurrences associated
                                 with EHS trigger.

                                 Event is ignored due to no trigger entry configured for this trigger.";
                        }

                        leaf error-admin-state {
                            type yang:counter32;
                            description
                                "Indicates the number of ignored logger event occurrences associated
                                 with EHS trigger.

                                 Event is ignored due to trigger may be out-of-service.";
                        }

                        leaf total {
                            type yang:counter32;
                            description "Sum of success + error-no-entry + error-admin-state.";
                        }

                    } // container statistics

                    container summary-entry-statistics {
                        description "Enter the summary-entry-statistics context";

                        leaf filter-match {
                            type yang:counter32;
                            description "Indicates the number of times a filter matches an logger event.";
                        }

                        leaf filter-fail {
                            type yang:counter32;
                            description "Indicates the number of times a filter does not match an logger event.";
                        }

                        leaf error-admin-state {
                            type yang:counter32;
                            description
                                "Indicates the number of times the logger event will be ignored due to
                                 admin state of EHS trigger entries is out-of-service.";
                        }

                        leaf error-filter {
                            type yang:counter32;
                            description
                                "Indicates the number of times the logger event will be ignored due to filter
                                 is not operational or is not configured in EHS trigger entries.";
                        }

                        leaf error-handler {
                            type yang:counter32;
                            description
                                "Indicates the number of times the logger event will be ignored due to handler
                                 is not operational or is not configured in EHS trigger entries.";
                        }

                        leaf trigger-count {
                            type yang:counter32;
                            description "Indicates the number of times script execution is triggered after filter match.";
                        }

                        leaf debounce-count {
                            type yang:counter32;
                            description "Indicates the number of times script is not executed due to debounce rule.";
                        }

                    } // container summary-entry-statistics

                    list entry {
                        key "id";
                        description "Enter the entry list instance";

                        leaf id {
                            type uint32 {
                                range "1..1500";
                            }
                            description "ID of the EHS event trigger entry";
                        }

                        leaf oper-state {
                            type types-sros:oper-state;
                            description "Indicates the operational state of the EHS Event Trigger Entry.";
                        }

                        container statistics {
                            description "Enter the statistics context";

                            leaf filter-match {
                                type yang:counter32;
                                description
                                    "Indicates the number of times a filter, for the specified trigger entry,
                                     matches an logger event.";
                            }

                            leaf filter-fail {
                                type yang:counter32;
                                description
                                    "Indicates the number of times a filter, for the specified trigger entry,
                                     does not match an logger event.";
                            }

                            leaf error-admin-state {
                                type yang:counter32;
                                description
                                    "Indicates the number of times the logger event will be ignored due to
                                     admin state of EHS trigger entry is out-of-service.";
                            }

                            leaf error-filter {
                                type yang:counter32;
                                description
                                    "Indicates the number of times the logger event will be ignored due to filter
                                     is not operational or is not configured in EHS trigger entry.";
                            }

                            leaf error-handler {
                                type yang:counter32;
                                description
                                    "Indicates the number of times the logger event will be ignored due to handler
                                     is not operational or is not configured in EHS trigger entry.";
                            }

                            leaf trigger-count {
                                type yang:counter32;
                                description
                                    "Indicates the number of times script execution is triggered after filter match
                                     for the specified trigger entry.";
                            }

                            leaf debounce-count {
                                type yang:counter32;
                                description
                                    "Indicates the number of times script is not executed due to debounce rule
                                     for the specified trigger entry.";
                            }

                        } // container statistics

                    } // list entry

                } // list chassis

                list debug {
                    key "event";
                    description "Enter the debug list instance";

                    leaf event {
                        type types-log:debug-events;
                        description "Log event as a trigger for one or more EHS handlers";
                    }

                    leaf oper-state {
                        type types-sros:oper-state;
                        description "Indicates the operational state of the EHS Event Trigger.";
                    }

                    container statistics {
                        description "Enter the statistics context";

                        leaf success {
                            type yang:counter32;
                            description
                                "Indicates the number of not ignored logger event occurrences
                                 associated with EHS trigger.";
                        }

                        leaf error-no-entry {
                            type yang:counter32;
                            description
                                "Indicates the number of ignored logger event occurrences associated
                                 with EHS trigger.

                                 Event is ignored due to no trigger entry configured for this trigger.";
                        }

                        leaf error-admin-state {
                            type yang:counter32;
                            description
                                "Indicates the number of ignored logger event occurrences associated
                                 with EHS trigger.

                                 Event is ignored due to trigger may be out-of-service.";
                        }

                        leaf total {
                            type yang:counter32;
                            description "Sum of success + error-no-entry + error-admin-state.";
                        }

                    } // container statistics

                    container summary-entry-statistics {
                        description "Enter the summary-entry-statistics context";

                        leaf filter-match {
                            type yang:counter32;
                            description "Indicates the number of times a filter matches an logger event.";
                        }

                        leaf filter-fail {
                            type yang:counter32;
                            description "Indicates the number of times a filter does not match an logger event.";
                        }

                        leaf error-admin-state {
                            type yang:counter32;
                            description
                                "Indicates the number of times the logger event will be ignored due to
                                 admin state of EHS trigger entries is out-of-service.";
                        }

                        leaf error-filter {
                            type yang:counter32;
                            description
                                "Indicates the number of times the logger event will be ignored due to filter
                                 is not operational or is not configured in EHS trigger entries.";
                        }

                        leaf error-handler {
                            type yang:counter32;
                            description
                                "Indicates the number of times the logger event will be ignored due to handler
                                 is not operational or is not configured in EHS trigger entries.";
                        }

                        leaf trigger-count {
                            type yang:counter32;
                            description "Indicates the number of times script execution is triggered after filter match.";
                        }

                        leaf debounce-count {
                            type yang:counter32;
                            description "Indicates the number of times script is not executed due to debounce rule.";
                        }

                    } // container summary-entry-statistics

                    list entry {
                        key "id";
                        description "Enter the entry list instance";

                        leaf id {
                            type uint32 {
                                range "1..1500";
                            }
                            description "ID of the EHS event trigger entry";
                        }

                        leaf oper-state {
                            type types-sros:oper-state;
                            description "Indicates the operational state of the EHS Event Trigger Entry.";
                        }

                        container statistics {
                            description "Enter the statistics context";

                            leaf filter-match {
                                type yang:counter32;
                                description
                                    "Indicates the number of times a filter, for the specified trigger entry,
                                     matches an logger event.";
                            }

                            leaf filter-fail {
                                type yang:counter32;
                                description
                                    "Indicates the number of times a filter, for the specified trigger entry,
                                     does not match an logger event.";
                            }

                            leaf error-admin-state {
                                type yang:counter32;
                                description
                                    "Indicates the number of times the logger event will be ignored due to
                                     admin state of EHS trigger entry is out-of-service.";
                            }

                            leaf error-filter {
                                type yang:counter32;
                                description
                                    "Indicates the number of times the logger event will be ignored due to filter
                                     is not operational or is not configured in EHS trigger entry.";
                            }

                            leaf error-handler {
                                type yang:counter32;
                                description
                                    "Indicates the number of times the logger event will be ignored due to handler
                                     is not operational or is not configured in EHS trigger entry.";
                            }

                            leaf trigger-count {
                                type yang:counter32;
                                description
                                    "Indicates the number of times script execution is triggered after filter match
                                     for the specified trigger entry.";
                            }

                            leaf debounce-count {
                                type yang:counter32;
                                description
                                    "Indicates the number of times script is not executed due to debounce rule
                                     for the specified trigger entry.";
                            }

                        } // container statistics

                    } // list entry

                } // list debug

                list dhcp {
                    key "event";
                    description "Enter the dhcp list instance";

                    leaf event {
                        type types-log:dhcp-events;
                        description "Log event as a trigger for one or more EHS handlers";
                    }

                    leaf oper-state {
                        type types-sros:oper-state;
                        description "Indicates the operational state of the EHS Event Trigger.";
                    }

                    container statistics {
                        description "Enter the statistics context";

                        leaf success {
                            type yang:counter32;
                            description
                                "Indicates the number of not ignored logger event occurrences
                                 associated with EHS trigger.";
                        }

                        leaf error-no-entry {
                            type yang:counter32;
                            description
                                "Indicates the number of ignored logger event occurrences associated
                                 with EHS trigger.

                                 Event is ignored due to no trigger entry configured for this trigger.";
                        }

                        leaf error-admin-state {
                            type yang:counter32;
                            description
                                "Indicates the number of ignored logger event occurrences associated
                                 with EHS trigger.

                                 Event is ignored due to trigger may be out-of-service.";
                        }

                        leaf total {
                            type yang:counter32;
                            description "Sum of success + error-no-entry + error-admin-state.";
                        }

                    } // container statistics

                    container summary-entry-statistics {
                        description "Enter the summary-entry-statistics context";

                        leaf filter-match {
                            type yang:counter32;
                            description "Indicates the number of times a filter matches an logger event.";
                        }

                        leaf filter-fail {
                            type yang:counter32;
                            description "Indicates the number of times a filter does not match an logger event.";
                        }

                        leaf error-admin-state {
                            type yang:counter32;
                            description
                                "Indicates the number of times the logger event will be ignored due to
                                 admin state of EHS trigger entries is out-of-service.";
                        }

                        leaf error-filter {
                            type yang:counter32;
                            description
                                "Indicates the number of times the logger event will be ignored due to filter
                                 is not operational or is not configured in EHS trigger entries.";
                        }

                        leaf error-handler {
                            type yang:counter32;
                            description
                                "Indicates the number of times the logger event will be ignored due to handler
                                 is not operational or is not configured in EHS trigger entries.";
                        }

                        leaf trigger-count {
                            type yang:counter32;
                            description "Indicates the number of times script execution is triggered after filter match.";
                        }

                        leaf debounce-count {
                            type yang:counter32;
                            description "Indicates the number of times script is not executed due to debounce rule.";
                        }

                    } // container summary-entry-statistics

                    list entry {
                        key "id";
                        description "Enter the entry list instance";

                        leaf id {
                            type uint32 {
                                range "1..1500";
                            }
                            description "ID of the EHS event trigger entry";
                        }

                        leaf oper-state {
                            type types-sros:oper-state;
                            description "Indicates the operational state of the EHS Event Trigger Entry.";
                        }

                        container statistics {
                            description "Enter the statistics context";

                            leaf filter-match {
                                type yang:counter32;
                                description
                                    "Indicates the number of times a filter, for the specified trigger entry,
                                     matches an logger event.";
                            }

                            leaf filter-fail {
                                type yang:counter32;
                                description
                                    "Indicates the number of times a filter, for the specified trigger entry,
                                     does not match an logger event.";
                            }

                            leaf error-admin-state {
                                type yang:counter32;
                                description
                                    "Indicates the number of times the logger event will be ignored due to
                                     admin state of EHS trigger entry is out-of-service.";
                            }

                            leaf error-filter {
                                type yang:counter32;
                                description
                                    "Indicates the number of times the logger event will be ignored due to filter
                                     is not operational or is not configured in EHS trigger entry.";
                            }

                            leaf error-handler {
                                type yang:counter32;
                                description
                                    "Indicates the number of times the logger event will be ignored due to handler
                                     is not operational or is not configured in EHS trigger entry.";
                            }

                            leaf trigger-count {
                                type yang:counter32;
                                description
                                    "Indicates the number of times script execution is triggered after filter match
                                     for the specified trigger entry.";
                            }

                            leaf debounce-count {
                                type yang:counter32;
                                description
                                    "Indicates the number of times script is not executed due to debounce rule
                                     for the specified trigger entry.";
                            }

                        } // container statistics

                    } // list entry

                } // list dhcp

                list dhcps {
                    key "event";
                    description "Enter the dhcps list instance";

                    leaf event {
                        type types-log:dhcps-events;
                        description "Log event as a trigger for one or more EHS handlers";
                    }

                    leaf oper-state {
                        type types-sros:oper-state;
                        description "Indicates the operational state of the EHS Event Trigger.";
                    }

                    container statistics {
                        description "Enter the statistics context";

                        leaf success {
                            type yang:counter32;
                            description
                                "Indicates the number of not ignored logger event occurrences
                                 associated with EHS trigger.";
                        }

                        leaf error-no-entry {
                            type yang:counter32;
                            description
                                "Indicates the number of ignored logger event occurrences associated
                                 with EHS trigger.

                                 Event is ignored due to no trigger entry configured for this trigger.";
                        }

                        leaf error-admin-state {
                            type yang:counter32;
                            description
                                "Indicates the number of ignored logger event occurrences associated
                                 with EHS trigger.

                                 Event is ignored due to trigger may be out-of-service.";
                        }

                        leaf total {
                            type yang:counter32;
                            description "Sum of success + error-no-entry + error-admin-state.";
                        }

                    } // container statistics

                    container summary-entry-statistics {
                        description "Enter the summary-entry-statistics context";

                        leaf filter-match {
                            type yang:counter32;
                            description "Indicates the number of times a filter matches an logger event.";
                        }

                        leaf filter-fail {
                            type yang:counter32;
                            description "Indicates the number of times a filter does not match an logger event.";
                        }

                        leaf error-admin-state {
                            type yang:counter32;
                            description
                                "Indicates the number of times the logger event will be ignored due to
                                 admin state of EHS trigger entries is out-of-service.";
                        }

                        leaf error-filter {
                            type yang:counter32;
                            description
                                "Indicates the number of times the logger event will be ignored due to filter
                                 is not operational or is not configured in EHS trigger entries.";
                        }

                        leaf error-handler {
                            type yang:counter32;
                            description
                                "Indicates the number of times the logger event will be ignored due to handler
                                 is not operational or is not configured in EHS trigger entries.";
                        }

                        leaf trigger-count {
                            type yang:counter32;
                            description "Indicates the number of times script execution is triggered after filter match.";
                        }

                        leaf debounce-count {
                            type yang:counter32;
                            description "Indicates the number of times script is not executed due to debounce rule.";
                        }

                    } // container summary-entry-statistics

                    list entry {
                        key "id";
                        description "Enter the entry list instance";

                        leaf id {
                            type uint32 {
                                range "1..1500";
                            }
                            description "ID of the EHS event trigger entry";
                        }

                        leaf oper-state {
                            type types-sros:oper-state;
                            description "Indicates the operational state of the EHS Event Trigger Entry.";
                        }

                        container statistics {
                            description "Enter the statistics context";

                            leaf filter-match {
                                type yang:counter32;
                                description
                                    "Indicates the number of times a filter, for the specified trigger entry,
                                     matches an logger event.";
                            }

                            leaf filter-fail {
                                type yang:counter32;
                                description
                                    "Indicates the number of times a filter, for the specified trigger entry,
                                     does not match an logger event.";
                            }

                            leaf error-admin-state {
                                type yang:counter32;
                                description
                                    "Indicates the number of times the logger event will be ignored due to
                                     admin state of EHS trigger entry is out-of-service.";
                            }

                            leaf error-filter {
                                type yang:counter32;
                                description
                                    "Indicates the number of times the logger event will be ignored due to filter
                                     is not operational or is not configured in EHS trigger entry.";
                            }

                            leaf error-handler {
                                type yang:counter32;
                                description
                                    "Indicates the number of times the logger event will be ignored due to handler
                                     is not operational or is not configured in EHS trigger entry.";
                            }

                            leaf trigger-count {
                                type yang:counter32;
                                description
                                    "Indicates the number of times script execution is triggered after filter match
                                     for the specified trigger entry.";
                            }

                            leaf debounce-count {
                                type yang:counter32;
                                description
                                    "Indicates the number of times script is not executed due to debounce rule
                                     for the specified trigger entry.";
                            }

                        } // container statistics

                    } // list entry

                } // list dhcps

                list diameter {
                    key "event";
                    description "Enter the diameter list instance";

                    leaf event {
                        type types-log:diameter-events;
                        description "Log event as a trigger for one or more EHS handlers";
                    }

                    leaf oper-state {
                        type types-sros:oper-state;
                        description "Indicates the operational state of the EHS Event Trigger.";
                    }

                    container statistics {
                        description "Enter the statistics context";

                        leaf success {
                            type yang:counter32;
                            description
                                "Indicates the number of not ignored logger event occurrences
                                 associated with EHS trigger.";
                        }

                        leaf error-no-entry {
                            type yang:counter32;
                            description
                                "Indicates the number of ignored logger event occurrences associated
                                 with EHS trigger.

                                 Event is ignored due to no trigger entry configured for this trigger.";
                        }

                        leaf error-admin-state {
                            type yang:counter32;
                            description
                                "Indicates the number of ignored logger event occurrences associated
                                 with EHS trigger.

                                 Event is ignored due to trigger may be out-of-service.";
                        }

                        leaf total {
                            type yang:counter32;
                            description "Sum of success + error-no-entry + error-admin-state.";
                        }

                    } // container statistics

                    container summary-entry-statistics {
                        description "Enter the summary-entry-statistics context";

                        leaf filter-match {
                            type yang:counter32;
                            description "Indicates the number of times a filter matches an logger event.";
                        }

                        leaf filter-fail {
                            type yang:counter32;
                            description "Indicates the number of times a filter does not match an logger event.";
                        }

                        leaf error-admin-state {
                            type yang:counter32;
                            description
                                "Indicates the number of times the logger event will be ignored due to
                                 admin state of EHS trigger entries is out-of-service.";
                        }

                        leaf error-filter {
                            type yang:counter32;
                            description
                                "Indicates the number of times the logger event will be ignored due to filter
                                 is not operational or is not configured in EHS trigger entries.";
                        }

                        leaf error-handler {
                            type yang:counter32;
                            description
                                "Indicates the number of times the logger event will be ignored due to handler
                                 is not operational or is not configured in EHS trigger entries.";
                        }

                        leaf trigger-count {
                            type yang:counter32;
                            description "Indicates the number of times script execution is triggered after filter match.";
                        }

                        leaf debounce-count {
                            type yang:counter32;
                            description "Indicates the number of times script is not executed due to debounce rule.";
                        }

                    } // container summary-entry-statistics

                    list entry {
                        key "id";
                        description "Enter the entry list instance";

                        leaf id {
                            type uint32 {
                                range "1..1500";
                            }
                            description "ID of the EHS event trigger entry";
                        }

                        leaf oper-state {
                            type types-sros:oper-state;
                            description "Indicates the operational state of the EHS Event Trigger Entry.";
                        }

                        container statistics {
                            description "Enter the statistics context";

                            leaf filter-match {
                                type yang:counter32;
                                description
                                    "Indicates the number of times a filter, for the specified trigger entry,
                                     matches an logger event.";
                            }

                            leaf filter-fail {
                                type yang:counter32;
                                description
                                    "Indicates the number of times a filter, for the specified trigger entry,
                                     does not match an logger event.";
                            }

                            leaf error-admin-state {
                                type yang:counter32;
                                description
                                    "Indicates the number of times the logger event will be ignored due to
                                     admin state of EHS trigger entry is out-of-service.";
                            }

                            leaf error-filter {
                                type yang:counter32;
                                description
                                    "Indicates the number of times the logger event will be ignored due to filter
                                     is not operational or is not configured in EHS trigger entry.";
                            }

                            leaf error-handler {
                                type yang:counter32;
                                description
                                    "Indicates the number of times the logger event will be ignored due to handler
                                     is not operational or is not configured in EHS trigger entry.";
                            }

                            leaf trigger-count {
                                type yang:counter32;
                                description
                                    "Indicates the number of times script execution is triggered after filter match
                                     for the specified trigger entry.";
                            }

                            leaf debounce-count {
                                type yang:counter32;
                                description
                                    "Indicates the number of times script is not executed due to debounce rule
                                     for the specified trigger entry.";
                            }

                        } // container statistics

                    } // list entry

                } // list diameter

                list dynsvc {
                    key "event";
                    description "Enter the dynsvc list instance";

                    leaf event {
                        type types-log:dynsvc-events;
                        description "Log event as a trigger for one or more EHS handlers";
                    }

                    leaf oper-state {
                        type types-sros:oper-state;
                        description "Indicates the operational state of the EHS Event Trigger.";
                    }

                    container statistics {
                        description "Enter the statistics context";

                        leaf success {
                            type yang:counter32;
                            description
                                "Indicates the number of not ignored logger event occurrences
                                 associated with EHS trigger.";
                        }

                        leaf error-no-entry {
                            type yang:counter32;
                            description
                                "Indicates the number of ignored logger event occurrences associated
                                 with EHS trigger.

                                 Event is ignored due to no trigger entry configured for this trigger.";
                        }

                        leaf error-admin-state {
                            type yang:counter32;
                            description
                                "Indicates the number of ignored logger event occurrences associated
                                 with EHS trigger.

                                 Event is ignored due to trigger may be out-of-service.";
                        }

                        leaf total {
                            type yang:counter32;
                            description "Sum of success + error-no-entry + error-admin-state.";
                        }

                    } // container statistics

                    container summary-entry-statistics {
                        description "Enter the summary-entry-statistics context";

                        leaf filter-match {
                            type yang:counter32;
                            description "Indicates the number of times a filter matches an logger event.";
                        }

                        leaf filter-fail {
                            type yang:counter32;
                            description "Indicates the number of times a filter does not match an logger event.";
                        }

                        leaf error-admin-state {
                            type yang:counter32;
                            description
                                "Indicates the number of times the logger event will be ignored due to
                                 admin state of EHS trigger entries is out-of-service.";
                        }

                        leaf error-filter {
                            type yang:counter32;
                            description
                                "Indicates the number of times the logger event will be ignored due to filter
                                 is not operational or is not configured in EHS trigger entries.";
                        }

                        leaf error-handler {
                            type yang:counter32;
                            description
                                "Indicates the number of times the logger event will be ignored due to handler
                                 is not operational or is not configured in EHS trigger entries.";
                        }

                        leaf trigger-count {
                            type yang:counter32;
                            description "Indicates the number of times script execution is triggered after filter match.";
                        }

                        leaf debounce-count {
                            type yang:counter32;
                            description "Indicates the number of times script is not executed due to debounce rule.";
                        }

                    } // container summary-entry-statistics

                    list entry {
                        key "id";
                        description "Enter the entry list instance";

                        leaf id {
                            type uint32 {
                                range "1..1500";
                            }
                            description "ID of the EHS event trigger entry";
                        }

                        leaf oper-state {
                            type types-sros:oper-state;
                            description "Indicates the operational state of the EHS Event Trigger Entry.";
                        }

                        container statistics {
                            description "Enter the statistics context";

                            leaf filter-match {
                                type yang:counter32;
                                description
                                    "Indicates the number of times a filter, for the specified trigger entry,
                                     matches an logger event.";
                            }

                            leaf filter-fail {
                                type yang:counter32;
                                description
                                    "Indicates the number of times a filter, for the specified trigger entry,
                                     does not match an logger event.";
                            }

                            leaf error-admin-state {
                                type yang:counter32;
                                description
                                    "Indicates the number of times the logger event will be ignored due to
                                     admin state of EHS trigger entry is out-of-service.";
                            }

                            leaf error-filter {
                                type yang:counter32;
                                description
                                    "Indicates the number of times the logger event will be ignored due to filter
                                     is not operational or is not configured in EHS trigger entry.";
                            }

                            leaf error-handler {
                                type yang:counter32;
                                description
                                    "Indicates the number of times the logger event will be ignored due to handler
                                     is not operational or is not configured in EHS trigger entry.";
                            }

                            leaf trigger-count {
                                type yang:counter32;
                                description
                                    "Indicates the number of times script execution is triggered after filter match
                                     for the specified trigger entry.";
                            }

                            leaf debounce-count {
                                type yang:counter32;
                                description
                                    "Indicates the number of times script is not executed due to debounce rule
                                     for the specified trigger entry.";
                            }

                        } // container statistics

                    } // list entry

                } // list dynsvc

                list efm-oam {
                    key "event";
                    description "Enter the efm-oam list instance";

                    leaf event {
                        type types-log:efm-oam-events;
                        description "Log event as a trigger for one or more EHS handlers";
                    }

                    leaf oper-state {
                        type types-sros:oper-state;
                        description "Indicates the operational state of the EHS Event Trigger.";
                    }

                    container statistics {
                        description "Enter the statistics context";

                        leaf success {
                            type yang:counter32;
                            description
                                "Indicates the number of not ignored logger event occurrences
                                 associated with EHS trigger.";
                        }

                        leaf error-no-entry {
                            type yang:counter32;
                            description
                                "Indicates the number of ignored logger event occurrences associated
                                 with EHS trigger.

                                 Event is ignored due to no trigger entry configured for this trigger.";
                        }

                        leaf error-admin-state {
                            type yang:counter32;
                            description
                                "Indicates the number of ignored logger event occurrences associated
                                 with EHS trigger.

                                 Event is ignored due to trigger may be out-of-service.";
                        }

                        leaf total {
                            type yang:counter32;
                            description "Sum of success + error-no-entry + error-admin-state.";
                        }

                    } // container statistics

                    container summary-entry-statistics {
                        description "Enter the summary-entry-statistics context";

                        leaf filter-match {
                            type yang:counter32;
                            description "Indicates the number of times a filter matches an logger event.";
                        }

                        leaf filter-fail {
                            type yang:counter32;
                            description "Indicates the number of times a filter does not match an logger event.";
                        }

                        leaf error-admin-state {
                            type yang:counter32;
                            description
                                "Indicates the number of times the logger event will be ignored due to
                                 admin state of EHS trigger entries is out-of-service.";
                        }

                        leaf error-filter {
                            type yang:counter32;
                            description
                                "Indicates the number of times the logger event will be ignored due to filter
                                 is not operational or is not configured in EHS trigger entries.";
                        }

                        leaf error-handler {
                            type yang:counter32;
                            description
                                "Indicates the number of times the logger event will be ignored due to handler
                                 is not operational or is not configured in EHS trigger entries.";
                        }

                        leaf trigger-count {
                            type yang:counter32;
                            description "Indicates the number of times script execution is triggered after filter match.";
                        }

                        leaf debounce-count {
                            type yang:counter32;
                            description "Indicates the number of times script is not executed due to debounce rule.";
                        }

                    } // container summary-entry-statistics

                    list entry {
                        key "id";
                        description "Enter the entry list instance";

                        leaf id {
                            type uint32 {
                                range "1..1500";
                            }
                            description "ID of the EHS event trigger entry";
                        }

                        leaf oper-state {
                            type types-sros:oper-state;
                            description "Indicates the operational state of the EHS Event Trigger Entry.";
                        }

                        container statistics {
                            description "Enter the statistics context";

                            leaf filter-match {
                                type yang:counter32;
                                description
                                    "Indicates the number of times a filter, for the specified trigger entry,
                                     matches an logger event.";
                            }

                            leaf filter-fail {
                                type yang:counter32;
                                description
                                    "Indicates the number of times a filter, for the specified trigger entry,
                                     does not match an logger event.";
                            }

                            leaf error-admin-state {
                                type yang:counter32;
                                description
                                    "Indicates the number of times the logger event will be ignored due to
                                     admin state of EHS trigger entry is out-of-service.";
                            }

                            leaf error-filter {
                                type yang:counter32;
                                description
                                    "Indicates the number of times the logger event will be ignored due to filter
                                     is not operational or is not configured in EHS trigger entry.";
                            }

                            leaf error-handler {
                                type yang:counter32;
                                description
                                    "Indicates the number of times the logger event will be ignored due to handler
                                     is not operational or is not configured in EHS trigger entry.";
                            }

                            leaf trigger-count {
                                type yang:counter32;
                                description
                                    "Indicates the number of times script execution is triggered after filter match
                                     for the specified trigger entry.";
                            }

                            leaf debounce-count {
                                type yang:counter32;
                                description
                                    "Indicates the number of times script is not executed due to debounce rule
                                     for the specified trigger entry.";
                            }

                        } // container statistics

                    } // list entry

                } // list efm-oam

                list elmi {
                    key "event";
                    description "Enter the elmi list instance";

                    leaf event {
                        type types-log:elmi-events;
                        description "Log event as a trigger for one or more EHS handlers";
                    }

                    leaf oper-state {
                        type types-sros:oper-state;
                        description "Indicates the operational state of the EHS Event Trigger.";
                    }

                    container statistics {
                        description "Enter the statistics context";

                        leaf success {
                            type yang:counter32;
                            description
                                "Indicates the number of not ignored logger event occurrences
                                 associated with EHS trigger.";
                        }

                        leaf error-no-entry {
                            type yang:counter32;
                            description
                                "Indicates the number of ignored logger event occurrences associated
                                 with EHS trigger.

                                 Event is ignored due to no trigger entry configured for this trigger.";
                        }

                        leaf error-admin-state {
                            type yang:counter32;
                            description
                                "Indicates the number of ignored logger event occurrences associated
                                 with EHS trigger.

                                 Event is ignored due to trigger may be out-of-service.";
                        }

                        leaf total {
                            type yang:counter32;
                            description "Sum of success + error-no-entry + error-admin-state.";
                        }

                    } // container statistics

                    container summary-entry-statistics {
                        description "Enter the summary-entry-statistics context";

                        leaf filter-match {
                            type yang:counter32;
                            description "Indicates the number of times a filter matches an logger event.";
                        }

                        leaf filter-fail {
                            type yang:counter32;
                            description "Indicates the number of times a filter does not match an logger event.";
                        }

                        leaf error-admin-state {
                            type yang:counter32;
                            description
                                "Indicates the number of times the logger event will be ignored due to
                                 admin state of EHS trigger entries is out-of-service.";
                        }

                        leaf error-filter {
                            type yang:counter32;
                            description
                                "Indicates the number of times the logger event will be ignored due to filter
                                 is not operational or is not configured in EHS trigger entries.";
                        }

                        leaf error-handler {
                            type yang:counter32;
                            description
                                "Indicates the number of times the logger event will be ignored due to handler
                                 is not operational or is not configured in EHS trigger entries.";
                        }

                        leaf trigger-count {
                            type yang:counter32;
                            description "Indicates the number of times script execution is triggered after filter match.";
                        }

                        leaf debounce-count {
                            type yang:counter32;
                            description "Indicates the number of times script is not executed due to debounce rule.";
                        }

                    } // container summary-entry-statistics

                    list entry {
                        key "id";
                        description "Enter the entry list instance";

                        leaf id {
                            type uint32 {
                                range "1..1500";
                            }
                            description "ID of the EHS event trigger entry";
                        }

                        leaf oper-state {
                            type types-sros:oper-state;
                            description "Indicates the operational state of the EHS Event Trigger Entry.";
                        }

                        container statistics {
                            description "Enter the statistics context";

                            leaf filter-match {
                                type yang:counter32;
                                description
                                    "Indicates the number of times a filter, for the specified trigger entry,
                                     matches an logger event.";
                            }

                            leaf filter-fail {
                                type yang:counter32;
                                description
                                    "Indicates the number of times a filter, for the specified trigger entry,
                                     does not match an logger event.";
                            }

                            leaf error-admin-state {
                                type yang:counter32;
                                description
                                    "Indicates the number of times the logger event will be ignored due to
                                     admin state of EHS trigger entry is out-of-service.";
                            }

                            leaf error-filter {
                                type yang:counter32;
                                description
                                    "Indicates the number of times the logger event will be ignored due to filter
                                     is not operational or is not configured in EHS trigger entry.";
                            }

                            leaf error-handler {
                                type yang:counter32;
                                description
                                    "Indicates the number of times the logger event will be ignored due to handler
                                     is not operational or is not configured in EHS trigger entry.";
                            }

                            leaf trigger-count {
                                type yang:counter32;
                                description
                                    "Indicates the number of times script execution is triggered after filter match
                                     for the specified trigger entry.";
                            }

                            leaf debounce-count {
                                type yang:counter32;
                                description
                                    "Indicates the number of times script is not executed due to debounce rule
                                     for the specified trigger entry.";
                            }

                        } // container statistics

                    } // list entry

                } // list elmi

                list ering {
                    key "event";
                    description "Enter the ering list instance";

                    leaf event {
                        type types-log:ethring-events;
                        description "Log event as a trigger for one or more EHS handlers";
                    }

                    leaf oper-state {
                        type types-sros:oper-state;
                        description "Indicates the operational state of the EHS Event Trigger.";
                    }

                    container statistics {
                        description "Enter the statistics context";

                        leaf success {
                            type yang:counter32;
                            description
                                "Indicates the number of not ignored logger event occurrences
                                 associated with EHS trigger.";
                        }

                        leaf error-no-entry {
                            type yang:counter32;
                            description
                                "Indicates the number of ignored logger event occurrences associated
                                 with EHS trigger.

                                 Event is ignored due to no trigger entry configured for this trigger.";
                        }

                        leaf error-admin-state {
                            type yang:counter32;
                            description
                                "Indicates the number of ignored logger event occurrences associated
                                 with EHS trigger.

                                 Event is ignored due to trigger may be out-of-service.";
                        }

                        leaf total {
                            type yang:counter32;
                            description "Sum of success + error-no-entry + error-admin-state.";
                        }

                    } // container statistics

                    container summary-entry-statistics {
                        description "Enter the summary-entry-statistics context";

                        leaf filter-match {
                            type yang:counter32;
                            description "Indicates the number of times a filter matches an logger event.";
                        }

                        leaf filter-fail {
                            type yang:counter32;
                            description "Indicates the number of times a filter does not match an logger event.";
                        }

                        leaf error-admin-state {
                            type yang:counter32;
                            description
                                "Indicates the number of times the logger event will be ignored due to
                                 admin state of EHS trigger entries is out-of-service.";
                        }

                        leaf error-filter {
                            type yang:counter32;
                            description
                                "Indicates the number of times the logger event will be ignored due to filter
                                 is not operational or is not configured in EHS trigger entries.";
                        }

                        leaf error-handler {
                            type yang:counter32;
                            description
                                "Indicates the number of times the logger event will be ignored due to handler
                                 is not operational or is not configured in EHS trigger entries.";
                        }

                        leaf trigger-count {
                            type yang:counter32;
                            description "Indicates the number of times script execution is triggered after filter match.";
                        }

                        leaf debounce-count {
                            type yang:counter32;
                            description "Indicates the number of times script is not executed due to debounce rule.";
                        }

                    } // container summary-entry-statistics

                    list entry {
                        key "id";
                        description "Enter the entry list instance";

                        leaf id {
                            type uint32 {
                                range "1..1500";
                            }
                            description "ID of the EHS event trigger entry";
                        }

                        leaf oper-state {
                            type types-sros:oper-state;
                            description "Indicates the operational state of the EHS Event Trigger Entry.";
                        }

                        container statistics {
                            description "Enter the statistics context";

                            leaf filter-match {
                                type yang:counter32;
                                description
                                    "Indicates the number of times a filter, for the specified trigger entry,
                                     matches an logger event.";
                            }

                            leaf filter-fail {
                                type yang:counter32;
                                description
                                    "Indicates the number of times a filter, for the specified trigger entry,
                                     does not match an logger event.";
                            }

                            leaf error-admin-state {
                                type yang:counter32;
                                description
                                    "Indicates the number of times the logger event will be ignored due to
                                     admin state of EHS trigger entry is out-of-service.";
                            }

                            leaf error-filter {
                                type yang:counter32;
                                description
                                    "Indicates the number of times the logger event will be ignored due to filter
                                     is not operational or is not configured in EHS trigger entry.";
                            }

                            leaf error-handler {
                                type yang:counter32;
                                description
                                    "Indicates the number of times the logger event will be ignored due to handler
                                     is not operational or is not configured in EHS trigger entry.";
                            }

                            leaf trigger-count {
                                type yang:counter32;
                                description
                                    "Indicates the number of times script execution is triggered after filter match
                                     for the specified trigger entry.";
                            }

                            leaf debounce-count {
                                type yang:counter32;
                                description
                                    "Indicates the number of times script is not executed due to debounce rule
                                     for the specified trigger entry.";
                            }

                        } // container statistics

                    } // list entry

                } // list ering

                list eth-cfm {
                    key "event";
                    description "Enter the eth-cfm list instance";

                    leaf event {
                        type types-log:ethcfm-events;
                        description "Log event as a trigger for one or more EHS handlers";
                    }

                    leaf oper-state {
                        type types-sros:oper-state;
                        description "Indicates the operational state of the EHS Event Trigger.";
                    }

                    container statistics {
                        description "Enter the statistics context";

                        leaf success {
                            type yang:counter32;
                            description
                                "Indicates the number of not ignored logger event occurrences
                                 associated with EHS trigger.";
                        }

                        leaf error-no-entry {
                            type yang:counter32;
                            description
                                "Indicates the number of ignored logger event occurrences associated
                                 with EHS trigger.

                                 Event is ignored due to no trigger entry configured for this trigger.";
                        }

                        leaf error-admin-state {
                            type yang:counter32;
                            description
                                "Indicates the number of ignored logger event occurrences associated
                                 with EHS trigger.

                                 Event is ignored due to trigger may be out-of-service.";
                        }

                        leaf total {
                            type yang:counter32;
                            description "Sum of success + error-no-entry + error-admin-state.";
                        }

                    } // container statistics

                    container summary-entry-statistics {
                        description "Enter the summary-entry-statistics context";

                        leaf filter-match {
                            type yang:counter32;
                            description "Indicates the number of times a filter matches an logger event.";
                        }

                        leaf filter-fail {
                            type yang:counter32;
                            description "Indicates the number of times a filter does not match an logger event.";
                        }

                        leaf error-admin-state {
                            type yang:counter32;
                            description
                                "Indicates the number of times the logger event will be ignored due to
                                 admin state of EHS trigger entries is out-of-service.";
                        }

                        leaf error-filter {
                            type yang:counter32;
                            description
                                "Indicates the number of times the logger event will be ignored due to filter
                                 is not operational or is not configured in EHS trigger entries.";
                        }

                        leaf error-handler {
                            type yang:counter32;
                            description
                                "Indicates the number of times the logger event will be ignored due to handler
                                 is not operational or is not configured in EHS trigger entries.";
                        }

                        leaf trigger-count {
                            type yang:counter32;
                            description "Indicates the number of times script execution is triggered after filter match.";
                        }

                        leaf debounce-count {
                            type yang:counter32;
                            description "Indicates the number of times script is not executed due to debounce rule.";
                        }

                    } // container summary-entry-statistics

                    list entry {
                        key "id";
                        description "Enter the entry list instance";

                        leaf id {
                            type uint32 {
                                range "1..1500";
                            }
                            description "ID of the EHS event trigger entry";
                        }

                        leaf oper-state {
                            type types-sros:oper-state;
                            description "Indicates the operational state of the EHS Event Trigger Entry.";
                        }

                        container statistics {
                            description "Enter the statistics context";

                            leaf filter-match {
                                type yang:counter32;
                                description
                                    "Indicates the number of times a filter, for the specified trigger entry,
                                     matches an logger event.";
                            }

                            leaf filter-fail {
                                type yang:counter32;
                                description
                                    "Indicates the number of times a filter, for the specified trigger entry,
                                     does not match an logger event.";
                            }

                            leaf error-admin-state {
                                type yang:counter32;
                                description
                                    "Indicates the number of times the logger event will be ignored due to
                                     admin state of EHS trigger entry is out-of-service.";
                            }

                            leaf error-filter {
                                type yang:counter32;
                                description
                                    "Indicates the number of times the logger event will be ignored due to filter
                                     is not operational or is not configured in EHS trigger entry.";
                            }

                            leaf error-handler {
                                type yang:counter32;
                                description
                                    "Indicates the number of times the logger event will be ignored due to handler
                                     is not operational or is not configured in EHS trigger entry.";
                            }

                            leaf trigger-count {
                                type yang:counter32;
                                description
                                    "Indicates the number of times script execution is triggered after filter match
                                     for the specified trigger entry.";
                            }

                            leaf debounce-count {
                                type yang:counter32;
                                description
                                    "Indicates the number of times script is not executed due to debounce rule
                                     for the specified trigger entry.";
                            }

                        } // container statistics

                    } // list entry

                } // list eth-cfm

                list etun {
                    key "event";
                    description "Enter the etun list instance";

                    leaf event {
                        type types-log:etun-events;
                        description "Log event as a trigger for one or more EHS handlers";
                    }

                    leaf oper-state {
                        type types-sros:oper-state;
                        description "Indicates the operational state of the EHS Event Trigger.";
                    }

                    container statistics {
                        description "Enter the statistics context";

                        leaf success {
                            type yang:counter32;
                            description
                                "Indicates the number of not ignored logger event occurrences
                                 associated with EHS trigger.";
                        }

                        leaf error-no-entry {
                            type yang:counter32;
                            description
                                "Indicates the number of ignored logger event occurrences associated
                                 with EHS trigger.

                                 Event is ignored due to no trigger entry configured for this trigger.";
                        }

                        leaf error-admin-state {
                            type yang:counter32;
                            description
                                "Indicates the number of ignored logger event occurrences associated
                                 with EHS trigger.

                                 Event is ignored due to trigger may be out-of-service.";
                        }

                        leaf total {
                            type yang:counter32;
                            description "Sum of success + error-no-entry + error-admin-state.";
                        }

                    } // container statistics

                    container summary-entry-statistics {
                        description "Enter the summary-entry-statistics context";

                        leaf filter-match {
                            type yang:counter32;
                            description "Indicates the number of times a filter matches an logger event.";
                        }

                        leaf filter-fail {
                            type yang:counter32;
                            description "Indicates the number of times a filter does not match an logger event.";
                        }

                        leaf error-admin-state {
                            type yang:counter32;
                            description
                                "Indicates the number of times the logger event will be ignored due to
                                 admin state of EHS trigger entries is out-of-service.";
                        }

                        leaf error-filter {
                            type yang:counter32;
                            description
                                "Indicates the number of times the logger event will be ignored due to filter
                                 is not operational or is not configured in EHS trigger entries.";
                        }

                        leaf error-handler {
                            type yang:counter32;
                            description
                                "Indicates the number of times the logger event will be ignored due to handler
                                 is not operational or is not configured in EHS trigger entries.";
                        }

                        leaf trigger-count {
                            type yang:counter32;
                            description "Indicates the number of times script execution is triggered after filter match.";
                        }

                        leaf debounce-count {
                            type yang:counter32;
                            description "Indicates the number of times script is not executed due to debounce rule.";
                        }

                    } // container summary-entry-statistics

                    list entry {
                        key "id";
                        description "Enter the entry list instance";

                        leaf id {
                            type uint32 {
                                range "1..1500";
                            }
                            description "ID of the EHS event trigger entry";
                        }

                        leaf oper-state {
                            type types-sros:oper-state;
                            description "Indicates the operational state of the EHS Event Trigger Entry.";
                        }

                        container statistics {
                            description "Enter the statistics context";

                            leaf filter-match {
                                type yang:counter32;
                                description
                                    "Indicates the number of times a filter, for the specified trigger entry,
                                     matches an logger event.";
                            }

                            leaf filter-fail {
                                type yang:counter32;
                                description
                                    "Indicates the number of times a filter, for the specified trigger entry,
                                     does not match an logger event.";
                            }

                            leaf error-admin-state {
                                type yang:counter32;
                                description
                                    "Indicates the number of times the logger event will be ignored due to
                                     admin state of EHS trigger entry is out-of-service.";
                            }

                            leaf error-filter {
                                type yang:counter32;
                                description
                                    "Indicates the number of times the logger event will be ignored due to filter
                                     is not operational or is not configured in EHS trigger entry.";
                            }

                            leaf error-handler {
                                type yang:counter32;
                                description
                                    "Indicates the number of times the logger event will be ignored due to handler
                                     is not operational or is not configured in EHS trigger entry.";
                            }

                            leaf trigger-count {
                                type yang:counter32;
                                description
                                    "Indicates the number of times script execution is triggered after filter match
                                     for the specified trigger entry.";
                            }

                            leaf debounce-count {
                                type yang:counter32;
                                description
                                    "Indicates the number of times script is not executed due to debounce rule
                                     for the specified trigger entry.";
                            }

                        } // container statistics

                    } // list entry

                } // list etun

                list filter {
                    key "event";
                    description "Enter the filter list instance";

                    leaf event {
                        type types-log:filter-events;
                        description "Log event as a trigger for one or more EHS handlers";
                    }

                    leaf oper-state {
                        type types-sros:oper-state;
                        description "Indicates the operational state of the EHS Event Trigger.";
                    }

                    container statistics {
                        description "Enter the statistics context";

                        leaf success {
                            type yang:counter32;
                            description
                                "Indicates the number of not ignored logger event occurrences
                                 associated with EHS trigger.";
                        }

                        leaf error-no-entry {
                            type yang:counter32;
                            description
                                "Indicates the number of ignored logger event occurrences associated
                                 with EHS trigger.

                                 Event is ignored due to no trigger entry configured for this trigger.";
                        }

                        leaf error-admin-state {
                            type yang:counter32;
                            description
                                "Indicates the number of ignored logger event occurrences associated
                                 with EHS trigger.

                                 Event is ignored due to trigger may be out-of-service.";
                        }

                        leaf total {
                            type yang:counter32;
                            description "Sum of success + error-no-entry + error-admin-state.";
                        }

                    } // container statistics

                    container summary-entry-statistics {
                        description "Enter the summary-entry-statistics context";

                        leaf filter-match {
                            type yang:counter32;
                            description "Indicates the number of times a filter matches an logger event.";
                        }

                        leaf filter-fail {
                            type yang:counter32;
                            description "Indicates the number of times a filter does not match an logger event.";
                        }

                        leaf error-admin-state {
                            type yang:counter32;
                            description
                                "Indicates the number of times the logger event will be ignored due to
                                 admin state of EHS trigger entries is out-of-service.";
                        }

                        leaf error-filter {
                            type yang:counter32;
                            description
                                "Indicates the number of times the logger event will be ignored due to filter
                                 is not operational or is not configured in EHS trigger entries.";
                        }

                        leaf error-handler {
                            type yang:counter32;
                            description
                                "Indicates the number of times the logger event will be ignored due to handler
                                 is not operational or is not configured in EHS trigger entries.";
                        }

                        leaf trigger-count {
                            type yang:counter32;
                            description "Indicates the number of times script execution is triggered after filter match.";
                        }

                        leaf debounce-count {
                            type yang:counter32;
                            description "Indicates the number of times script is not executed due to debounce rule.";
                        }

                    } // container summary-entry-statistics

                    list entry {
                        key "id";
                        description "Enter the entry list instance";

                        leaf id {
                            type uint32 {
                                range "1..1500";
                            }
                            description "ID of the EHS event trigger entry";
                        }

                        leaf oper-state {
                            type types-sros:oper-state;
                            description "Indicates the operational state of the EHS Event Trigger Entry.";
                        }

                        container statistics {
                            description "Enter the statistics context";

                            leaf filter-match {
                                type yang:counter32;
                                description
                                    "Indicates the number of times a filter, for the specified trigger entry,
                                     matches an logger event.";
                            }

                            leaf filter-fail {
                                type yang:counter32;
                                description
                                    "Indicates the number of times a filter, for the specified trigger entry,
                                     does not match an logger event.";
                            }

                            leaf error-admin-state {
                                type yang:counter32;
                                description
                                    "Indicates the number of times the logger event will be ignored due to
                                     admin state of EHS trigger entry is out-of-service.";
                            }

                            leaf error-filter {
                                type yang:counter32;
                                description
                                    "Indicates the number of times the logger event will be ignored due to filter
                                     is not operational or is not configured in EHS trigger entry.";
                            }

                            leaf error-handler {
                                type yang:counter32;
                                description
                                    "Indicates the number of times the logger event will be ignored due to handler
                                     is not operational or is not configured in EHS trigger entry.";
                            }

                            leaf trigger-count {
                                type yang:counter32;
                                description
                                    "Indicates the number of times script execution is triggered after filter match
                                     for the specified trigger entry.";
                            }

                            leaf debounce-count {
                                type yang:counter32;
                                description
                                    "Indicates the number of times script is not executed due to debounce rule
                                     for the specified trigger entry.";
                            }

                        } // container statistics

                    } // list entry

                } // list filter

                list gsmp {
                    key "event";
                    description "Enter the gsmp list instance";

                    leaf event {
                        type types-log:gsmp-events;
                        description "Log event as a trigger for one or more EHS handlers";
                    }

                    leaf oper-state {
                        type types-sros:oper-state;
                        description "Indicates the operational state of the EHS Event Trigger.";
                    }

                    container statistics {
                        description "Enter the statistics context";

                        leaf success {
                            type yang:counter32;
                            description
                                "Indicates the number of not ignored logger event occurrences
                                 associated with EHS trigger.";
                        }

                        leaf error-no-entry {
                            type yang:counter32;
                            description
                                "Indicates the number of ignored logger event occurrences associated
                                 with EHS trigger.

                                 Event is ignored due to no trigger entry configured for this trigger.";
                        }

                        leaf error-admin-state {
                            type yang:counter32;
                            description
                                "Indicates the number of ignored logger event occurrences associated
                                 with EHS trigger.

                                 Event is ignored due to trigger may be out-of-service.";
                        }

                        leaf total {
                            type yang:counter32;
                            description "Sum of success + error-no-entry + error-admin-state.";
                        }

                    } // container statistics

                    container summary-entry-statistics {
                        description "Enter the summary-entry-statistics context";

                        leaf filter-match {
                            type yang:counter32;
                            description "Indicates the number of times a filter matches an logger event.";
                        }

                        leaf filter-fail {
                            type yang:counter32;
                            description "Indicates the number of times a filter does not match an logger event.";
                        }

                        leaf error-admin-state {
                            type yang:counter32;
                            description
                                "Indicates the number of times the logger event will be ignored due to
                                 admin state of EHS trigger entries is out-of-service.";
                        }

                        leaf error-filter {
                            type yang:counter32;
                            description
                                "Indicates the number of times the logger event will be ignored due to filter
                                 is not operational or is not configured in EHS trigger entries.";
                        }

                        leaf error-handler {
                            type yang:counter32;
                            description
                                "Indicates the number of times the logger event will be ignored due to handler
                                 is not operational or is not configured in EHS trigger entries.";
                        }

                        leaf trigger-count {
                            type yang:counter32;
                            description "Indicates the number of times script execution is triggered after filter match.";
                        }

                        leaf debounce-count {
                            type yang:counter32;
                            description "Indicates the number of times script is not executed due to debounce rule.";
                        }

                    } // container summary-entry-statistics

                    list entry {
                        key "id";
                        description "Enter the entry list instance";

                        leaf id {
                            type uint32 {
                                range "1..1500";
                            }
                            description "ID of the EHS event trigger entry";
                        }

                        leaf oper-state {
                            type types-sros:oper-state;
                            description "Indicates the operational state of the EHS Event Trigger Entry.";
                        }

                        container statistics {
                            description "Enter the statistics context";

                            leaf filter-match {
                                type yang:counter32;
                                description
                                    "Indicates the number of times a filter, for the specified trigger entry,
                                     matches an logger event.";
                            }

                            leaf filter-fail {
                                type yang:counter32;
                                description
                                    "Indicates the number of times a filter, for the specified trigger entry,
                                     does not match an logger event.";
                            }

                            leaf error-admin-state {
                                type yang:counter32;
                                description
                                    "Indicates the number of times the logger event will be ignored due to
                                     admin state of EHS trigger entry is out-of-service.";
                            }

                            leaf error-filter {
                                type yang:counter32;
                                description
                                    "Indicates the number of times the logger event will be ignored due to filter
                                     is not operational or is not configured in EHS trigger entry.";
                            }

                            leaf error-handler {
                                type yang:counter32;
                                description
                                    "Indicates the number of times the logger event will be ignored due to handler
                                     is not operational or is not configured in EHS trigger entry.";
                            }

                            leaf trigger-count {
                                type yang:counter32;
                                description
                                    "Indicates the number of times script execution is triggered after filter match
                                     for the specified trigger entry.";
                            }

                            leaf debounce-count {
                                type yang:counter32;
                                description
                                    "Indicates the number of times script is not executed due to debounce rule
                                     for the specified trigger entry.";
                            }

                        } // container statistics

                    } // list entry

                } // list gsmp

                list igmp {
                    key "event";
                    description "Enter the igmp list instance";

                    leaf event {
                        type types-log:igmp-events;
                        description "Log event as a trigger for one or more EHS handlers";
                    }

                    leaf oper-state {
                        type types-sros:oper-state;
                        description "Indicates the operational state of the EHS Event Trigger.";
                    }

                    container statistics {
                        description "Enter the statistics context";

                        leaf success {
                            type yang:counter32;
                            description
                                "Indicates the number of not ignored logger event occurrences
                                 associated with EHS trigger.";
                        }

                        leaf error-no-entry {
                            type yang:counter32;
                            description
                                "Indicates the number of ignored logger event occurrences associated
                                 with EHS trigger.

                                 Event is ignored due to no trigger entry configured for this trigger.";
                        }

                        leaf error-admin-state {
                            type yang:counter32;
                            description
                                "Indicates the number of ignored logger event occurrences associated
                                 with EHS trigger.

                                 Event is ignored due to trigger may be out-of-service.";
                        }

                        leaf total {
                            type yang:counter32;
                            description "Sum of success + error-no-entry + error-admin-state.";
                        }

                    } // container statistics

                    container summary-entry-statistics {
                        description "Enter the summary-entry-statistics context";

                        leaf filter-match {
                            type yang:counter32;
                            description "Indicates the number of times a filter matches an logger event.";
                        }

                        leaf filter-fail {
                            type yang:counter32;
                            description "Indicates the number of times a filter does not match an logger event.";
                        }

                        leaf error-admin-state {
                            type yang:counter32;
                            description
                                "Indicates the number of times the logger event will be ignored due to
                                 admin state of EHS trigger entries is out-of-service.";
                        }

                        leaf error-filter {
                            type yang:counter32;
                            description
                                "Indicates the number of times the logger event will be ignored due to filter
                                 is not operational or is not configured in EHS trigger entries.";
                        }

                        leaf error-handler {
                            type yang:counter32;
                            description
                                "Indicates the number of times the logger event will be ignored due to handler
                                 is not operational or is not configured in EHS trigger entries.";
                        }

                        leaf trigger-count {
                            type yang:counter32;
                            description "Indicates the number of times script execution is triggered after filter match.";
                        }

                        leaf debounce-count {
                            type yang:counter32;
                            description "Indicates the number of times script is not executed due to debounce rule.";
                        }

                    } // container summary-entry-statistics

                    list entry {
                        key "id";
                        description "Enter the entry list instance";

                        leaf id {
                            type uint32 {
                                range "1..1500";
                            }
                            description "ID of the EHS event trigger entry";
                        }

                        leaf oper-state {
                            type types-sros:oper-state;
                            description "Indicates the operational state of the EHS Event Trigger Entry.";
                        }

                        container statistics {
                            description "Enter the statistics context";

                            leaf filter-match {
                                type yang:counter32;
                                description
                                    "Indicates the number of times a filter, for the specified trigger entry,
                                     matches an logger event.";
                            }

                            leaf filter-fail {
                                type yang:counter32;
                                description
                                    "Indicates the number of times a filter, for the specified trigger entry,
                                     does not match an logger event.";
                            }

                            leaf error-admin-state {
                                type yang:counter32;
                                description
                                    "Indicates the number of times the logger event will be ignored due to
                                     admin state of EHS trigger entry is out-of-service.";
                            }

                            leaf error-filter {
                                type yang:counter32;
                                description
                                    "Indicates the number of times the logger event will be ignored due to filter
                                     is not operational or is not configured in EHS trigger entry.";
                            }

                            leaf error-handler {
                                type yang:counter32;
                                description
                                    "Indicates the number of times the logger event will be ignored due to handler
                                     is not operational or is not configured in EHS trigger entry.";
                            }

                            leaf trigger-count {
                                type yang:counter32;
                                description
                                    "Indicates the number of times script execution is triggered after filter match
                                     for the specified trigger entry.";
                            }

                            leaf debounce-count {
                                type yang:counter32;
                                description
                                    "Indicates the number of times script is not executed due to debounce rule
                                     for the specified trigger entry.";
                            }

                        } // container statistics

                    } // list entry

                } // list igmp

                list igmp-snooping {
                    key "event";
                    description "Enter the igmp-snooping list instance";

                    leaf event {
                        type types-log:igmp-snooping-events;
                        description "Log event as a trigger for one or more EHS handlers";
                    }

                    leaf oper-state {
                        type types-sros:oper-state;
                        description "Indicates the operational state of the EHS Event Trigger.";
                    }

                    container statistics {
                        description "Enter the statistics context";

                        leaf success {
                            type yang:counter32;
                            description
                                "Indicates the number of not ignored logger event occurrences
                                 associated with EHS trigger.";
                        }

                        leaf error-no-entry {
                            type yang:counter32;
                            description
                                "Indicates the number of ignored logger event occurrences associated
                                 with EHS trigger.

                                 Event is ignored due to no trigger entry configured for this trigger.";
                        }

                        leaf error-admin-state {
                            type yang:counter32;
                            description
                                "Indicates the number of ignored logger event occurrences associated
                                 with EHS trigger.

                                 Event is ignored due to trigger may be out-of-service.";
                        }

                        leaf total {
                            type yang:counter32;
                            description "Sum of success + error-no-entry + error-admin-state.";
                        }

                    } // container statistics

                    container summary-entry-statistics {
                        description "Enter the summary-entry-statistics context";

                        leaf filter-match {
                            type yang:counter32;
                            description "Indicates the number of times a filter matches an logger event.";
                        }

                        leaf filter-fail {
                            type yang:counter32;
                            description "Indicates the number of times a filter does not match an logger event.";
                        }

                        leaf error-admin-state {
                            type yang:counter32;
                            description
                                "Indicates the number of times the logger event will be ignored due to
                                 admin state of EHS trigger entries is out-of-service.";
                        }

                        leaf error-filter {
                            type yang:counter32;
                            description
                                "Indicates the number of times the logger event will be ignored due to filter
                                 is not operational or is not configured in EHS trigger entries.";
                        }

                        leaf error-handler {
                            type yang:counter32;
                            description
                                "Indicates the number of times the logger event will be ignored due to handler
                                 is not operational or is not configured in EHS trigger entries.";
                        }

                        leaf trigger-count {
                            type yang:counter32;
                            description "Indicates the number of times script execution is triggered after filter match.";
                        }

                        leaf debounce-count {
                            type yang:counter32;
                            description "Indicates the number of times script is not executed due to debounce rule.";
                        }

                    } // container summary-entry-statistics

                    list entry {
                        key "id";
                        description "Enter the entry list instance";

                        leaf id {
                            type uint32 {
                                range "1..1500";
                            }
                            description "ID of the EHS event trigger entry";
                        }

                        leaf oper-state {
                            type types-sros:oper-state;
                            description "Indicates the operational state of the EHS Event Trigger Entry.";
                        }

                        container statistics {
                            description "Enter the statistics context";

                            leaf filter-match {
                                type yang:counter32;
                                description
                                    "Indicates the number of times a filter, for the specified trigger entry,
                                     matches an logger event.";
                            }

                            leaf filter-fail {
                                type yang:counter32;
                                description
                                    "Indicates the number of times a filter, for the specified trigger entry,
                                     does not match an logger event.";
                            }

                            leaf error-admin-state {
                                type yang:counter32;
                                description
                                    "Indicates the number of times the logger event will be ignored due to
                                     admin state of EHS trigger entry is out-of-service.";
                            }

                            leaf error-filter {
                                type yang:counter32;
                                description
                                    "Indicates the number of times the logger event will be ignored due to filter
                                     is not operational or is not configured in EHS trigger entry.";
                            }

                            leaf error-handler {
                                type yang:counter32;
                                description
                                    "Indicates the number of times the logger event will be ignored due to handler
                                     is not operational or is not configured in EHS trigger entry.";
                            }

                            leaf trigger-count {
                                type yang:counter32;
                                description
                                    "Indicates the number of times script execution is triggered after filter match
                                     for the specified trigger entry.";
                            }

                            leaf debounce-count {
                                type yang:counter32;
                                description
                                    "Indicates the number of times script is not executed due to debounce rule
                                     for the specified trigger entry.";
                            }

                        } // container statistics

                    } // list entry

                } // list igmp-snooping

                list ip {
                    key "event";
                    description "Enter the ip list instance";

                    leaf event {
                        type types-log:ip-events;
                        description "Log event as a trigger for one or more EHS handlers";
                    }

                    leaf oper-state {
                        type types-sros:oper-state;
                        description "Indicates the operational state of the EHS Event Trigger.";
                    }

                    container statistics {
                        description "Enter the statistics context";

                        leaf success {
                            type yang:counter32;
                            description
                                "Indicates the number of not ignored logger event occurrences
                                 associated with EHS trigger.";
                        }

                        leaf error-no-entry {
                            type yang:counter32;
                            description
                                "Indicates the number of ignored logger event occurrences associated
                                 with EHS trigger.

                                 Event is ignored due to no trigger entry configured for this trigger.";
                        }

                        leaf error-admin-state {
                            type yang:counter32;
                            description
                                "Indicates the number of ignored logger event occurrences associated
                                 with EHS trigger.

                                 Event is ignored due to trigger may be out-of-service.";
                        }

                        leaf total {
                            type yang:counter32;
                            description "Sum of success + error-no-entry + error-admin-state.";
                        }

                    } // container statistics

                    container summary-entry-statistics {
                        description "Enter the summary-entry-statistics context";

                        leaf filter-match {
                            type yang:counter32;
                            description "Indicates the number of times a filter matches an logger event.";
                        }

                        leaf filter-fail {
                            type yang:counter32;
                            description "Indicates the number of times a filter does not match an logger event.";
                        }

                        leaf error-admin-state {
                            type yang:counter32;
                            description
                                "Indicates the number of times the logger event will be ignored due to
                                 admin state of EHS trigger entries is out-of-service.";
                        }

                        leaf error-filter {
                            type yang:counter32;
                            description
                                "Indicates the number of times the logger event will be ignored due to filter
                                 is not operational or is not configured in EHS trigger entries.";
                        }

                        leaf error-handler {
                            type yang:counter32;
                            description
                                "Indicates the number of times the logger event will be ignored due to handler
                                 is not operational or is not configured in EHS trigger entries.";
                        }

                        leaf trigger-count {
                            type yang:counter32;
                            description "Indicates the number of times script execution is triggered after filter match.";
                        }

                        leaf debounce-count {
                            type yang:counter32;
                            description "Indicates the number of times script is not executed due to debounce rule.";
                        }

                    } // container summary-entry-statistics

                    list entry {
                        key "id";
                        description "Enter the entry list instance";

                        leaf id {
                            type uint32 {
                                range "1..1500";
                            }
                            description "ID of the EHS event trigger entry";
                        }

                        leaf oper-state {
                            type types-sros:oper-state;
                            description "Indicates the operational state of the EHS Event Trigger Entry.";
                        }

                        container statistics {
                            description "Enter the statistics context";

                            leaf filter-match {
                                type yang:counter32;
                                description
                                    "Indicates the number of times a filter, for the specified trigger entry,
                                     matches an logger event.";
                            }

                            leaf filter-fail {
                                type yang:counter32;
                                description
                                    "Indicates the number of times a filter, for the specified trigger entry,
                                     does not match an logger event.";
                            }

                            leaf error-admin-state {
                                type yang:counter32;
                                description
                                    "Indicates the number of times the logger event will be ignored due to
                                     admin state of EHS trigger entry is out-of-service.";
                            }

                            leaf error-filter {
                                type yang:counter32;
                                description
                                    "Indicates the number of times the logger event will be ignored due to filter
                                     is not operational or is not configured in EHS trigger entry.";
                            }

                            leaf error-handler {
                                type yang:counter32;
                                description
                                    "Indicates the number of times the logger event will be ignored due to handler
                                     is not operational or is not configured in EHS trigger entry.";
                            }

                            leaf trigger-count {
                                type yang:counter32;
                                description
                                    "Indicates the number of times script execution is triggered after filter match
                                     for the specified trigger entry.";
                            }

                            leaf debounce-count {
                                type yang:counter32;
                                description
                                    "Indicates the number of times script is not executed due to debounce rule
                                     for the specified trigger entry.";
                            }

                        } // container statistics

                    } // list entry

                } // list ip

                list ipsec {
                    key "event";
                    description "Enter the ipsec list instance";

                    leaf event {
                        type types-log:ipsec-events;
                        description "Log event as a trigger for one or more EHS handlers";
                    }

                    leaf oper-state {
                        type types-sros:oper-state;
                        description "Indicates the operational state of the EHS Event Trigger.";
                    }

                    container statistics {
                        description "Enter the statistics context";

                        leaf success {
                            type yang:counter32;
                            description
                                "Indicates the number of not ignored logger event occurrences
                                 associated with EHS trigger.";
                        }

                        leaf error-no-entry {
                            type yang:counter32;
                            description
                                "Indicates the number of ignored logger event occurrences associated
                                 with EHS trigger.

                                 Event is ignored due to no trigger entry configured for this trigger.";
                        }

                        leaf error-admin-state {
                            type yang:counter32;
                            description
                                "Indicates the number of ignored logger event occurrences associated
                                 with EHS trigger.

                                 Event is ignored due to trigger may be out-of-service.";
                        }

                        leaf total {
                            type yang:counter32;
                            description "Sum of success + error-no-entry + error-admin-state.";
                        }

                    } // container statistics

                    container summary-entry-statistics {
                        description "Enter the summary-entry-statistics context";

                        leaf filter-match {
                            type yang:counter32;
                            description "Indicates the number of times a filter matches an logger event.";
                        }

                        leaf filter-fail {
                            type yang:counter32;
                            description "Indicates the number of times a filter does not match an logger event.";
                        }

                        leaf error-admin-state {
                            type yang:counter32;
                            description
                                "Indicates the number of times the logger event will be ignored due to
                                 admin state of EHS trigger entries is out-of-service.";
                        }

                        leaf error-filter {
                            type yang:counter32;
                            description
                                "Indicates the number of times the logger event will be ignored due to filter
                                 is not operational or is not configured in EHS trigger entries.";
                        }

                        leaf error-handler {
                            type yang:counter32;
                            description
                                "Indicates the number of times the logger event will be ignored due to handler
                                 is not operational or is not configured in EHS trigger entries.";
                        }

                        leaf trigger-count {
                            type yang:counter32;
                            description "Indicates the number of times script execution is triggered after filter match.";
                        }

                        leaf debounce-count {
                            type yang:counter32;
                            description "Indicates the number of times script is not executed due to debounce rule.";
                        }

                    } // container summary-entry-statistics

                    list entry {
                        key "id";
                        description "Enter the entry list instance";

                        leaf id {
                            type uint32 {
                                range "1..1500";
                            }
                            description "ID of the EHS event trigger entry";
                        }

                        leaf oper-state {
                            type types-sros:oper-state;
                            description "Indicates the operational state of the EHS Event Trigger Entry.";
                        }

                        container statistics {
                            description "Enter the statistics context";

                            leaf filter-match {
                                type yang:counter32;
                                description
                                    "Indicates the number of times a filter, for the specified trigger entry,
                                     matches an logger event.";
                            }

                            leaf filter-fail {
                                type yang:counter32;
                                description
                                    "Indicates the number of times a filter, for the specified trigger entry,
                                     does not match an logger event.";
                            }

                            leaf error-admin-state {
                                type yang:counter32;
                                description
                                    "Indicates the number of times the logger event will be ignored due to
                                     admin state of EHS trigger entry is out-of-service.";
                            }

                            leaf error-filter {
                                type yang:counter32;
                                description
                                    "Indicates the number of times the logger event will be ignored due to filter
                                     is not operational or is not configured in EHS trigger entry.";
                            }

                            leaf error-handler {
                                type yang:counter32;
                                description
                                    "Indicates the number of times the logger event will be ignored due to handler
                                     is not operational or is not configured in EHS trigger entry.";
                            }

                            leaf trigger-count {
                                type yang:counter32;
                                description
                                    "Indicates the number of times script execution is triggered after filter match
                                     for the specified trigger entry.";
                            }

                            leaf debounce-count {
                                type yang:counter32;
                                description
                                    "Indicates the number of times script is not executed due to debounce rule
                                     for the specified trigger entry.";
                            }

                        } // container statistics

                    } // list entry

                } // list ipsec

                list isis {
                    key "event";
                    description "Enter the isis list instance";

                    leaf event {
                        type types-log:isis-events;
                        description "Log event as a trigger for one or more EHS handlers";
                    }

                    leaf oper-state {
                        type types-sros:oper-state;
                        description "Indicates the operational state of the EHS Event Trigger.";
                    }

                    container statistics {
                        description "Enter the statistics context";

                        leaf success {
                            type yang:counter32;
                            description
                                "Indicates the number of not ignored logger event occurrences
                                 associated with EHS trigger.";
                        }

                        leaf error-no-entry {
                            type yang:counter32;
                            description
                                "Indicates the number of ignored logger event occurrences associated
                                 with EHS trigger.

                                 Event is ignored due to no trigger entry configured for this trigger.";
                        }

                        leaf error-admin-state {
                            type yang:counter32;
                            description
                                "Indicates the number of ignored logger event occurrences associated
                                 with EHS trigger.

                                 Event is ignored due to trigger may be out-of-service.";
                        }

                        leaf total {
                            type yang:counter32;
                            description "Sum of success + error-no-entry + error-admin-state.";
                        }

                    } // container statistics

                    container summary-entry-statistics {
                        description "Enter the summary-entry-statistics context";

                        leaf filter-match {
                            type yang:counter32;
                            description "Indicates the number of times a filter matches an logger event.";
                        }

                        leaf filter-fail {
                            type yang:counter32;
                            description "Indicates the number of times a filter does not match an logger event.";
                        }

                        leaf error-admin-state {
                            type yang:counter32;
                            description
                                "Indicates the number of times the logger event will be ignored due to
                                 admin state of EHS trigger entries is out-of-service.";
                        }

                        leaf error-filter {
                            type yang:counter32;
                            description
                                "Indicates the number of times the logger event will be ignored due to filter
                                 is not operational or is not configured in EHS trigger entries.";
                        }

                        leaf error-handler {
                            type yang:counter32;
                            description
                                "Indicates the number of times the logger event will be ignored due to handler
                                 is not operational or is not configured in EHS trigger entries.";
                        }

                        leaf trigger-count {
                            type yang:counter32;
                            description "Indicates the number of times script execution is triggered after filter match.";
                        }

                        leaf debounce-count {
                            type yang:counter32;
                            description "Indicates the number of times script is not executed due to debounce rule.";
                        }

                    } // container summary-entry-statistics

                    list entry {
                        key "id";
                        description "Enter the entry list instance";

                        leaf id {
                            type uint32 {
                                range "1..1500";
                            }
                            description "ID of the EHS event trigger entry";
                        }

                        leaf oper-state {
                            type types-sros:oper-state;
                            description "Indicates the operational state of the EHS Event Trigger Entry.";
                        }

                        container statistics {
                            description "Enter the statistics context";

                            leaf filter-match {
                                type yang:counter32;
                                description
                                    "Indicates the number of times a filter, for the specified trigger entry,
                                     matches an logger event.";
                            }

                            leaf filter-fail {
                                type yang:counter32;
                                description
                                    "Indicates the number of times a filter, for the specified trigger entry,
                                     does not match an logger event.";
                            }

                            leaf error-admin-state {
                                type yang:counter32;
                                description
                                    "Indicates the number of times the logger event will be ignored due to
                                     admin state of EHS trigger entry is out-of-service.";
                            }

                            leaf error-filter {
                                type yang:counter32;
                                description
                                    "Indicates the number of times the logger event will be ignored due to filter
                                     is not operational or is not configured in EHS trigger entry.";
                            }

                            leaf error-handler {
                                type yang:counter32;
                                description
                                    "Indicates the number of times the logger event will be ignored due to handler
                                     is not operational or is not configured in EHS trigger entry.";
                            }

                            leaf trigger-count {
                                type yang:counter32;
                                description
                                    "Indicates the number of times script execution is triggered after filter match
                                     for the specified trigger entry.";
                            }

                            leaf debounce-count {
                                type yang:counter32;
                                description
                                    "Indicates the number of times script is not executed due to debounce rule
                                     for the specified trigger entry.";
                            }

                        } // container statistics

                    } // list entry

                } // list isis

                list l2tp {
                    key "event";
                    description "Enter the l2tp list instance";

                    leaf event {
                        type types-log:l2tp-events;
                        description "Log event as a trigger for one or more EHS handlers";
                    }

                    leaf oper-state {
                        type types-sros:oper-state;
                        description "Indicates the operational state of the EHS Event Trigger.";
                    }

                    container statistics {
                        description "Enter the statistics context";

                        leaf success {
                            type yang:counter32;
                            description
                                "Indicates the number of not ignored logger event occurrences
                                 associated with EHS trigger.";
                        }

                        leaf error-no-entry {
                            type yang:counter32;
                            description
                                "Indicates the number of ignored logger event occurrences associated
                                 with EHS trigger.

                                 Event is ignored due to no trigger entry configured for this trigger.";
                        }

                        leaf error-admin-state {
                            type yang:counter32;
                            description
                                "Indicates the number of ignored logger event occurrences associated
                                 with EHS trigger.

                                 Event is ignored due to trigger may be out-of-service.";
                        }

                        leaf total {
                            type yang:counter32;
                            description "Sum of success + error-no-entry + error-admin-state.";
                        }

                    } // container statistics

                    container summary-entry-statistics {
                        description "Enter the summary-entry-statistics context";

                        leaf filter-match {
                            type yang:counter32;
                            description "Indicates the number of times a filter matches an logger event.";
                        }

                        leaf filter-fail {
                            type yang:counter32;
                            description "Indicates the number of times a filter does not match an logger event.";
                        }

                        leaf error-admin-state {
                            type yang:counter32;
                            description
                                "Indicates the number of times the logger event will be ignored due to
                                 admin state of EHS trigger entries is out-of-service.";
                        }

                        leaf error-filter {
                            type yang:counter32;
                            description
                                "Indicates the number of times the logger event will be ignored due to filter
                                 is not operational or is not configured in EHS trigger entries.";
                        }

                        leaf error-handler {
                            type yang:counter32;
                            description
                                "Indicates the number of times the logger event will be ignored due to handler
                                 is not operational or is not configured in EHS trigger entries.";
                        }

                        leaf trigger-count {
                            type yang:counter32;
                            description "Indicates the number of times script execution is triggered after filter match.";
                        }

                        leaf debounce-count {
                            type yang:counter32;
                            description "Indicates the number of times script is not executed due to debounce rule.";
                        }

                    } // container summary-entry-statistics

                    list entry {
                        key "id";
                        description "Enter the entry list instance";

                        leaf id {
                            type uint32 {
                                range "1..1500";
                            }
                            description "ID of the EHS event trigger entry";
                        }

                        leaf oper-state {
                            type types-sros:oper-state;
                            description "Indicates the operational state of the EHS Event Trigger Entry.";
                        }

                        container statistics {
                            description "Enter the statistics context";

                            leaf filter-match {
                                type yang:counter32;
                                description
                                    "Indicates the number of times a filter, for the specified trigger entry,
                                     matches an logger event.";
                            }

                            leaf filter-fail {
                                type yang:counter32;
                                description
                                    "Indicates the number of times a filter, for the specified trigger entry,
                                     does not match an logger event.";
                            }

                            leaf error-admin-state {
                                type yang:counter32;
                                description
                                    "Indicates the number of times the logger event will be ignored due to
                                     admin state of EHS trigger entry is out-of-service.";
                            }

                            leaf error-filter {
                                type yang:counter32;
                                description
                                    "Indicates the number of times the logger event will be ignored due to filter
                                     is not operational or is not configured in EHS trigger entry.";
                            }

                            leaf error-handler {
                                type yang:counter32;
                                description
                                    "Indicates the number of times the logger event will be ignored due to handler
                                     is not operational or is not configured in EHS trigger entry.";
                            }

                            leaf trigger-count {
                                type yang:counter32;
                                description
                                    "Indicates the number of times script execution is triggered after filter match
                                     for the specified trigger entry.";
                            }

                            leaf debounce-count {
                                type yang:counter32;
                                description
                                    "Indicates the number of times script is not executed due to debounce rule
                                     for the specified trigger entry.";
                            }

                        } // container statistics

                    } // list entry

                } // list l2tp

                list lag {
                    key "event";
                    description "Enter the lag list instance";

                    leaf event {
                        type types-log:lag-events;
                        description "Log event as a trigger for one or more EHS handlers";
                    }

                    leaf oper-state {
                        type types-sros:oper-state;
                        description "Indicates the operational state of the EHS Event Trigger.";
                    }

                    container statistics {
                        description "Enter the statistics context";

                        leaf success {
                            type yang:counter32;
                            description
                                "Indicates the number of not ignored logger event occurrences
                                 associated with EHS trigger.";
                        }

                        leaf error-no-entry {
                            type yang:counter32;
                            description
                                "Indicates the number of ignored logger event occurrences associated
                                 with EHS trigger.

                                 Event is ignored due to no trigger entry configured for this trigger.";
                        }

                        leaf error-admin-state {
                            type yang:counter32;
                            description
                                "Indicates the number of ignored logger event occurrences associated
                                 with EHS trigger.

                                 Event is ignored due to trigger may be out-of-service.";
                        }

                        leaf total {
                            type yang:counter32;
                            description "Sum of success + error-no-entry + error-admin-state.";
                        }

                    } // container statistics

                    container summary-entry-statistics {
                        description "Enter the summary-entry-statistics context";

                        leaf filter-match {
                            type yang:counter32;
                            description "Indicates the number of times a filter matches an logger event.";
                        }

                        leaf filter-fail {
                            type yang:counter32;
                            description "Indicates the number of times a filter does not match an logger event.";
                        }

                        leaf error-admin-state {
                            type yang:counter32;
                            description
                                "Indicates the number of times the logger event will be ignored due to
                                 admin state of EHS trigger entries is out-of-service.";
                        }

                        leaf error-filter {
                            type yang:counter32;
                            description
                                "Indicates the number of times the logger event will be ignored due to filter
                                 is not operational or is not configured in EHS trigger entries.";
                        }

                        leaf error-handler {
                            type yang:counter32;
                            description
                                "Indicates the number of times the logger event will be ignored due to handler
                                 is not operational or is not configured in EHS trigger entries.";
                        }

                        leaf trigger-count {
                            type yang:counter32;
                            description "Indicates the number of times script execution is triggered after filter match.";
                        }

                        leaf debounce-count {
                            type yang:counter32;
                            description "Indicates the number of times script is not executed due to debounce rule.";
                        }

                    } // container summary-entry-statistics

                    list entry {
                        key "id";
                        description "Enter the entry list instance";

                        leaf id {
                            type uint32 {
                                range "1..1500";
                            }
                            description "ID of the EHS event trigger entry";
                        }

                        leaf oper-state {
                            type types-sros:oper-state;
                            description "Indicates the operational state of the EHS Event Trigger Entry.";
                        }

                        container statistics {
                            description "Enter the statistics context";

                            leaf filter-match {
                                type yang:counter32;
                                description
                                    "Indicates the number of times a filter, for the specified trigger entry,
                                     matches an logger event.";
                            }

                            leaf filter-fail {
                                type yang:counter32;
                                description
                                    "Indicates the number of times a filter, for the specified trigger entry,
                                     does not match an logger event.";
                            }

                            leaf error-admin-state {
                                type yang:counter32;
                                description
                                    "Indicates the number of times the logger event will be ignored due to
                                     admin state of EHS trigger entry is out-of-service.";
                            }

                            leaf error-filter {
                                type yang:counter32;
                                description
                                    "Indicates the number of times the logger event will be ignored due to filter
                                     is not operational or is not configured in EHS trigger entry.";
                            }

                            leaf error-handler {
                                type yang:counter32;
                                description
                                    "Indicates the number of times the logger event will be ignored due to handler
                                     is not operational or is not configured in EHS trigger entry.";
                            }

                            leaf trigger-count {
                                type yang:counter32;
                                description
                                    "Indicates the number of times script execution is triggered after filter match
                                     for the specified trigger entry.";
                            }

                            leaf debounce-count {
                                type yang:counter32;
                                description
                                    "Indicates the number of times script is not executed due to debounce rule
                                     for the specified trigger entry.";
                            }

                        } // container statistics

                    } // list entry

                } // list lag

                list ldap {
                    key "event";
                    description "Enter the ldap list instance";

                    leaf event {
                        type types-log:ldap-events;
                        description "Log event as a trigger for one or more EHS handlers";
                    }

                    leaf oper-state {
                        type types-sros:oper-state;
                        description "Indicates the operational state of the EHS Event Trigger.";
                    }

                    container statistics {
                        description "Enter the statistics context";

                        leaf success {
                            type yang:counter32;
                            description
                                "Indicates the number of not ignored logger event occurrences
                                 associated with EHS trigger.";
                        }

                        leaf error-no-entry {
                            type yang:counter32;
                            description
                                "Indicates the number of ignored logger event occurrences associated
                                 with EHS trigger.

                                 Event is ignored due to no trigger entry configured for this trigger.";
                        }

                        leaf error-admin-state {
                            type yang:counter32;
                            description
                                "Indicates the number of ignored logger event occurrences associated
                                 with EHS trigger.

                                 Event is ignored due to trigger may be out-of-service.";
                        }

                        leaf total {
                            type yang:counter32;
                            description "Sum of success + error-no-entry + error-admin-state.";
                        }

                    } // container statistics

                    container summary-entry-statistics {
                        description "Enter the summary-entry-statistics context";

                        leaf filter-match {
                            type yang:counter32;
                            description "Indicates the number of times a filter matches an logger event.";
                        }

                        leaf filter-fail {
                            type yang:counter32;
                            description "Indicates the number of times a filter does not match an logger event.";
                        }

                        leaf error-admin-state {
                            type yang:counter32;
                            description
                                "Indicates the number of times the logger event will be ignored due to
                                 admin state of EHS trigger entries is out-of-service.";
                        }

                        leaf error-filter {
                            type yang:counter32;
                            description
                                "Indicates the number of times the logger event will be ignored due to filter
                                 is not operational or is not configured in EHS trigger entries.";
                        }

                        leaf error-handler {
                            type yang:counter32;
                            description
                                "Indicates the number of times the logger event will be ignored due to handler
                                 is not operational or is not configured in EHS trigger entries.";
                        }

                        leaf trigger-count {
                            type yang:counter32;
                            description "Indicates the number of times script execution is triggered after filter match.";
                        }

                        leaf debounce-count {
                            type yang:counter32;
                            description "Indicates the number of times script is not executed due to debounce rule.";
                        }

                    } // container summary-entry-statistics

                    list entry {
                        key "id";
                        description "Enter the entry list instance";

                        leaf id {
                            type uint32 {
                                range "1..1500";
                            }
                            description "ID of the EHS event trigger entry";
                        }

                        leaf oper-state {
                            type types-sros:oper-state;
                            description "Indicates the operational state of the EHS Event Trigger Entry.";
                        }

                        container statistics {
                            description "Enter the statistics context";

                            leaf filter-match {
                                type yang:counter32;
                                description
                                    "Indicates the number of times a filter, for the specified trigger entry,
                                     matches an logger event.";
                            }

                            leaf filter-fail {
                                type yang:counter32;
                                description
                                    "Indicates the number of times a filter, for the specified trigger entry,
                                     does not match an logger event.";
                            }

                            leaf error-admin-state {
                                type yang:counter32;
                                description
                                    "Indicates the number of times the logger event will be ignored due to
                                     admin state of EHS trigger entry is out-of-service.";
                            }

                            leaf error-filter {
                                type yang:counter32;
                                description
                                    "Indicates the number of times the logger event will be ignored due to filter
                                     is not operational or is not configured in EHS trigger entry.";
                            }

                            leaf error-handler {
                                type yang:counter32;
                                description
                                    "Indicates the number of times the logger event will be ignored due to handler
                                     is not operational or is not configured in EHS trigger entry.";
                            }

                            leaf trigger-count {
                                type yang:counter32;
                                description
                                    "Indicates the number of times script execution is triggered after filter match
                                     for the specified trigger entry.";
                            }

                            leaf debounce-count {
                                type yang:counter32;
                                description
                                    "Indicates the number of times script is not executed due to debounce rule
                                     for the specified trigger entry.";
                            }

                        } // container statistics

                    } // list entry

                } // list ldap

                list ldp {
                    key "event";
                    description "Enter the ldp list instance";

                    leaf event {
                        type types-log:ldp-events;
                        description "Log event as a trigger for one or more EHS handlers";
                    }

                    leaf oper-state {
                        type types-sros:oper-state;
                        description "Indicates the operational state of the EHS Event Trigger.";
                    }

                    container statistics {
                        description "Enter the statistics context";

                        leaf success {
                            type yang:counter32;
                            description
                                "Indicates the number of not ignored logger event occurrences
                                 associated with EHS trigger.";
                        }

                        leaf error-no-entry {
                            type yang:counter32;
                            description
                                "Indicates the number of ignored logger event occurrences associated
                                 with EHS trigger.

                                 Event is ignored due to no trigger entry configured for this trigger.";
                        }

                        leaf error-admin-state {
                            type yang:counter32;
                            description
                                "Indicates the number of ignored logger event occurrences associated
                                 with EHS trigger.

                                 Event is ignored due to trigger may be out-of-service.";
                        }

                        leaf total {
                            type yang:counter32;
                            description "Sum of success + error-no-entry + error-admin-state.";
                        }

                    } // container statistics

                    container summary-entry-statistics {
                        description "Enter the summary-entry-statistics context";

                        leaf filter-match {
                            type yang:counter32;
                            description "Indicates the number of times a filter matches an logger event.";
                        }

                        leaf filter-fail {
                            type yang:counter32;
                            description "Indicates the number of times a filter does not match an logger event.";
                        }

                        leaf error-admin-state {
                            type yang:counter32;
                            description
                                "Indicates the number of times the logger event will be ignored due to
                                 admin state of EHS trigger entries is out-of-service.";
                        }

                        leaf error-filter {
                            type yang:counter32;
                            description
                                "Indicates the number of times the logger event will be ignored due to filter
                                 is not operational or is not configured in EHS trigger entries.";
                        }

                        leaf error-handler {
                            type yang:counter32;
                            description
                                "Indicates the number of times the logger event will be ignored due to handler
                                 is not operational or is not configured in EHS trigger entries.";
                        }

                        leaf trigger-count {
                            type yang:counter32;
                            description "Indicates the number of times script execution is triggered after filter match.";
                        }

                        leaf debounce-count {
                            type yang:counter32;
                            description "Indicates the number of times script is not executed due to debounce rule.";
                        }

                    } // container summary-entry-statistics

                    list entry {
                        key "id";
                        description "Enter the entry list instance";

                        leaf id {
                            type uint32 {
                                range "1..1500";
                            }
                            description "ID of the EHS event trigger entry";
                        }

                        leaf oper-state {
                            type types-sros:oper-state;
                            description "Indicates the operational state of the EHS Event Trigger Entry.";
                        }

                        container statistics {
                            description "Enter the statistics context";

                            leaf filter-match {
                                type yang:counter32;
                                description
                                    "Indicates the number of times a filter, for the specified trigger entry,
                                     matches an logger event.";
                            }

                            leaf filter-fail {
                                type yang:counter32;
                                description
                                    "Indicates the number of times a filter, for the specified trigger entry,
                                     does not match an logger event.";
                            }

                            leaf error-admin-state {
                                type yang:counter32;
                                description
                                    "Indicates the number of times the logger event will be ignored due to
                                     admin state of EHS trigger entry is out-of-service.";
                            }

                            leaf error-filter {
                                type yang:counter32;
                                description
                                    "Indicates the number of times the logger event will be ignored due to filter
                                     is not operational or is not configured in EHS trigger entry.";
                            }

                            leaf error-handler {
                                type yang:counter32;
                                description
                                    "Indicates the number of times the logger event will be ignored due to handler
                                     is not operational or is not configured in EHS trigger entry.";
                            }

                            leaf trigger-count {
                                type yang:counter32;
                                description
                                    "Indicates the number of times script execution is triggered after filter match
                                     for the specified trigger entry.";
                            }

                            leaf debounce-count {
                                type yang:counter32;
                                description
                                    "Indicates the number of times script is not executed due to debounce rule
                                     for the specified trigger entry.";
                            }

                        } // container statistics

                    } // list entry

                } // list ldp

                list li {
                    key "event";
                    description "Enter the li list instance";

                    leaf event {
                        type types-log:li-events;
                        description "Log event as a trigger for one or more EHS handlers";
                    }

                    leaf oper-state {
                        type types-sros:oper-state;
                        description "Indicates the operational state of the EHS Event Trigger.";
                    }

                    container statistics {
                        description "Enter the statistics context";

                        leaf success {
                            type yang:counter32;
                            description
                                "Indicates the number of not ignored logger event occurrences
                                 associated with EHS trigger.";
                        }

                        leaf error-no-entry {
                            type yang:counter32;
                            description
                                "Indicates the number of ignored logger event occurrences associated
                                 with EHS trigger.

                                 Event is ignored due to no trigger entry configured for this trigger.";
                        }

                        leaf error-admin-state {
                            type yang:counter32;
                            description
                                "Indicates the number of ignored logger event occurrences associated
                                 with EHS trigger.

                                 Event is ignored due to trigger may be out-of-service.";
                        }

                        leaf total {
                            type yang:counter32;
                            description "Sum of success + error-no-entry + error-admin-state.";
                        }

                    } // container statistics

                    container summary-entry-statistics {
                        description "Enter the summary-entry-statistics context";

                        leaf filter-match {
                            type yang:counter32;
                            description "Indicates the number of times a filter matches an logger event.";
                        }

                        leaf filter-fail {
                            type yang:counter32;
                            description "Indicates the number of times a filter does not match an logger event.";
                        }

                        leaf error-admin-state {
                            type yang:counter32;
                            description
                                "Indicates the number of times the logger event will be ignored due to
                                 admin state of EHS trigger entries is out-of-service.";
                        }

                        leaf error-filter {
                            type yang:counter32;
                            description
                                "Indicates the number of times the logger event will be ignored due to filter
                                 is not operational or is not configured in EHS trigger entries.";
                        }

                        leaf error-handler {
                            type yang:counter32;
                            description
                                "Indicates the number of times the logger event will be ignored due to handler
                                 is not operational or is not configured in EHS trigger entries.";
                        }

                        leaf trigger-count {
                            type yang:counter32;
                            description "Indicates the number of times script execution is triggered after filter match.";
                        }

                        leaf debounce-count {
                            type yang:counter32;
                            description "Indicates the number of times script is not executed due to debounce rule.";
                        }

                    } // container summary-entry-statistics

                    list entry {
                        key "id";
                        description "Enter the entry list instance";

                        leaf id {
                            type uint32 {
                                range "1..1500";
                            }
                            description "ID of the EHS event trigger entry";
                        }

                        leaf oper-state {
                            type types-sros:oper-state;
                            description "Indicates the operational state of the EHS Event Trigger Entry.";
                        }

                        container statistics {
                            description "Enter the statistics context";

                            leaf filter-match {
                                type yang:counter32;
                                description
                                    "Indicates the number of times a filter, for the specified trigger entry,
                                     matches an logger event.";
                            }

                            leaf filter-fail {
                                type yang:counter32;
                                description
                                    "Indicates the number of times a filter, for the specified trigger entry,
                                     does not match an logger event.";
                            }

                            leaf error-admin-state {
                                type yang:counter32;
                                description
                                    "Indicates the number of times the logger event will be ignored due to
                                     admin state of EHS trigger entry is out-of-service.";
                            }

                            leaf error-filter {
                                type yang:counter32;
                                description
                                    "Indicates the number of times the logger event will be ignored due to filter
                                     is not operational or is not configured in EHS trigger entry.";
                            }

                            leaf error-handler {
                                type yang:counter32;
                                description
                                    "Indicates the number of times the logger event will be ignored due to handler
                                     is not operational or is not configured in EHS trigger entry.";
                            }

                            leaf trigger-count {
                                type yang:counter32;
                                description
                                    "Indicates the number of times script execution is triggered after filter match
                                     for the specified trigger entry.";
                            }

                            leaf debounce-count {
                                type yang:counter32;
                                description
                                    "Indicates the number of times script is not executed due to debounce rule
                                     for the specified trigger entry.";
                            }

                        } // container statistics

                    } // list entry

                } // list li

                list lldp {
                    key "event";
                    description "Enter the lldp list instance";

                    leaf event {
                        type types-log:lldp-events;
                        description "Log event as a trigger for one or more EHS handlers";
                    }

                    leaf oper-state {
                        type types-sros:oper-state;
                        description "Indicates the operational state of the EHS Event Trigger.";
                    }

                    container statistics {
                        description "Enter the statistics context";

                        leaf success {
                            type yang:counter32;
                            description
                                "Indicates the number of not ignored logger event occurrences
                                 associated with EHS trigger.";
                        }

                        leaf error-no-entry {
                            type yang:counter32;
                            description
                                "Indicates the number of ignored logger event occurrences associated
                                 with EHS trigger.

                                 Event is ignored due to no trigger entry configured for this trigger.";
                        }

                        leaf error-admin-state {
                            type yang:counter32;
                            description
                                "Indicates the number of ignored logger event occurrences associated
                                 with EHS trigger.

                                 Event is ignored due to trigger may be out-of-service.";
                        }

                        leaf total {
                            type yang:counter32;
                            description "Sum of success + error-no-entry + error-admin-state.";
                        }

                    } // container statistics

                    container summary-entry-statistics {
                        description "Enter the summary-entry-statistics context";

                        leaf filter-match {
                            type yang:counter32;
                            description "Indicates the number of times a filter matches an logger event.";
                        }

                        leaf filter-fail {
                            type yang:counter32;
                            description "Indicates the number of times a filter does not match an logger event.";
                        }

                        leaf error-admin-state {
                            type yang:counter32;
                            description
                                "Indicates the number of times the logger event will be ignored due to
                                 admin state of EHS trigger entries is out-of-service.";
                        }

                        leaf error-filter {
                            type yang:counter32;
                            description
                                "Indicates the number of times the logger event will be ignored due to filter
                                 is not operational or is not configured in EHS trigger entries.";
                        }

                        leaf error-handler {
                            type yang:counter32;
                            description
                                "Indicates the number of times the logger event will be ignored due to handler
                                 is not operational or is not configured in EHS trigger entries.";
                        }

                        leaf trigger-count {
                            type yang:counter32;
                            description "Indicates the number of times script execution is triggered after filter match.";
                        }

                        leaf debounce-count {
                            type yang:counter32;
                            description "Indicates the number of times script is not executed due to debounce rule.";
                        }

                    } // container summary-entry-statistics

                    list entry {
                        key "id";
                        description "Enter the entry list instance";

                        leaf id {
                            type uint32 {
                                range "1..1500";
                            }
                            description "ID of the EHS event trigger entry";
                        }

                        leaf oper-state {
                            type types-sros:oper-state;
                            description "Indicates the operational state of the EHS Event Trigger Entry.";
                        }

                        container statistics {
                            description "Enter the statistics context";

                            leaf filter-match {
                                type yang:counter32;
                                description
                                    "Indicates the number of times a filter, for the specified trigger entry,
                                     matches an logger event.";
                            }

                            leaf filter-fail {
                                type yang:counter32;
                                description
                                    "Indicates the number of times a filter, for the specified trigger entry,
                                     does not match an logger event.";
                            }

                            leaf error-admin-state {
                                type yang:counter32;
                                description
                                    "Indicates the number of times the logger event will be ignored due to
                                     admin state of EHS trigger entry is out-of-service.";
                            }

                            leaf error-filter {
                                type yang:counter32;
                                description
                                    "Indicates the number of times the logger event will be ignored due to filter
                                     is not operational or is not configured in EHS trigger entry.";
                            }

                            leaf error-handler {
                                type yang:counter32;
                                description
                                    "Indicates the number of times the logger event will be ignored due to handler
                                     is not operational or is not configured in EHS trigger entry.";
                            }

                            leaf trigger-count {
                                type yang:counter32;
                                description
                                    "Indicates the number of times script execution is triggered after filter match
                                     for the specified trigger entry.";
                            }

                            leaf debounce-count {
                                type yang:counter32;
                                description
                                    "Indicates the number of times script is not executed due to debounce rule
                                     for the specified trigger entry.";
                            }

                        } // container statistics

                    } // list entry

                } // list lldp

                list logger {
                    key "event";
                    description "Enter the logger list instance";

                    leaf event {
                        type types-log:logger-events;
                        description "Log event as a trigger for one or more EHS handlers";
                    }

                    leaf oper-state {
                        type types-sros:oper-state;
                        description "Indicates the operational state of the EHS Event Trigger.";
                    }

                    container statistics {
                        description "Enter the statistics context";

                        leaf success {
                            type yang:counter32;
                            description
                                "Indicates the number of not ignored logger event occurrences
                                 associated with EHS trigger.";
                        }

                        leaf error-no-entry {
                            type yang:counter32;
                            description
                                "Indicates the number of ignored logger event occurrences associated
                                 with EHS trigger.

                                 Event is ignored due to no trigger entry configured for this trigger.";
                        }

                        leaf error-admin-state {
                            type yang:counter32;
                            description
                                "Indicates the number of ignored logger event occurrences associated
                                 with EHS trigger.

                                 Event is ignored due to trigger may be out-of-service.";
                        }

                        leaf total {
                            type yang:counter32;
                            description "Sum of success + error-no-entry + error-admin-state.";
                        }

                    } // container statistics

                    container summary-entry-statistics {
                        description "Enter the summary-entry-statistics context";

                        leaf filter-match {
                            type yang:counter32;
                            description "Indicates the number of times a filter matches an logger event.";
                        }

                        leaf filter-fail {
                            type yang:counter32;
                            description "Indicates the number of times a filter does not match an logger event.";
                        }

                        leaf error-admin-state {
                            type yang:counter32;
                            description
                                "Indicates the number of times the logger event will be ignored due to
                                 admin state of EHS trigger entries is out-of-service.";
                        }

                        leaf error-filter {
                            type yang:counter32;
                            description
                                "Indicates the number of times the logger event will be ignored due to filter
                                 is not operational or is not configured in EHS trigger entries.";
                        }

                        leaf error-handler {
                            type yang:counter32;
                            description
                                "Indicates the number of times the logger event will be ignored due to handler
                                 is not operational or is not configured in EHS trigger entries.";
                        }

                        leaf trigger-count {
                            type yang:counter32;
                            description "Indicates the number of times script execution is triggered after filter match.";
                        }

                        leaf debounce-count {
                            type yang:counter32;
                            description "Indicates the number of times script is not executed due to debounce rule.";
                        }

                    } // container summary-entry-statistics

                    list entry {
                        key "id";
                        description "Enter the entry list instance";

                        leaf id {
                            type uint32 {
                                range "1..1500";
                            }
                            description "ID of the EHS event trigger entry";
                        }

                        leaf oper-state {
                            type types-sros:oper-state;
                            description "Indicates the operational state of the EHS Event Trigger Entry.";
                        }

                        container statistics {
                            description "Enter the statistics context";

                            leaf filter-match {
                                type yang:counter32;
                                description
                                    "Indicates the number of times a filter, for the specified trigger entry,
                                     matches an logger event.";
                            }

                            leaf filter-fail {
                                type yang:counter32;
                                description
                                    "Indicates the number of times a filter, for the specified trigger entry,
                                     does not match an logger event.";
                            }

                            leaf error-admin-state {
                                type yang:counter32;
                                description
                                    "Indicates the number of times the logger event will be ignored due to
                                     admin state of EHS trigger entry is out-of-service.";
                            }

                            leaf error-filter {
                                type yang:counter32;
                                description
                                    "Indicates the number of times the logger event will be ignored due to filter
                                     is not operational or is not configured in EHS trigger entry.";
                            }

                            leaf error-handler {
                                type yang:counter32;
                                description
                                    "Indicates the number of times the logger event will be ignored due to handler
                                     is not operational or is not configured in EHS trigger entry.";
                            }

                            leaf trigger-count {
                                type yang:counter32;
                                description
                                    "Indicates the number of times script execution is triggered after filter match
                                     for the specified trigger entry.";
                            }

                            leaf debounce-count {
                                type yang:counter32;
                                description
                                    "Indicates the number of times script is not executed due to debounce rule
                                     for the specified trigger entry.";
                            }

                        } // container statistics

                    } // list entry

                } // list logger

                list macsec {
                    key "event";
                    description "Enter the macsec list instance";

                    leaf event {
                        type types-log:macsec-events;
                        description "Log event as a trigger for one or more EHS handlers";
                    }

                    leaf oper-state {
                        type types-sros:oper-state;
                        description "Indicates the operational state of the EHS Event Trigger.";
                    }

                    container statistics {
                        description "Enter the statistics context";

                        leaf success {
                            type yang:counter32;
                            description
                                "Indicates the number of not ignored logger event occurrences
                                 associated with EHS trigger.";
                        }

                        leaf error-no-entry {
                            type yang:counter32;
                            description
                                "Indicates the number of ignored logger event occurrences associated
                                 with EHS trigger.

                                 Event is ignored due to no trigger entry configured for this trigger.";
                        }

                        leaf error-admin-state {
                            type yang:counter32;
                            description
                                "Indicates the number of ignored logger event occurrences associated
                                 with EHS trigger.

                                 Event is ignored due to trigger may be out-of-service.";
                        }

                        leaf total {
                            type yang:counter32;
                            description "Sum of success + error-no-entry + error-admin-state.";
                        }

                    } // container statistics

                    container summary-entry-statistics {
                        description "Enter the summary-entry-statistics context";

                        leaf filter-match {
                            type yang:counter32;
                            description "Indicates the number of times a filter matches an logger event.";
                        }

                        leaf filter-fail {
                            type yang:counter32;
                            description "Indicates the number of times a filter does not match an logger event.";
                        }

                        leaf error-admin-state {
                            type yang:counter32;
                            description
                                "Indicates the number of times the logger event will be ignored due to
                                 admin state of EHS trigger entries is out-of-service.";
                        }

                        leaf error-filter {
                            type yang:counter32;
                            description
                                "Indicates the number of times the logger event will be ignored due to filter
                                 is not operational or is not configured in EHS trigger entries.";
                        }

                        leaf error-handler {
                            type yang:counter32;
                            description
                                "Indicates the number of times the logger event will be ignored due to handler
                                 is not operational or is not configured in EHS trigger entries.";
                        }

                        leaf trigger-count {
                            type yang:counter32;
                            description "Indicates the number of times script execution is triggered after filter match.";
                        }

                        leaf debounce-count {
                            type yang:counter32;
                            description "Indicates the number of times script is not executed due to debounce rule.";
                        }

                    } // container summary-entry-statistics

                    list entry {
                        key "id";
                        description "Enter the entry list instance";

                        leaf id {
                            type uint32 {
                                range "1..1500";
                            }
                            description "ID of the EHS event trigger entry";
                        }

                        leaf oper-state {
                            type types-sros:oper-state;
                            description "Indicates the operational state of the EHS Event Trigger Entry.";
                        }

                        container statistics {
                            description "Enter the statistics context";

                            leaf filter-match {
                                type yang:counter32;
                                description
                                    "Indicates the number of times a filter, for the specified trigger entry,
                                     matches an logger event.";
                            }

                            leaf filter-fail {
                                type yang:counter32;
                                description
                                    "Indicates the number of times a filter, for the specified trigger entry,
                                     does not match an logger event.";
                            }

                            leaf error-admin-state {
                                type yang:counter32;
                                description
                                    "Indicates the number of times the logger event will be ignored due to
                                     admin state of EHS trigger entry is out-of-service.";
                            }

                            leaf error-filter {
                                type yang:counter32;
                                description
                                    "Indicates the number of times the logger event will be ignored due to filter
                                     is not operational or is not configured in EHS trigger entry.";
                            }

                            leaf error-handler {
                                type yang:counter32;
                                description
                                    "Indicates the number of times the logger event will be ignored due to handler
                                     is not operational or is not configured in EHS trigger entry.";
                            }

                            leaf trigger-count {
                                type yang:counter32;
                                description
                                    "Indicates the number of times script execution is triggered after filter match
                                     for the specified trigger entry.";
                            }

                            leaf debounce-count {
                                type yang:counter32;
                                description
                                    "Indicates the number of times script is not executed due to debounce rule
                                     for the specified trigger entry.";
                            }

                        } // container statistics

                    } // list entry

                } // list macsec

                list mcpath {
                    key "event";
                    description "Enter the mcpath list instance";

                    leaf event {
                        type types-log:mcpath-events;
                        description "Log event as a trigger for one or more EHS handlers";
                    }

                    leaf oper-state {
                        type types-sros:oper-state;
                        description "Indicates the operational state of the EHS Event Trigger.";
                    }

                    container statistics {
                        description "Enter the statistics context";

                        leaf success {
                            type yang:counter32;
                            description
                                "Indicates the number of not ignored logger event occurrences
                                 associated with EHS trigger.";
                        }

                        leaf error-no-entry {
                            type yang:counter32;
                            description
                                "Indicates the number of ignored logger event occurrences associated
                                 with EHS trigger.

                                 Event is ignored due to no trigger entry configured for this trigger.";
                        }

                        leaf error-admin-state {
                            type yang:counter32;
                            description
                                "Indicates the number of ignored logger event occurrences associated
                                 with EHS trigger.

                                 Event is ignored due to trigger may be out-of-service.";
                        }

                        leaf total {
                            type yang:counter32;
                            description "Sum of success + error-no-entry + error-admin-state.";
                        }

                    } // container statistics

                    container summary-entry-statistics {
                        description "Enter the summary-entry-statistics context";

                        leaf filter-match {
                            type yang:counter32;
                            description "Indicates the number of times a filter matches an logger event.";
                        }

                        leaf filter-fail {
                            type yang:counter32;
                            description "Indicates the number of times a filter does not match an logger event.";
                        }

                        leaf error-admin-state {
                            type yang:counter32;
                            description
                                "Indicates the number of times the logger event will be ignored due to
                                 admin state of EHS trigger entries is out-of-service.";
                        }

                        leaf error-filter {
                            type yang:counter32;
                            description
                                "Indicates the number of times the logger event will be ignored due to filter
                                 is not operational or is not configured in EHS trigger entries.";
                        }

                        leaf error-handler {
                            type yang:counter32;
                            description
                                "Indicates the number of times the logger event will be ignored due to handler
                                 is not operational or is not configured in EHS trigger entries.";
                        }

                        leaf trigger-count {
                            type yang:counter32;
                            description "Indicates the number of times script execution is triggered after filter match.";
                        }

                        leaf debounce-count {
                            type yang:counter32;
                            description "Indicates the number of times script is not executed due to debounce rule.";
                        }

                    } // container summary-entry-statistics

                    list entry {
                        key "id";
                        description "Enter the entry list instance";

                        leaf id {
                            type uint32 {
                                range "1..1500";
                            }
                            description "ID of the EHS event trigger entry";
                        }

                        leaf oper-state {
                            type types-sros:oper-state;
                            description "Indicates the operational state of the EHS Event Trigger Entry.";
                        }

                        container statistics {
                            description "Enter the statistics context";

                            leaf filter-match {
                                type yang:counter32;
                                description
                                    "Indicates the number of times a filter, for the specified trigger entry,
                                     matches an logger event.";
                            }

                            leaf filter-fail {
                                type yang:counter32;
                                description
                                    "Indicates the number of times a filter, for the specified trigger entry,
                                     does not match an logger event.";
                            }

                            leaf error-admin-state {
                                type yang:counter32;
                                description
                                    "Indicates the number of times the logger event will be ignored due to
                                     admin state of EHS trigger entry is out-of-service.";
                            }

                            leaf error-filter {
                                type yang:counter32;
                                description
                                    "Indicates the number of times the logger event will be ignored due to filter
                                     is not operational or is not configured in EHS trigger entry.";
                            }

                            leaf error-handler {
                                type yang:counter32;
                                description
                                    "Indicates the number of times the logger event will be ignored due to handler
                                     is not operational or is not configured in EHS trigger entry.";
                            }

                            leaf trigger-count {
                                type yang:counter32;
                                description
                                    "Indicates the number of times script execution is triggered after filter match
                                     for the specified trigger entry.";
                            }

                            leaf debounce-count {
                                type yang:counter32;
                                description
                                    "Indicates the number of times script is not executed due to debounce rule
                                     for the specified trigger entry.";
                            }

                        } // container statistics

                    } // list entry

                } // list mcpath

                list mc-redundancy {
                    key "event";
                    description "Enter the mc-redundancy list instance";

                    leaf event {
                        type types-log:mc-redundancy-events;
                        description "Log event as a trigger for one or more EHS handlers";
                    }

                    leaf oper-state {
                        type types-sros:oper-state;
                        description "Indicates the operational state of the EHS Event Trigger.";
                    }

                    container statistics {
                        description "Enter the statistics context";

                        leaf success {
                            type yang:counter32;
                            description
                                "Indicates the number of not ignored logger event occurrences
                                 associated with EHS trigger.";
                        }

                        leaf error-no-entry {
                            type yang:counter32;
                            description
                                "Indicates the number of ignored logger event occurrences associated
                                 with EHS trigger.

                                 Event is ignored due to no trigger entry configured for this trigger.";
                        }

                        leaf error-admin-state {
                            type yang:counter32;
                            description
                                "Indicates the number of ignored logger event occurrences associated
                                 with EHS trigger.

                                 Event is ignored due to trigger may be out-of-service.";
                        }

                        leaf total {
                            type yang:counter32;
                            description "Sum of success + error-no-entry + error-admin-state.";
                        }

                    } // container statistics

                    container summary-entry-statistics {
                        description "Enter the summary-entry-statistics context";

                        leaf filter-match {
                            type yang:counter32;
                            description "Indicates the number of times a filter matches an logger event.";
                        }

                        leaf filter-fail {
                            type yang:counter32;
                            description "Indicates the number of times a filter does not match an logger event.";
                        }

                        leaf error-admin-state {
                            type yang:counter32;
                            description
                                "Indicates the number of times the logger event will be ignored due to
                                 admin state of EHS trigger entries is out-of-service.";
                        }

                        leaf error-filter {
                            type yang:counter32;
                            description
                                "Indicates the number of times the logger event will be ignored due to filter
                                 is not operational or is not configured in EHS trigger entries.";
                        }

                        leaf error-handler {
                            type yang:counter32;
                            description
                                "Indicates the number of times the logger event will be ignored due to handler
                                 is not operational or is not configured in EHS trigger entries.";
                        }

                        leaf trigger-count {
                            type yang:counter32;
                            description "Indicates the number of times script execution is triggered after filter match.";
                        }

                        leaf debounce-count {
                            type yang:counter32;
                            description "Indicates the number of times script is not executed due to debounce rule.";
                        }

                    } // container summary-entry-statistics

                    list entry {
                        key "id";
                        description "Enter the entry list instance";

                        leaf id {
                            type uint32 {
                                range "1..1500";
                            }
                            description "ID of the EHS event trigger entry";
                        }

                        leaf oper-state {
                            type types-sros:oper-state;
                            description "Indicates the operational state of the EHS Event Trigger Entry.";
                        }

                        container statistics {
                            description "Enter the statistics context";

                            leaf filter-match {
                                type yang:counter32;
                                description
                                    "Indicates the number of times a filter, for the specified trigger entry,
                                     matches an logger event.";
                            }

                            leaf filter-fail {
                                type yang:counter32;
                                description
                                    "Indicates the number of times a filter, for the specified trigger entry,
                                     does not match an logger event.";
                            }

                            leaf error-admin-state {
                                type yang:counter32;
                                description
                                    "Indicates the number of times the logger event will be ignored due to
                                     admin state of EHS trigger entry is out-of-service.";
                            }

                            leaf error-filter {
                                type yang:counter32;
                                description
                                    "Indicates the number of times the logger event will be ignored due to filter
                                     is not operational or is not configured in EHS trigger entry.";
                            }

                            leaf error-handler {
                                type yang:counter32;
                                description
                                    "Indicates the number of times the logger event will be ignored due to handler
                                     is not operational or is not configured in EHS trigger entry.";
                            }

                            leaf trigger-count {
                                type yang:counter32;
                                description
                                    "Indicates the number of times script execution is triggered after filter match
                                     for the specified trigger entry.";
                            }

                            leaf debounce-count {
                                type yang:counter32;
                                description
                                    "Indicates the number of times script is not executed due to debounce rule
                                     for the specified trigger entry.";
                            }

                        } // container statistics

                    } // list entry

                } // list mc-redundancy

                list mgmt-core {
                    key "event";
                    description "Enter the mgmt-core list instance";

                    leaf event {
                        type types-log:mgmt-core-events;
                        description "Log event as a trigger for one or more EHS handlers";
                    }

                    leaf oper-state {
                        type types-sros:oper-state;
                        description "Indicates the operational state of the EHS Event Trigger.";
                    }

                    container statistics {
                        description "Enter the statistics context";

                        leaf success {
                            type yang:counter32;
                            description
                                "Indicates the number of not ignored logger event occurrences
                                 associated with EHS trigger.";
                        }

                        leaf error-no-entry {
                            type yang:counter32;
                            description
                                "Indicates the number of ignored logger event occurrences associated
                                 with EHS trigger.

                                 Event is ignored due to no trigger entry configured for this trigger.";
                        }

                        leaf error-admin-state {
                            type yang:counter32;
                            description
                                "Indicates the number of ignored logger event occurrences associated
                                 with EHS trigger.

                                 Event is ignored due to trigger may be out-of-service.";
                        }

                        leaf total {
                            type yang:counter32;
                            description "Sum of success + error-no-entry + error-admin-state.";
                        }

                    } // container statistics

                    container summary-entry-statistics {
                        description "Enter the summary-entry-statistics context";

                        leaf filter-match {
                            type yang:counter32;
                            description "Indicates the number of times a filter matches an logger event.";
                        }

                        leaf filter-fail {
                            type yang:counter32;
                            description "Indicates the number of times a filter does not match an logger event.";
                        }

                        leaf error-admin-state {
                            type yang:counter32;
                            description
                                "Indicates the number of times the logger event will be ignored due to
                                 admin state of EHS trigger entries is out-of-service.";
                        }

                        leaf error-filter {
                            type yang:counter32;
                            description
                                "Indicates the number of times the logger event will be ignored due to filter
                                 is not operational or is not configured in EHS trigger entries.";
                        }

                        leaf error-handler {
                            type yang:counter32;
                            description
                                "Indicates the number of times the logger event will be ignored due to handler
                                 is not operational or is not configured in EHS trigger entries.";
                        }

                        leaf trigger-count {
                            type yang:counter32;
                            description "Indicates the number of times script execution is triggered after filter match.";
                        }

                        leaf debounce-count {
                            type yang:counter32;
                            description "Indicates the number of times script is not executed due to debounce rule.";
                        }

                    } // container summary-entry-statistics

                    list entry {
                        key "id";
                        description "Enter the entry list instance";

                        leaf id {
                            type uint32 {
                                range "1..1500";
                            }
                            description "ID of the EHS event trigger entry";
                        }

                        leaf oper-state {
                            type types-sros:oper-state;
                            description "Indicates the operational state of the EHS Event Trigger Entry.";
                        }

                        container statistics {
                            description "Enter the statistics context";

                            leaf filter-match {
                                type yang:counter32;
                                description
                                    "Indicates the number of times a filter, for the specified trigger entry,
                                     matches an logger event.";
                            }

                            leaf filter-fail {
                                type yang:counter32;
                                description
                                    "Indicates the number of times a filter, for the specified trigger entry,
                                     does not match an logger event.";
                            }

                            leaf error-admin-state {
                                type yang:counter32;
                                description
                                    "Indicates the number of times the logger event will be ignored due to
                                     admin state of EHS trigger entry is out-of-service.";
                            }

                            leaf error-filter {
                                type yang:counter32;
                                description
                                    "Indicates the number of times the logger event will be ignored due to filter
                                     is not operational or is not configured in EHS trigger entry.";
                            }

                            leaf error-handler {
                                type yang:counter32;
                                description
                                    "Indicates the number of times the logger event will be ignored due to handler
                                     is not operational or is not configured in EHS trigger entry.";
                            }

                            leaf trigger-count {
                                type yang:counter32;
                                description
                                    "Indicates the number of times script execution is triggered after filter match
                                     for the specified trigger entry.";
                            }

                            leaf debounce-count {
                                type yang:counter32;
                                description
                                    "Indicates the number of times script is not executed due to debounce rule
                                     for the specified trigger entry.";
                            }

                        } // container statistics

                    } // list entry

                } // list mgmt-core

                list mirror {
                    key "event";
                    description "Enter the mirror list instance";

                    leaf event {
                        type types-log:mirror-events;
                        description "Log event as a trigger for one or more EHS handlers";
                    }

                    leaf oper-state {
                        type types-sros:oper-state;
                        description "Indicates the operational state of the EHS Event Trigger.";
                    }

                    container statistics {
                        description "Enter the statistics context";

                        leaf success {
                            type yang:counter32;
                            description
                                "Indicates the number of not ignored logger event occurrences
                                 associated with EHS trigger.";
                        }

                        leaf error-no-entry {
                            type yang:counter32;
                            description
                                "Indicates the number of ignored logger event occurrences associated
                                 with EHS trigger.

                                 Event is ignored due to no trigger entry configured for this trigger.";
                        }

                        leaf error-admin-state {
                            type yang:counter32;
                            description
                                "Indicates the number of ignored logger event occurrences associated
                                 with EHS trigger.

                                 Event is ignored due to trigger may be out-of-service.";
                        }

                        leaf total {
                            type yang:counter32;
                            description "Sum of success + error-no-entry + error-admin-state.";
                        }

                    } // container statistics

                    container summary-entry-statistics {
                        description "Enter the summary-entry-statistics context";

                        leaf filter-match {
                            type yang:counter32;
                            description "Indicates the number of times a filter matches an logger event.";
                        }

                        leaf filter-fail {
                            type yang:counter32;
                            description "Indicates the number of times a filter does not match an logger event.";
                        }

                        leaf error-admin-state {
                            type yang:counter32;
                            description
                                "Indicates the number of times the logger event will be ignored due to
                                 admin state of EHS trigger entries is out-of-service.";
                        }

                        leaf error-filter {
                            type yang:counter32;
                            description
                                "Indicates the number of times the logger event will be ignored due to filter
                                 is not operational or is not configured in EHS trigger entries.";
                        }

                        leaf error-handler {
                            type yang:counter32;
                            description
                                "Indicates the number of times the logger event will be ignored due to handler
                                 is not operational or is not configured in EHS trigger entries.";
                        }

                        leaf trigger-count {
                            type yang:counter32;
                            description "Indicates the number of times script execution is triggered after filter match.";
                        }

                        leaf debounce-count {
                            type yang:counter32;
                            description "Indicates the number of times script is not executed due to debounce rule.";
                        }

                    } // container summary-entry-statistics

                    list entry {
                        key "id";
                        description "Enter the entry list instance";

                        leaf id {
                            type uint32 {
                                range "1..1500";
                            }
                            description "ID of the EHS event trigger entry";
                        }

                        leaf oper-state {
                            type types-sros:oper-state;
                            description "Indicates the operational state of the EHS Event Trigger Entry.";
                        }

                        container statistics {
                            description "Enter the statistics context";

                            leaf filter-match {
                                type yang:counter32;
                                description
                                    "Indicates the number of times a filter, for the specified trigger entry,
                                     matches an logger event.";
                            }

                            leaf filter-fail {
                                type yang:counter32;
                                description
                                    "Indicates the number of times a filter, for the specified trigger entry,
                                     does not match an logger event.";
                            }

                            leaf error-admin-state {
                                type yang:counter32;
                                description
                                    "Indicates the number of times the logger event will be ignored due to
                                     admin state of EHS trigger entry is out-of-service.";
                            }

                            leaf error-filter {
                                type yang:counter32;
                                description
                                    "Indicates the number of times the logger event will be ignored due to filter
                                     is not operational or is not configured in EHS trigger entry.";
                            }

                            leaf error-handler {
                                type yang:counter32;
                                description
                                    "Indicates the number of times the logger event will be ignored due to handler
                                     is not operational or is not configured in EHS trigger entry.";
                            }

                            leaf trigger-count {
                                type yang:counter32;
                                description
                                    "Indicates the number of times script execution is triggered after filter match
                                     for the specified trigger entry.";
                            }

                            leaf debounce-count {
                                type yang:counter32;
                                description
                                    "Indicates the number of times script is not executed due to debounce rule
                                     for the specified trigger entry.";
                            }

                        } // container statistics

                    } // list entry

                } // list mirror

                list mld {
                    key "event";
                    description "Enter the mld list instance";

                    leaf event {
                        type types-log:mld-events;
                        description "Log event as a trigger for one or more EHS handlers";
                    }

                    leaf oper-state {
                        type types-sros:oper-state;
                        description "Indicates the operational state of the EHS Event Trigger.";
                    }

                    container statistics {
                        description "Enter the statistics context";

                        leaf success {
                            type yang:counter32;
                            description
                                "Indicates the number of not ignored logger event occurrences
                                 associated with EHS trigger.";
                        }

                        leaf error-no-entry {
                            type yang:counter32;
                            description
                                "Indicates the number of ignored logger event occurrences associated
                                 with EHS trigger.

                                 Event is ignored due to no trigger entry configured for this trigger.";
                        }

                        leaf error-admin-state {
                            type yang:counter32;
                            description
                                "Indicates the number of ignored logger event occurrences associated
                                 with EHS trigger.

                                 Event is ignored due to trigger may be out-of-service.";
                        }

                        leaf total {
                            type yang:counter32;
                            description "Sum of success + error-no-entry + error-admin-state.";
                        }

                    } // container statistics

                    container summary-entry-statistics {
                        description "Enter the summary-entry-statistics context";

                        leaf filter-match {
                            type yang:counter32;
                            description "Indicates the number of times a filter matches an logger event.";
                        }

                        leaf filter-fail {
                            type yang:counter32;
                            description "Indicates the number of times a filter does not match an logger event.";
                        }

                        leaf error-admin-state {
                            type yang:counter32;
                            description
                                "Indicates the number of times the logger event will be ignored due to
                                 admin state of EHS trigger entries is out-of-service.";
                        }

                        leaf error-filter {
                            type yang:counter32;
                            description
                                "Indicates the number of times the logger event will be ignored due to filter
                                 is not operational or is not configured in EHS trigger entries.";
                        }

                        leaf error-handler {
                            type yang:counter32;
                            description
                                "Indicates the number of times the logger event will be ignored due to handler
                                 is not operational or is not configured in EHS trigger entries.";
                        }

                        leaf trigger-count {
                            type yang:counter32;
                            description "Indicates the number of times script execution is triggered after filter match.";
                        }

                        leaf debounce-count {
                            type yang:counter32;
                            description "Indicates the number of times script is not executed due to debounce rule.";
                        }

                    } // container summary-entry-statistics

                    list entry {
                        key "id";
                        description "Enter the entry list instance";

                        leaf id {
                            type uint32 {
                                range "1..1500";
                            }
                            description "ID of the EHS event trigger entry";
                        }

                        leaf oper-state {
                            type types-sros:oper-state;
                            description "Indicates the operational state of the EHS Event Trigger Entry.";
                        }

                        container statistics {
                            description "Enter the statistics context";

                            leaf filter-match {
                                type yang:counter32;
                                description
                                    "Indicates the number of times a filter, for the specified trigger entry,
                                     matches an logger event.";
                            }

                            leaf filter-fail {
                                type yang:counter32;
                                description
                                    "Indicates the number of times a filter, for the specified trigger entry,
                                     does not match an logger event.";
                            }

                            leaf error-admin-state {
                                type yang:counter32;
                                description
                                    "Indicates the number of times the logger event will be ignored due to
                                     admin state of EHS trigger entry is out-of-service.";
                            }

                            leaf error-filter {
                                type yang:counter32;
                                description
                                    "Indicates the number of times the logger event will be ignored due to filter
                                     is not operational or is not configured in EHS trigger entry.";
                            }

                            leaf error-handler {
                                type yang:counter32;
                                description
                                    "Indicates the number of times the logger event will be ignored due to handler
                                     is not operational or is not configured in EHS trigger entry.";
                            }

                            leaf trigger-count {
                                type yang:counter32;
                                description
                                    "Indicates the number of times script execution is triggered after filter match
                                     for the specified trigger entry.";
                            }

                            leaf debounce-count {
                                type yang:counter32;
                                description
                                    "Indicates the number of times script is not executed due to debounce rule
                                     for the specified trigger entry.";
                            }

                        } // container statistics

                    } // list entry

                } // list mld

                list mld-snooping {
                    key "event";
                    description "Enter the mld-snooping list instance";

                    leaf event {
                        type types-log:mld-snooping-events;
                        description "Log event as a trigger for one or more EHS handlers";
                    }

                    leaf oper-state {
                        type types-sros:oper-state;
                        description "Indicates the operational state of the EHS Event Trigger.";
                    }

                    container statistics {
                        description "Enter the statistics context";

                        leaf success {
                            type yang:counter32;
                            description
                                "Indicates the number of not ignored logger event occurrences
                                 associated with EHS trigger.";
                        }

                        leaf error-no-entry {
                            type yang:counter32;
                            description
                                "Indicates the number of ignored logger event occurrences associated
                                 with EHS trigger.

                                 Event is ignored due to no trigger entry configured for this trigger.";
                        }

                        leaf error-admin-state {
                            type yang:counter32;
                            description
                                "Indicates the number of ignored logger event occurrences associated
                                 with EHS trigger.

                                 Event is ignored due to trigger may be out-of-service.";
                        }

                        leaf total {
                            type yang:counter32;
                            description "Sum of success + error-no-entry + error-admin-state.";
                        }

                    } // container statistics

                    container summary-entry-statistics {
                        description "Enter the summary-entry-statistics context";

                        leaf filter-match {
                            type yang:counter32;
                            description "Indicates the number of times a filter matches an logger event.";
                        }

                        leaf filter-fail {
                            type yang:counter32;
                            description "Indicates the number of times a filter does not match an logger event.";
                        }

                        leaf error-admin-state {
                            type yang:counter32;
                            description
                                "Indicates the number of times the logger event will be ignored due to
                                 admin state of EHS trigger entries is out-of-service.";
                        }

                        leaf error-filter {
                            type yang:counter32;
                            description
                                "Indicates the number of times the logger event will be ignored due to filter
                                 is not operational or is not configured in EHS trigger entries.";
                        }

                        leaf error-handler {
                            type yang:counter32;
                            description
                                "Indicates the number of times the logger event will be ignored due to handler
                                 is not operational or is not configured in EHS trigger entries.";
                        }

                        leaf trigger-count {
                            type yang:counter32;
                            description "Indicates the number of times script execution is triggered after filter match.";
                        }

                        leaf debounce-count {
                            type yang:counter32;
                            description "Indicates the number of times script is not executed due to debounce rule.";
                        }

                    } // container summary-entry-statistics

                    list entry {
                        key "id";
                        description "Enter the entry list instance";

                        leaf id {
                            type uint32 {
                                range "1..1500";
                            }
                            description "ID of the EHS event trigger entry";
                        }

                        leaf oper-state {
                            type types-sros:oper-state;
                            description "Indicates the operational state of the EHS Event Trigger Entry.";
                        }

                        container statistics {
                            description "Enter the statistics context";

                            leaf filter-match {
                                type yang:counter32;
                                description
                                    "Indicates the number of times a filter, for the specified trigger entry,
                                     matches an logger event.";
                            }

                            leaf filter-fail {
                                type yang:counter32;
                                description
                                    "Indicates the number of times a filter, for the specified trigger entry,
                                     does not match an logger event.";
                            }

                            leaf error-admin-state {
                                type yang:counter32;
                                description
                                    "Indicates the number of times the logger event will be ignored due to
                                     admin state of EHS trigger entry is out-of-service.";
                            }

                            leaf error-filter {
                                type yang:counter32;
                                description
                                    "Indicates the number of times the logger event will be ignored due to filter
                                     is not operational or is not configured in EHS trigger entry.";
                            }

                            leaf error-handler {
                                type yang:counter32;
                                description
                                    "Indicates the number of times the logger event will be ignored due to handler
                                     is not operational or is not configured in EHS trigger entry.";
                            }

                            leaf trigger-count {
                                type yang:counter32;
                                description
                                    "Indicates the number of times script execution is triggered after filter match
                                     for the specified trigger entry.";
                            }

                            leaf debounce-count {
                                type yang:counter32;
                                description
                                    "Indicates the number of times script is not executed due to debounce rule
                                     for the specified trigger entry.";
                            }

                        } // container statistics

                    } // list entry

                } // list mld-snooping

                list mpls {
                    key "event";
                    description "Enter the mpls list instance";

                    leaf event {
                        type types-log:mpls-events;
                        description "Log event as a trigger for one or more EHS handlers";
                    }

                    leaf oper-state {
                        type types-sros:oper-state;
                        description "Indicates the operational state of the EHS Event Trigger.";
                    }

                    container statistics {
                        description "Enter the statistics context";

                        leaf success {
                            type yang:counter32;
                            description
                                "Indicates the number of not ignored logger event occurrences
                                 associated with EHS trigger.";
                        }

                        leaf error-no-entry {
                            type yang:counter32;
                            description
                                "Indicates the number of ignored logger event occurrences associated
                                 with EHS trigger.

                                 Event is ignored due to no trigger entry configured for this trigger.";
                        }

                        leaf error-admin-state {
                            type yang:counter32;
                            description
                                "Indicates the number of ignored logger event occurrences associated
                                 with EHS trigger.

                                 Event is ignored due to trigger may be out-of-service.";
                        }

                        leaf total {
                            type yang:counter32;
                            description "Sum of success + error-no-entry + error-admin-state.";
                        }

                    } // container statistics

                    container summary-entry-statistics {
                        description "Enter the summary-entry-statistics context";

                        leaf filter-match {
                            type yang:counter32;
                            description "Indicates the number of times a filter matches an logger event.";
                        }

                        leaf filter-fail {
                            type yang:counter32;
                            description "Indicates the number of times a filter does not match an logger event.";
                        }

                        leaf error-admin-state {
                            type yang:counter32;
                            description
                                "Indicates the number of times the logger event will be ignored due to
                                 admin state of EHS trigger entries is out-of-service.";
                        }

                        leaf error-filter {
                            type yang:counter32;
                            description
                                "Indicates the number of times the logger event will be ignored due to filter
                                 is not operational or is not configured in EHS trigger entries.";
                        }

                        leaf error-handler {
                            type yang:counter32;
                            description
                                "Indicates the number of times the logger event will be ignored due to handler
                                 is not operational or is not configured in EHS trigger entries.";
                        }

                        leaf trigger-count {
                            type yang:counter32;
                            description "Indicates the number of times script execution is triggered after filter match.";
                        }

                        leaf debounce-count {
                            type yang:counter32;
                            description "Indicates the number of times script is not executed due to debounce rule.";
                        }

                    } // container summary-entry-statistics

                    list entry {
                        key "id";
                        description "Enter the entry list instance";

                        leaf id {
                            type uint32 {
                                range "1..1500";
                            }
                            description "ID of the EHS event trigger entry";
                        }

                        leaf oper-state {
                            type types-sros:oper-state;
                            description "Indicates the operational state of the EHS Event Trigger Entry.";
                        }

                        container statistics {
                            description "Enter the statistics context";

                            leaf filter-match {
                                type yang:counter32;
                                description
                                    "Indicates the number of times a filter, for the specified trigger entry,
                                     matches an logger event.";
                            }

                            leaf filter-fail {
                                type yang:counter32;
                                description
                                    "Indicates the number of times a filter, for the specified trigger entry,
                                     does not match an logger event.";
                            }

                            leaf error-admin-state {
                                type yang:counter32;
                                description
                                    "Indicates the number of times the logger event will be ignored due to
                                     admin state of EHS trigger entry is out-of-service.";
                            }

                            leaf error-filter {
                                type yang:counter32;
                                description
                                    "Indicates the number of times the logger event will be ignored due to filter
                                     is not operational or is not configured in EHS trigger entry.";
                            }

                            leaf error-handler {
                                type yang:counter32;
                                description
                                    "Indicates the number of times the logger event will be ignored due to handler
                                     is not operational or is not configured in EHS trigger entry.";
                            }

                            leaf trigger-count {
                                type yang:counter32;
                                description
                                    "Indicates the number of times script execution is triggered after filter match
                                     for the specified trigger entry.";
                            }

                            leaf debounce-count {
                                type yang:counter32;
                                description
                                    "Indicates the number of times script is not executed due to debounce rule
                                     for the specified trigger entry.";
                            }

                        } // container statistics

                    } // list entry

                } // list mpls

                list mpls-tp {
                    key "event";
                    description "Enter the mpls-tp list instance";

                    leaf event {
                        type types-log:mpls-tp-events;
                        description "Log event as a trigger for one or more EHS handlers";
                    }

                    leaf oper-state {
                        type types-sros:oper-state;
                        description "Indicates the operational state of the EHS Event Trigger.";
                    }

                    container statistics {
                        description "Enter the statistics context";

                        leaf success {
                            type yang:counter32;
                            description
                                "Indicates the number of not ignored logger event occurrences
                                 associated with EHS trigger.";
                        }

                        leaf error-no-entry {
                            type yang:counter32;
                            description
                                "Indicates the number of ignored logger event occurrences associated
                                 with EHS trigger.

                                 Event is ignored due to no trigger entry configured for this trigger.";
                        }

                        leaf error-admin-state {
                            type yang:counter32;
                            description
                                "Indicates the number of ignored logger event occurrences associated
                                 with EHS trigger.

                                 Event is ignored due to trigger may be out-of-service.";
                        }

                        leaf total {
                            type yang:counter32;
                            description "Sum of success + error-no-entry + error-admin-state.";
                        }

                    } // container statistics

                    container summary-entry-statistics {
                        description "Enter the summary-entry-statistics context";

                        leaf filter-match {
                            type yang:counter32;
                            description "Indicates the number of times a filter matches an logger event.";
                        }

                        leaf filter-fail {
                            type yang:counter32;
                            description "Indicates the number of times a filter does not match an logger event.";
                        }

                        leaf error-admin-state {
                            type yang:counter32;
                            description
                                "Indicates the number of times the logger event will be ignored due to
                                 admin state of EHS trigger entries is out-of-service.";
                        }

                        leaf error-filter {
                            type yang:counter32;
                            description
                                "Indicates the number of times the logger event will be ignored due to filter
                                 is not operational or is not configured in EHS trigger entries.";
                        }

                        leaf error-handler {
                            type yang:counter32;
                            description
                                "Indicates the number of times the logger event will be ignored due to handler
                                 is not operational or is not configured in EHS trigger entries.";
                        }

                        leaf trigger-count {
                            type yang:counter32;
                            description "Indicates the number of times script execution is triggered after filter match.";
                        }

                        leaf debounce-count {
                            type yang:counter32;
                            description "Indicates the number of times script is not executed due to debounce rule.";
                        }

                    } // container summary-entry-statistics

                    list entry {
                        key "id";
                        description "Enter the entry list instance";

                        leaf id {
                            type uint32 {
                                range "1..1500";
                            }
                            description "ID of the EHS event trigger entry";
                        }

                        leaf oper-state {
                            type types-sros:oper-state;
                            description "Indicates the operational state of the EHS Event Trigger Entry.";
                        }

                        container statistics {
                            description "Enter the statistics context";

                            leaf filter-match {
                                type yang:counter32;
                                description
                                    "Indicates the number of times a filter, for the specified trigger entry,
                                     matches an logger event.";
                            }

                            leaf filter-fail {
                                type yang:counter32;
                                description
                                    "Indicates the number of times a filter, for the specified trigger entry,
                                     does not match an logger event.";
                            }

                            leaf error-admin-state {
                                type yang:counter32;
                                description
                                    "Indicates the number of times the logger event will be ignored due to
                                     admin state of EHS trigger entry is out-of-service.";
                            }

                            leaf error-filter {
                                type yang:counter32;
                                description
                                    "Indicates the number of times the logger event will be ignored due to filter
                                     is not operational or is not configured in EHS trigger entry.";
                            }

                            leaf error-handler {
                                type yang:counter32;
                                description
                                    "Indicates the number of times the logger event will be ignored due to handler
                                     is not operational or is not configured in EHS trigger entry.";
                            }

                            leaf trigger-count {
                                type yang:counter32;
                                description
                                    "Indicates the number of times script execution is triggered after filter match
                                     for the specified trigger entry.";
                            }

                            leaf debounce-count {
                                type yang:counter32;
                                description
                                    "Indicates the number of times script is not executed due to debounce rule
                                     for the specified trigger entry.";
                            }

                        } // container statistics

                    } // list entry

                } // list mpls-tp

                list msdp {
                    key "event";
                    description "Enter the msdp list instance";

                    leaf event {
                        type types-log:msdp-events;
                        description "Log event as a trigger for one or more EHS handlers";
                    }

                    leaf oper-state {
                        type types-sros:oper-state;
                        description "Indicates the operational state of the EHS Event Trigger.";
                    }

                    container statistics {
                        description "Enter the statistics context";

                        leaf success {
                            type yang:counter32;
                            description
                                "Indicates the number of not ignored logger event occurrences
                                 associated with EHS trigger.";
                        }

                        leaf error-no-entry {
                            type yang:counter32;
                            description
                                "Indicates the number of ignored logger event occurrences associated
                                 with EHS trigger.

                                 Event is ignored due to no trigger entry configured for this trigger.";
                        }

                        leaf error-admin-state {
                            type yang:counter32;
                            description
                                "Indicates the number of ignored logger event occurrences associated
                                 with EHS trigger.

                                 Event is ignored due to trigger may be out-of-service.";
                        }

                        leaf total {
                            type yang:counter32;
                            description "Sum of success + error-no-entry + error-admin-state.";
                        }

                    } // container statistics

                    container summary-entry-statistics {
                        description "Enter the summary-entry-statistics context";

                        leaf filter-match {
                            type yang:counter32;
                            description "Indicates the number of times a filter matches an logger event.";
                        }

                        leaf filter-fail {
                            type yang:counter32;
                            description "Indicates the number of times a filter does not match an logger event.";
                        }

                        leaf error-admin-state {
                            type yang:counter32;
                            description
                                "Indicates the number of times the logger event will be ignored due to
                                 admin state of EHS trigger entries is out-of-service.";
                        }

                        leaf error-filter {
                            type yang:counter32;
                            description
                                "Indicates the number of times the logger event will be ignored due to filter
                                 is not operational or is not configured in EHS trigger entries.";
                        }

                        leaf error-handler {
                            type yang:counter32;
                            description
                                "Indicates the number of times the logger event will be ignored due to handler
                                 is not operational or is not configured in EHS trigger entries.";
                        }

                        leaf trigger-count {
                            type yang:counter32;
                            description "Indicates the number of times script execution is triggered after filter match.";
                        }

                        leaf debounce-count {
                            type yang:counter32;
                            description "Indicates the number of times script is not executed due to debounce rule.";
                        }

                    } // container summary-entry-statistics

                    list entry {
                        key "id";
                        description "Enter the entry list instance";

                        leaf id {
                            type uint32 {
                                range "1..1500";
                            }
                            description "ID of the EHS event trigger entry";
                        }

                        leaf oper-state {
                            type types-sros:oper-state;
                            description "Indicates the operational state of the EHS Event Trigger Entry.";
                        }

                        container statistics {
                            description "Enter the statistics context";

                            leaf filter-match {
                                type yang:counter32;
                                description
                                    "Indicates the number of times a filter, for the specified trigger entry,
                                     matches an logger event.";
                            }

                            leaf filter-fail {
                                type yang:counter32;
                                description
                                    "Indicates the number of times a filter, for the specified trigger entry,
                                     does not match an logger event.";
                            }

                            leaf error-admin-state {
                                type yang:counter32;
                                description
                                    "Indicates the number of times the logger event will be ignored due to
                                     admin state of EHS trigger entry is out-of-service.";
                            }

                            leaf error-filter {
                                type yang:counter32;
                                description
                                    "Indicates the number of times the logger event will be ignored due to filter
                                     is not operational or is not configured in EHS trigger entry.";
                            }

                            leaf error-handler {
                                type yang:counter32;
                                description
                                    "Indicates the number of times the logger event will be ignored due to handler
                                     is not operational or is not configured in EHS trigger entry.";
                            }

                            leaf trigger-count {
                                type yang:counter32;
                                description
                                    "Indicates the number of times script execution is triggered after filter match
                                     for the specified trigger entry.";
                            }

                            leaf debounce-count {
                                type yang:counter32;
                                description
                                    "Indicates the number of times script is not executed due to debounce rule
                                     for the specified trigger entry.";
                            }

                        } // container statistics

                    } // list entry

                } // list msdp

                list nat {
                    key "event";
                    description "Enter the nat list instance";

                    leaf event {
                        type types-log:nat-events;
                        description "Log event as a trigger for one or more EHS handlers";
                    }

                    leaf oper-state {
                        type types-sros:oper-state;
                        description "Indicates the operational state of the EHS Event Trigger.";
                    }

                    container statistics {
                        description "Enter the statistics context";

                        leaf success {
                            type yang:counter32;
                            description
                                "Indicates the number of not ignored logger event occurrences
                                 associated with EHS trigger.";
                        }

                        leaf error-no-entry {
                            type yang:counter32;
                            description
                                "Indicates the number of ignored logger event occurrences associated
                                 with EHS trigger.

                                 Event is ignored due to no trigger entry configured for this trigger.";
                        }

                        leaf error-admin-state {
                            type yang:counter32;
                            description
                                "Indicates the number of ignored logger event occurrences associated
                                 with EHS trigger.

                                 Event is ignored due to trigger may be out-of-service.";
                        }

                        leaf total {
                            type yang:counter32;
                            description "Sum of success + error-no-entry + error-admin-state.";
                        }

                    } // container statistics

                    container summary-entry-statistics {
                        description "Enter the summary-entry-statistics context";

                        leaf filter-match {
                            type yang:counter32;
                            description "Indicates the number of times a filter matches an logger event.";
                        }

                        leaf filter-fail {
                            type yang:counter32;
                            description "Indicates the number of times a filter does not match an logger event.";
                        }

                        leaf error-admin-state {
                            type yang:counter32;
                            description
                                "Indicates the number of times the logger event will be ignored due to
                                 admin state of EHS trigger entries is out-of-service.";
                        }

                        leaf error-filter {
                            type yang:counter32;
                            description
                                "Indicates the number of times the logger event will be ignored due to filter
                                 is not operational or is not configured in EHS trigger entries.";
                        }

                        leaf error-handler {
                            type yang:counter32;
                            description
                                "Indicates the number of times the logger event will be ignored due to handler
                                 is not operational or is not configured in EHS trigger entries.";
                        }

                        leaf trigger-count {
                            type yang:counter32;
                            description "Indicates the number of times script execution is triggered after filter match.";
                        }

                        leaf debounce-count {
                            type yang:counter32;
                            description "Indicates the number of times script is not executed due to debounce rule.";
                        }

                    } // container summary-entry-statistics

                    list entry {
                        key "id";
                        description "Enter the entry list instance";

                        leaf id {
                            type uint32 {
                                range "1..1500";
                            }
                            description "ID of the EHS event trigger entry";
                        }

                        leaf oper-state {
                            type types-sros:oper-state;
                            description "Indicates the operational state of the EHS Event Trigger Entry.";
                        }

                        container statistics {
                            description "Enter the statistics context";

                            leaf filter-match {
                                type yang:counter32;
                                description
                                    "Indicates the number of times a filter, for the specified trigger entry,
                                     matches an logger event.";
                            }

                            leaf filter-fail {
                                type yang:counter32;
                                description
                                    "Indicates the number of times a filter, for the specified trigger entry,
                                     does not match an logger event.";
                            }

                            leaf error-admin-state {
                                type yang:counter32;
                                description
                                    "Indicates the number of times the logger event will be ignored due to
                                     admin state of EHS trigger entry is out-of-service.";
                            }

                            leaf error-filter {
                                type yang:counter32;
                                description
                                    "Indicates the number of times the logger event will be ignored due to filter
                                     is not operational or is not configured in EHS trigger entry.";
                            }

                            leaf error-handler {
                                type yang:counter32;
                                description
                                    "Indicates the number of times the logger event will be ignored due to handler
                                     is not operational or is not configured in EHS trigger entry.";
                            }

                            leaf trigger-count {
                                type yang:counter32;
                                description
                                    "Indicates the number of times script execution is triggered after filter match
                                     for the specified trigger entry.";
                            }

                            leaf debounce-count {
                                type yang:counter32;
                                description
                                    "Indicates the number of times script is not executed due to debounce rule
                                     for the specified trigger entry.";
                            }

                        } // container statistics

                    } // list entry

                } // list nat

                list ntp {
                    key "event";
                    description "Enter the ntp list instance";

                    leaf event {
                        type types-log:ntp-events;
                        description "Log event as a trigger for one or more EHS handlers";
                    }

                    leaf oper-state {
                        type types-sros:oper-state;
                        description "Indicates the operational state of the EHS Event Trigger.";
                    }

                    container statistics {
                        description "Enter the statistics context";

                        leaf success {
                            type yang:counter32;
                            description
                                "Indicates the number of not ignored logger event occurrences
                                 associated with EHS trigger.";
                        }

                        leaf error-no-entry {
                            type yang:counter32;
                            description
                                "Indicates the number of ignored logger event occurrences associated
                                 with EHS trigger.

                                 Event is ignored due to no trigger entry configured for this trigger.";
                        }

                        leaf error-admin-state {
                            type yang:counter32;
                            description
                                "Indicates the number of ignored logger event occurrences associated
                                 with EHS trigger.

                                 Event is ignored due to trigger may be out-of-service.";
                        }

                        leaf total {
                            type yang:counter32;
                            description "Sum of success + error-no-entry + error-admin-state.";
                        }

                    } // container statistics

                    container summary-entry-statistics {
                        description "Enter the summary-entry-statistics context";

                        leaf filter-match {
                            type yang:counter32;
                            description "Indicates the number of times a filter matches an logger event.";
                        }

                        leaf filter-fail {
                            type yang:counter32;
                            description "Indicates the number of times a filter does not match an logger event.";
                        }

                        leaf error-admin-state {
                            type yang:counter32;
                            description
                                "Indicates the number of times the logger event will be ignored due to
                                 admin state of EHS trigger entries is out-of-service.";
                        }

                        leaf error-filter {
                            type yang:counter32;
                            description
                                "Indicates the number of times the logger event will be ignored due to filter
                                 is not operational or is not configured in EHS trigger entries.";
                        }

                        leaf error-handler {
                            type yang:counter32;
                            description
                                "Indicates the number of times the logger event will be ignored due to handler
                                 is not operational or is not configured in EHS trigger entries.";
                        }

                        leaf trigger-count {
                            type yang:counter32;
                            description "Indicates the number of times script execution is triggered after filter match.";
                        }

                        leaf debounce-count {
                            type yang:counter32;
                            description "Indicates the number of times script is not executed due to debounce rule.";
                        }

                    } // container summary-entry-statistics

                    list entry {
                        key "id";
                        description "Enter the entry list instance";

                        leaf id {
                            type uint32 {
                                range "1..1500";
                            }
                            description "ID of the EHS event trigger entry";
                        }

                        leaf oper-state {
                            type types-sros:oper-state;
                            description "Indicates the operational state of the EHS Event Trigger Entry.";
                        }

                        container statistics {
                            description "Enter the statistics context";

                            leaf filter-match {
                                type yang:counter32;
                                description
                                    "Indicates the number of times a filter, for the specified trigger entry,
                                     matches an logger event.";
                            }

                            leaf filter-fail {
                                type yang:counter32;
                                description
                                    "Indicates the number of times a filter, for the specified trigger entry,
                                     does not match an logger event.";
                            }

                            leaf error-admin-state {
                                type yang:counter32;
                                description
                                    "Indicates the number of times the logger event will be ignored due to
                                     admin state of EHS trigger entry is out-of-service.";
                            }

                            leaf error-filter {
                                type yang:counter32;
                                description
                                    "Indicates the number of times the logger event will be ignored due to filter
                                     is not operational or is not configured in EHS trigger entry.";
                            }

                            leaf error-handler {
                                type yang:counter32;
                                description
                                    "Indicates the number of times the logger event will be ignored due to handler
                                     is not operational or is not configured in EHS trigger entry.";
                            }

                            leaf trigger-count {
                                type yang:counter32;
                                description
                                    "Indicates the number of times script execution is triggered after filter match
                                     for the specified trigger entry.";
                            }

                            leaf debounce-count {
                                type yang:counter32;
                                description
                                    "Indicates the number of times script is not executed due to debounce rule
                                     for the specified trigger entry.";
                            }

                        } // container statistics

                    } // list entry

                } // list ntp

                list oam {
                    key "event";
                    description "Enter the oam list instance";

                    leaf event {
                        type types-log:oam-events;
                        description "Log event as a trigger for one or more EHS handlers";
                    }

                    leaf oper-state {
                        type types-sros:oper-state;
                        description "Indicates the operational state of the EHS Event Trigger.";
                    }

                    container statistics {
                        description "Enter the statistics context";

                        leaf success {
                            type yang:counter32;
                            description
                                "Indicates the number of not ignored logger event occurrences
                                 associated with EHS trigger.";
                        }

                        leaf error-no-entry {
                            type yang:counter32;
                            description
                                "Indicates the number of ignored logger event occurrences associated
                                 with EHS trigger.

                                 Event is ignored due to no trigger entry configured for this trigger.";
                        }

                        leaf error-admin-state {
                            type yang:counter32;
                            description
                                "Indicates the number of ignored logger event occurrences associated
                                 with EHS trigger.

                                 Event is ignored due to trigger may be out-of-service.";
                        }

                        leaf total {
                            type yang:counter32;
                            description "Sum of success + error-no-entry + error-admin-state.";
                        }

                    } // container statistics

                    container summary-entry-statistics {
                        description "Enter the summary-entry-statistics context";

                        leaf filter-match {
                            type yang:counter32;
                            description "Indicates the number of times a filter matches an logger event.";
                        }

                        leaf filter-fail {
                            type yang:counter32;
                            description "Indicates the number of times a filter does not match an logger event.";
                        }

                        leaf error-admin-state {
                            type yang:counter32;
                            description
                                "Indicates the number of times the logger event will be ignored due to
                                 admin state of EHS trigger entries is out-of-service.";
                        }

                        leaf error-filter {
                            type yang:counter32;
                            description
                                "Indicates the number of times the logger event will be ignored due to filter
                                 is not operational or is not configured in EHS trigger entries.";
                        }

                        leaf error-handler {
                            type yang:counter32;
                            description
                                "Indicates the number of times the logger event will be ignored due to handler
                                 is not operational or is not configured in EHS trigger entries.";
                        }

                        leaf trigger-count {
                            type yang:counter32;
                            description "Indicates the number of times script execution is triggered after filter match.";
                        }

                        leaf debounce-count {
                            type yang:counter32;
                            description "Indicates the number of times script is not executed due to debounce rule.";
                        }

                    } // container summary-entry-statistics

                    list entry {
                        key "id";
                        description "Enter the entry list instance";

                        leaf id {
                            type uint32 {
                                range "1..1500";
                            }
                            description "ID of the EHS event trigger entry";
                        }

                        leaf oper-state {
                            type types-sros:oper-state;
                            description "Indicates the operational state of the EHS Event Trigger Entry.";
                        }

                        container statistics {
                            description "Enter the statistics context";

                            leaf filter-match {
                                type yang:counter32;
                                description
                                    "Indicates the number of times a filter, for the specified trigger entry,
                                     matches an logger event.";
                            }

                            leaf filter-fail {
                                type yang:counter32;
                                description
                                    "Indicates the number of times a filter, for the specified trigger entry,
                                     does not match an logger event.";
                            }

                            leaf error-admin-state {
                                type yang:counter32;
                                description
                                    "Indicates the number of times the logger event will be ignored due to
                                     admin state of EHS trigger entry is out-of-service.";
                            }

                            leaf error-filter {
                                type yang:counter32;
                                description
                                    "Indicates the number of times the logger event will be ignored due to filter
                                     is not operational or is not configured in EHS trigger entry.";
                            }

                            leaf error-handler {
                                type yang:counter32;
                                description
                                    "Indicates the number of times the logger event will be ignored due to handler
                                     is not operational or is not configured in EHS trigger entry.";
                            }

                            leaf trigger-count {
                                type yang:counter32;
                                description
                                    "Indicates the number of times script execution is triggered after filter match
                                     for the specified trigger entry.";
                            }

                            leaf debounce-count {
                                type yang:counter32;
                                description
                                    "Indicates the number of times script is not executed due to debounce rule
                                     for the specified trigger entry.";
                            }

                        } // container statistics

                    } // list entry

                } // list oam

                list openflow {
                    key "event";
                    description "Enter the openflow list instance";

                    leaf event {
                        type types-log:openflow-events;
                        description "Log event as a trigger for one or more EHS handlers";
                    }

                    leaf oper-state {
                        type types-sros:oper-state;
                        description "Indicates the operational state of the EHS Event Trigger.";
                    }

                    container statistics {
                        description "Enter the statistics context";

                        leaf success {
                            type yang:counter32;
                            description
                                "Indicates the number of not ignored logger event occurrences
                                 associated with EHS trigger.";
                        }

                        leaf error-no-entry {
                            type yang:counter32;
                            description
                                "Indicates the number of ignored logger event occurrences associated
                                 with EHS trigger.

                                 Event is ignored due to no trigger entry configured for this trigger.";
                        }

                        leaf error-admin-state {
                            type yang:counter32;
                            description
                                "Indicates the number of ignored logger event occurrences associated
                                 with EHS trigger.

                                 Event is ignored due to trigger may be out-of-service.";
                        }

                        leaf total {
                            type yang:counter32;
                            description "Sum of success + error-no-entry + error-admin-state.";
                        }

                    } // container statistics

                    container summary-entry-statistics {
                        description "Enter the summary-entry-statistics context";

                        leaf filter-match {
                            type yang:counter32;
                            description "Indicates the number of times a filter matches an logger event.";
                        }

                        leaf filter-fail {
                            type yang:counter32;
                            description "Indicates the number of times a filter does not match an logger event.";
                        }

                        leaf error-admin-state {
                            type yang:counter32;
                            description
                                "Indicates the number of times the logger event will be ignored due to
                                 admin state of EHS trigger entries is out-of-service.";
                        }

                        leaf error-filter {
                            type yang:counter32;
                            description
                                "Indicates the number of times the logger event will be ignored due to filter
                                 is not operational or is not configured in EHS trigger entries.";
                        }

                        leaf error-handler {
                            type yang:counter32;
                            description
                                "Indicates the number of times the logger event will be ignored due to handler
                                 is not operational or is not configured in EHS trigger entries.";
                        }

                        leaf trigger-count {
                            type yang:counter32;
                            description "Indicates the number of times script execution is triggered after filter match.";
                        }

                        leaf debounce-count {
                            type yang:counter32;
                            description "Indicates the number of times script is not executed due to debounce rule.";
                        }

                    } // container summary-entry-statistics

                    list entry {
                        key "id";
                        description "Enter the entry list instance";

                        leaf id {
                            type uint32 {
                                range "1..1500";
                            }
                            description "ID of the EHS event trigger entry";
                        }

                        leaf oper-state {
                            type types-sros:oper-state;
                            description "Indicates the operational state of the EHS Event Trigger Entry.";
                        }

                        container statistics {
                            description "Enter the statistics context";

                            leaf filter-match {
                                type yang:counter32;
                                description
                                    "Indicates the number of times a filter, for the specified trigger entry,
                                     matches an logger event.";
                            }

                            leaf filter-fail {
                                type yang:counter32;
                                description
                                    "Indicates the number of times a filter, for the specified trigger entry,
                                     does not match an logger event.";
                            }

                            leaf error-admin-state {
                                type yang:counter32;
                                description
                                    "Indicates the number of times the logger event will be ignored due to
                                     admin state of EHS trigger entry is out-of-service.";
                            }

                            leaf error-filter {
                                type yang:counter32;
                                description
                                    "Indicates the number of times the logger event will be ignored due to filter
                                     is not operational or is not configured in EHS trigger entry.";
                            }

                            leaf error-handler {
                                type yang:counter32;
                                description
                                    "Indicates the number of times the logger event will be ignored due to handler
                                     is not operational or is not configured in EHS trigger entry.";
                            }

                            leaf trigger-count {
                                type yang:counter32;
                                description
                                    "Indicates the number of times script execution is triggered after filter match
                                     for the specified trigger entry.";
                            }

                            leaf debounce-count {
                                type yang:counter32;
                                description
                                    "Indicates the number of times script is not executed due to debounce rule
                                     for the specified trigger entry.";
                            }

                        } // container statistics

                    } // list entry

                } // list openflow

                list ospf {
                    key "event";
                    description "Enter the ospf list instance";

                    leaf event {
                        type types-log:ospf-events;
                        description "Log event as a trigger for one or more EHS handlers";
                    }

                    leaf oper-state {
                        type types-sros:oper-state;
                        description "Indicates the operational state of the EHS Event Trigger.";
                    }

                    container statistics {
                        description "Enter the statistics context";

                        leaf success {
                            type yang:counter32;
                            description
                                "Indicates the number of not ignored logger event occurrences
                                 associated with EHS trigger.";
                        }

                        leaf error-no-entry {
                            type yang:counter32;
                            description
                                "Indicates the number of ignored logger event occurrences associated
                                 with EHS trigger.

                                 Event is ignored due to no trigger entry configured for this trigger.";
                        }

                        leaf error-admin-state {
                            type yang:counter32;
                            description
                                "Indicates the number of ignored logger event occurrences associated
                                 with EHS trigger.

                                 Event is ignored due to trigger may be out-of-service.";
                        }

                        leaf total {
                            type yang:counter32;
                            description "Sum of success + error-no-entry + error-admin-state.";
                        }

                    } // container statistics

                    container summary-entry-statistics {
                        description "Enter the summary-entry-statistics context";

                        leaf filter-match {
                            type yang:counter32;
                            description "Indicates the number of times a filter matches an logger event.";
                        }

                        leaf filter-fail {
                            type yang:counter32;
                            description "Indicates the number of times a filter does not match an logger event.";
                        }

                        leaf error-admin-state {
                            type yang:counter32;
                            description
                                "Indicates the number of times the logger event will be ignored due to
                                 admin state of EHS trigger entries is out-of-service.";
                        }

                        leaf error-filter {
                            type yang:counter32;
                            description
                                "Indicates the number of times the logger event will be ignored due to filter
                                 is not operational or is not configured in EHS trigger entries.";
                        }

                        leaf error-handler {
                            type yang:counter32;
                            description
                                "Indicates the number of times the logger event will be ignored due to handler
                                 is not operational or is not configured in EHS trigger entries.";
                        }

                        leaf trigger-count {
                            type yang:counter32;
                            description "Indicates the number of times script execution is triggered after filter match.";
                        }

                        leaf debounce-count {
                            type yang:counter32;
                            description "Indicates the number of times script is not executed due to debounce rule.";
                        }

                    } // container summary-entry-statistics

                    list entry {
                        key "id";
                        description "Enter the entry list instance";

                        leaf id {
                            type uint32 {
                                range "1..1500";
                            }
                            description "ID of the EHS event trigger entry";
                        }

                        leaf oper-state {
                            type types-sros:oper-state;
                            description "Indicates the operational state of the EHS Event Trigger Entry.";
                        }

                        container statistics {
                            description "Enter the statistics context";

                            leaf filter-match {
                                type yang:counter32;
                                description
                                    "Indicates the number of times a filter, for the specified trigger entry,
                                     matches an logger event.";
                            }

                            leaf filter-fail {
                                type yang:counter32;
                                description
                                    "Indicates the number of times a filter, for the specified trigger entry,
                                     does not match an logger event.";
                            }

                            leaf error-admin-state {
                                type yang:counter32;
                                description
                                    "Indicates the number of times the logger event will be ignored due to
                                     admin state of EHS trigger entry is out-of-service.";
                            }

                            leaf error-filter {
                                type yang:counter32;
                                description
                                    "Indicates the number of times the logger event will be ignored due to filter
                                     is not operational or is not configured in EHS trigger entry.";
                            }

                            leaf error-handler {
                                type yang:counter32;
                                description
                                    "Indicates the number of times the logger event will be ignored due to handler
                                     is not operational or is not configured in EHS trigger entry.";
                            }

                            leaf trigger-count {
                                type yang:counter32;
                                description
                                    "Indicates the number of times script execution is triggered after filter match
                                     for the specified trigger entry.";
                            }

                            leaf debounce-count {
                                type yang:counter32;
                                description
                                    "Indicates the number of times script is not executed due to debounce rule
                                     for the specified trigger entry.";
                            }

                        } // container statistics

                    } // list entry

                } // list ospf

                list pcap {
                    key "event";
                    description "Enter the pcap list instance";

                    leaf event {
                        type types-log:pcap-events;
                        description "Log event as a trigger for one or more EHS handlers";
                    }

                    leaf oper-state {
                        type types-sros:oper-state;
                        description "Indicates the operational state of the EHS Event Trigger.";
                    }

                    container statistics {
                        description "Enter the statistics context";

                        leaf success {
                            type yang:counter32;
                            description
                                "Indicates the number of not ignored logger event occurrences
                                 associated with EHS trigger.";
                        }

                        leaf error-no-entry {
                            type yang:counter32;
                            description
                                "Indicates the number of ignored logger event occurrences associated
                                 with EHS trigger.

                                 Event is ignored due to no trigger entry configured for this trigger.";
                        }

                        leaf error-admin-state {
                            type yang:counter32;
                            description
                                "Indicates the number of ignored logger event occurrences associated
                                 with EHS trigger.

                                 Event is ignored due to trigger may be out-of-service.";
                        }

                        leaf total {
                            type yang:counter32;
                            description "Sum of success + error-no-entry + error-admin-state.";
                        }

                    } // container statistics

                    container summary-entry-statistics {
                        description "Enter the summary-entry-statistics context";

                        leaf filter-match {
                            type yang:counter32;
                            description "Indicates the number of times a filter matches an logger event.";
                        }

                        leaf filter-fail {
                            type yang:counter32;
                            description "Indicates the number of times a filter does not match an logger event.";
                        }

                        leaf error-admin-state {
                            type yang:counter32;
                            description
                                "Indicates the number of times the logger event will be ignored due to
                                 admin state of EHS trigger entries is out-of-service.";
                        }

                        leaf error-filter {
                            type yang:counter32;
                            description
                                "Indicates the number of times the logger event will be ignored due to filter
                                 is not operational or is not configured in EHS trigger entries.";
                        }

                        leaf error-handler {
                            type yang:counter32;
                            description
                                "Indicates the number of times the logger event will be ignored due to handler
                                 is not operational or is not configured in EHS trigger entries.";
                        }

                        leaf trigger-count {
                            type yang:counter32;
                            description "Indicates the number of times script execution is triggered after filter match.";
                        }

                        leaf debounce-count {
                            type yang:counter32;
                            description "Indicates the number of times script is not executed due to debounce rule.";
                        }

                    } // container summary-entry-statistics

                    list entry {
                        key "id";
                        description "Enter the entry list instance";

                        leaf id {
                            type uint32 {
                                range "1..1500";
                            }
                            description "ID of the EHS event trigger entry";
                        }

                        leaf oper-state {
                            type types-sros:oper-state;
                            description "Indicates the operational state of the EHS Event Trigger Entry.";
                        }

                        container statistics {
                            description "Enter the statistics context";

                            leaf filter-match {
                                type yang:counter32;
                                description
                                    "Indicates the number of times a filter, for the specified trigger entry,
                                     matches an logger event.";
                            }

                            leaf filter-fail {
                                type yang:counter32;
                                description
                                    "Indicates the number of times a filter, for the specified trigger entry,
                                     does not match an logger event.";
                            }

                            leaf error-admin-state {
                                type yang:counter32;
                                description
                                    "Indicates the number of times the logger event will be ignored due to
                                     admin state of EHS trigger entry is out-of-service.";
                            }

                            leaf error-filter {
                                type yang:counter32;
                                description
                                    "Indicates the number of times the logger event will be ignored due to filter
                                     is not operational or is not configured in EHS trigger entry.";
                            }

                            leaf error-handler {
                                type yang:counter32;
                                description
                                    "Indicates the number of times the logger event will be ignored due to handler
                                     is not operational or is not configured in EHS trigger entry.";
                            }

                            leaf trigger-count {
                                type yang:counter32;
                                description
                                    "Indicates the number of times script execution is triggered after filter match
                                     for the specified trigger entry.";
                            }

                            leaf debounce-count {
                                type yang:counter32;
                                description
                                    "Indicates the number of times script is not executed due to debounce rule
                                     for the specified trigger entry.";
                            }

                        } // container statistics

                    } // list entry

                } // list pcap

                list pcep {
                    key "event";
                    description "Enter the pcep list instance";

                    leaf event {
                        type types-log:pcep-events;
                        description "PCEP module events";
                    }

                    leaf oper-state {
                        type types-sros:oper-state;
                        description "Indicates the operational state of the EHS Event Trigger.";
                    }

                    container statistics {
                        description "Enter the statistics context";

                        leaf success {
                            type yang:counter32;
                            description
                                "Indicates the number of not ignored logger event occurrences
                                 associated with EHS trigger.";
                        }

                        leaf error-no-entry {
                            type yang:counter32;
                            description
                                "Indicates the number of ignored logger event occurrences associated
                                 with EHS trigger.

                                 Event is ignored due to no trigger entry configured for this trigger.";
                        }

                        leaf error-admin-state {
                            type yang:counter32;
                            description
                                "Indicates the number of ignored logger event occurrences associated
                                 with EHS trigger.

                                 Event is ignored due to trigger may be out-of-service.";
                        }

                        leaf total {
                            type yang:counter32;
                            description "Sum of success + error-no-entry + error-admin-state.";
                        }

                    } // container statistics

                    container summary-entry-statistics {
                        description "Enter the summary-entry-statistics context";

                        leaf filter-match {
                            type yang:counter32;
                            description "Indicates the number of times a filter matches an logger event.";
                        }

                        leaf filter-fail {
                            type yang:counter32;
                            description "Indicates the number of times a filter does not match an logger event.";
                        }

                        leaf error-admin-state {
                            type yang:counter32;
                            description
                                "Indicates the number of times the logger event will be ignored due to
                                 admin state of EHS trigger entries is out-of-service.";
                        }

                        leaf error-filter {
                            type yang:counter32;
                            description
                                "Indicates the number of times the logger event will be ignored due to filter
                                 is not operational or is not configured in EHS trigger entries.";
                        }

                        leaf error-handler {
                            type yang:counter32;
                            description
                                "Indicates the number of times the logger event will be ignored due to handler
                                 is not operational or is not configured in EHS trigger entries.";
                        }

                        leaf trigger-count {
                            type yang:counter32;
                            description "Indicates the number of times script execution is triggered after filter match.";
                        }

                        leaf debounce-count {
                            type yang:counter32;
                            description "Indicates the number of times script is not executed due to debounce rule.";
                        }

                    } // container summary-entry-statistics

                    list entry {
                        key "id";
                        description "Enter the entry list instance";

                        leaf id {
                            type uint32 {
                                range "1..1500";
                            }
                            description "ID of the EHS event trigger entry";
                        }

                        leaf oper-state {
                            type types-sros:oper-state;
                            description "Indicates the operational state of the EHS Event Trigger Entry.";
                        }

                        container statistics {
                            description "Enter the statistics context";

                            leaf filter-match {
                                type yang:counter32;
                                description
                                    "Indicates the number of times a filter, for the specified trigger entry,
                                     matches an logger event.";
                            }

                            leaf filter-fail {
                                type yang:counter32;
                                description
                                    "Indicates the number of times a filter, for the specified trigger entry,
                                     does not match an logger event.";
                            }

                            leaf error-admin-state {
                                type yang:counter32;
                                description
                                    "Indicates the number of times the logger event will be ignored due to
                                     admin state of EHS trigger entry is out-of-service.";
                            }

                            leaf error-filter {
                                type yang:counter32;
                                description
                                    "Indicates the number of times the logger event will be ignored due to filter
                                     is not operational or is not configured in EHS trigger entry.";
                            }

                            leaf error-handler {
                                type yang:counter32;
                                description
                                    "Indicates the number of times the logger event will be ignored due to handler
                                     is not operational or is not configured in EHS trigger entry.";
                            }

                            leaf trigger-count {
                                type yang:counter32;
                                description
                                    "Indicates the number of times script execution is triggered after filter match
                                     for the specified trigger entry.";
                            }

                            leaf debounce-count {
                                type yang:counter32;
                                description
                                    "Indicates the number of times script is not executed due to debounce rule
                                     for the specified trigger entry.";
                            }

                        } // container statistics

                    } // list entry

                } // list pcep

                list pim {
                    key "event";
                    description "Enter the pim list instance";

                    leaf event {
                        type types-log:pim-events;
                        description "Log event as a trigger for one or more EHS handlers";
                    }

                    leaf oper-state {
                        type types-sros:oper-state;
                        description "Indicates the operational state of the EHS Event Trigger.";
                    }

                    container statistics {
                        description "Enter the statistics context";

                        leaf success {
                            type yang:counter32;
                            description
                                "Indicates the number of not ignored logger event occurrences
                                 associated with EHS trigger.";
                        }

                        leaf error-no-entry {
                            type yang:counter32;
                            description
                                "Indicates the number of ignored logger event occurrences associated
                                 with EHS trigger.

                                 Event is ignored due to no trigger entry configured for this trigger.";
                        }

                        leaf error-admin-state {
                            type yang:counter32;
                            description
                                "Indicates the number of ignored logger event occurrences associated
                                 with EHS trigger.

                                 Event is ignored due to trigger may be out-of-service.";
                        }

                        leaf total {
                            type yang:counter32;
                            description "Sum of success + error-no-entry + error-admin-state.";
                        }

                    } // container statistics

                    container summary-entry-statistics {
                        description "Enter the summary-entry-statistics context";

                        leaf filter-match {
                            type yang:counter32;
                            description "Indicates the number of times a filter matches an logger event.";
                        }

                        leaf filter-fail {
                            type yang:counter32;
                            description "Indicates the number of times a filter does not match an logger event.";
                        }

                        leaf error-admin-state {
                            type yang:counter32;
                            description
                                "Indicates the number of times the logger event will be ignored due to
                                 admin state of EHS trigger entries is out-of-service.";
                        }

                        leaf error-filter {
                            type yang:counter32;
                            description
                                "Indicates the number of times the logger event will be ignored due to filter
                                 is not operational or is not configured in EHS trigger entries.";
                        }

                        leaf error-handler {
                            type yang:counter32;
                            description
                                "Indicates the number of times the logger event will be ignored due to handler
                                 is not operational or is not configured in EHS trigger entries.";
                        }

                        leaf trigger-count {
                            type yang:counter32;
                            description "Indicates the number of times script execution is triggered after filter match.";
                        }

                        leaf debounce-count {
                            type yang:counter32;
                            description "Indicates the number of times script is not executed due to debounce rule.";
                        }

                    } // container summary-entry-statistics

                    list entry {
                        key "id";
                        description "Enter the entry list instance";

                        leaf id {
                            type uint32 {
                                range "1..1500";
                            }
                            description "ID of the EHS event trigger entry";
                        }

                        leaf oper-state {
                            type types-sros:oper-state;
                            description "Indicates the operational state of the EHS Event Trigger Entry.";
                        }

                        container statistics {
                            description "Enter the statistics context";

                            leaf filter-match {
                                type yang:counter32;
                                description
                                    "Indicates the number of times a filter, for the specified trigger entry,
                                     matches an logger event.";
                            }

                            leaf filter-fail {
                                type yang:counter32;
                                description
                                    "Indicates the number of times a filter, for the specified trigger entry,
                                     does not match an logger event.";
                            }

                            leaf error-admin-state {
                                type yang:counter32;
                                description
                                    "Indicates the number of times the logger event will be ignored due to
                                     admin state of EHS trigger entry is out-of-service.";
                            }

                            leaf error-filter {
                                type yang:counter32;
                                description
                                    "Indicates the number of times the logger event will be ignored due to filter
                                     is not operational or is not configured in EHS trigger entry.";
                            }

                            leaf error-handler {
                                type yang:counter32;
                                description
                                    "Indicates the number of times the logger event will be ignored due to handler
                                     is not operational or is not configured in EHS trigger entry.";
                            }

                            leaf trigger-count {
                                type yang:counter32;
                                description
                                    "Indicates the number of times script execution is triggered after filter match
                                     for the specified trigger entry.";
                            }

                            leaf debounce-count {
                                type yang:counter32;
                                description
                                    "Indicates the number of times script is not executed due to debounce rule
                                     for the specified trigger entry.";
                            }

                        } // container statistics

                    } // list entry

                } // list pim

                list pim-snooping {
                    key "event";
                    description "Enter the pim-snooping list instance";

                    leaf event {
                        type types-log:pim-snooping-events;
                        description "Log event as a trigger for one or more EHS handlers";
                    }

                    leaf oper-state {
                        type types-sros:oper-state;
                        description "Indicates the operational state of the EHS Event Trigger.";
                    }

                    container statistics {
                        description "Enter the statistics context";

                        leaf success {
                            type yang:counter32;
                            description
                                "Indicates the number of not ignored logger event occurrences
                                 associated with EHS trigger.";
                        }

                        leaf error-no-entry {
                            type yang:counter32;
                            description
                                "Indicates the number of ignored logger event occurrences associated
                                 with EHS trigger.

                                 Event is ignored due to no trigger entry configured for this trigger.";
                        }

                        leaf error-admin-state {
                            type yang:counter32;
                            description
                                "Indicates the number of ignored logger event occurrences associated
                                 with EHS trigger.

                                 Event is ignored due to trigger may be out-of-service.";
                        }

                        leaf total {
                            type yang:counter32;
                            description "Sum of success + error-no-entry + error-admin-state.";
                        }

                    } // container statistics

                    container summary-entry-statistics {
                        description "Enter the summary-entry-statistics context";

                        leaf filter-match {
                            type yang:counter32;
                            description "Indicates the number of times a filter matches an logger event.";
                        }

                        leaf filter-fail {
                            type yang:counter32;
                            description "Indicates the number of times a filter does not match an logger event.";
                        }

                        leaf error-admin-state {
                            type yang:counter32;
                            description
                                "Indicates the number of times the logger event will be ignored due to
                                 admin state of EHS trigger entries is out-of-service.";
                        }

                        leaf error-filter {
                            type yang:counter32;
                            description
                                "Indicates the number of times the logger event will be ignored due to filter
                                 is not operational or is not configured in EHS trigger entries.";
                        }

                        leaf error-handler {
                            type yang:counter32;
                            description
                                "Indicates the number of times the logger event will be ignored due to handler
                                 is not operational or is not configured in EHS trigger entries.";
                        }

                        leaf trigger-count {
                            type yang:counter32;
                            description "Indicates the number of times script execution is triggered after filter match.";
                        }

                        leaf debounce-count {
                            type yang:counter32;
                            description "Indicates the number of times script is not executed due to debounce rule.";
                        }

                    } // container summary-entry-statistics

                    list entry {
                        key "id";
                        description "Enter the entry list instance";

                        leaf id {
                            type uint32 {
                                range "1..1500";
                            }
                            description "ID of the EHS event trigger entry";
                        }

                        leaf oper-state {
                            type types-sros:oper-state;
                            description "Indicates the operational state of the EHS Event Trigger Entry.";
                        }

                        container statistics {
                            description "Enter the statistics context";

                            leaf filter-match {
                                type yang:counter32;
                                description
                                    "Indicates the number of times a filter, for the specified trigger entry,
                                     matches an logger event.";
                            }

                            leaf filter-fail {
                                type yang:counter32;
                                description
                                    "Indicates the number of times a filter, for the specified trigger entry,
                                     does not match an logger event.";
                            }

                            leaf error-admin-state {
                                type yang:counter32;
                                description
                                    "Indicates the number of times the logger event will be ignored due to
                                     admin state of EHS trigger entry is out-of-service.";
                            }

                            leaf error-filter {
                                type yang:counter32;
                                description
                                    "Indicates the number of times the logger event will be ignored due to filter
                                     is not operational or is not configured in EHS trigger entry.";
                            }

                            leaf error-handler {
                                type yang:counter32;
                                description
                                    "Indicates the number of times the logger event will be ignored due to handler
                                     is not operational or is not configured in EHS trigger entry.";
                            }

                            leaf trigger-count {
                                type yang:counter32;
                                description
                                    "Indicates the number of times script execution is triggered after filter match
                                     for the specified trigger entry.";
                            }

                            leaf debounce-count {
                                type yang:counter32;
                                description
                                    "Indicates the number of times script is not executed due to debounce rule
                                     for the specified trigger entry.";
                            }

                        } // container statistics

                    } // list entry

                } // list pim-snooping

                list port {
                    key "event";
                    description "Enter the port list instance";

                    leaf event {
                        type types-log:port-events;
                        description "Log event as a trigger for one or more EHS handlers";
                    }

                    leaf oper-state {
                        type types-sros:oper-state;
                        description "Indicates the operational state of the EHS Event Trigger.";
                    }

                    container statistics {
                        description "Enter the statistics context";

                        leaf success {
                            type yang:counter32;
                            description
                                "Indicates the number of not ignored logger event occurrences
                                 associated with EHS trigger.";
                        }

                        leaf error-no-entry {
                            type yang:counter32;
                            description
                                "Indicates the number of ignored logger event occurrences associated
                                 with EHS trigger.

                                 Event is ignored due to no trigger entry configured for this trigger.";
                        }

                        leaf error-admin-state {
                            type yang:counter32;
                            description
                                "Indicates the number of ignored logger event occurrences associated
                                 with EHS trigger.

                                 Event is ignored due to trigger may be out-of-service.";
                        }

                        leaf total {
                            type yang:counter32;
                            description "Sum of success + error-no-entry + error-admin-state.";
                        }

                    } // container statistics

                    container summary-entry-statistics {
                        description "Enter the summary-entry-statistics context";

                        leaf filter-match {
                            type yang:counter32;
                            description "Indicates the number of times a filter matches an logger event.";
                        }

                        leaf filter-fail {
                            type yang:counter32;
                            description "Indicates the number of times a filter does not match an logger event.";
                        }

                        leaf error-admin-state {
                            type yang:counter32;
                            description
                                "Indicates the number of times the logger event will be ignored due to
                                 admin state of EHS trigger entries is out-of-service.";
                        }

                        leaf error-filter {
                            type yang:counter32;
                            description
                                "Indicates the number of times the logger event will be ignored due to filter
                                 is not operational or is not configured in EHS trigger entries.";
                        }

                        leaf error-handler {
                            type yang:counter32;
                            description
                                "Indicates the number of times the logger event will be ignored due to handler
                                 is not operational or is not configured in EHS trigger entries.";
                        }

                        leaf trigger-count {
                            type yang:counter32;
                            description "Indicates the number of times script execution is triggered after filter match.";
                        }

                        leaf debounce-count {
                            type yang:counter32;
                            description "Indicates the number of times script is not executed due to debounce rule.";
                        }

                    } // container summary-entry-statistics

                    list entry {
                        key "id";
                        description "Enter the entry list instance";

                        leaf id {
                            type uint32 {
                                range "1..1500";
                            }
                            description "ID of the EHS event trigger entry";
                        }

                        leaf oper-state {
                            type types-sros:oper-state;
                            description "Indicates the operational state of the EHS Event Trigger Entry.";
                        }

                        container statistics {
                            description "Enter the statistics context";

                            leaf filter-match {
                                type yang:counter32;
                                description
                                    "Indicates the number of times a filter, for the specified trigger entry,
                                     matches an logger event.";
                            }

                            leaf filter-fail {
                                type yang:counter32;
                                description
                                    "Indicates the number of times a filter, for the specified trigger entry,
                                     does not match an logger event.";
                            }

                            leaf error-admin-state {
                                type yang:counter32;
                                description
                                    "Indicates the number of times the logger event will be ignored due to
                                     admin state of EHS trigger entry is out-of-service.";
                            }

                            leaf error-filter {
                                type yang:counter32;
                                description
                                    "Indicates the number of times the logger event will be ignored due to filter
                                     is not operational or is not configured in EHS trigger entry.";
                            }

                            leaf error-handler {
                                type yang:counter32;
                                description
                                    "Indicates the number of times the logger event will be ignored due to handler
                                     is not operational or is not configured in EHS trigger entry.";
                            }

                            leaf trigger-count {
                                type yang:counter32;
                                description
                                    "Indicates the number of times script execution is triggered after filter match
                                     for the specified trigger entry.";
                            }

                            leaf debounce-count {
                                type yang:counter32;
                                description
                                    "Indicates the number of times script is not executed due to debounce rule
                                     for the specified trigger entry.";
                            }

                        } // container statistics

                    } // list entry

                } // list port

                list pppoe {
                    key "event";
                    description "Enter the pppoe list instance";

                    leaf event {
                        type types-log:pppoe-events;
                        description "Log event as a trigger for one or more EHS handlers";
                    }

                    leaf oper-state {
                        type types-sros:oper-state;
                        description "Indicates the operational state of the EHS Event Trigger.";
                    }

                    container statistics {
                        description "Enter the statistics context";

                        leaf success {
                            type yang:counter32;
                            description
                                "Indicates the number of not ignored logger event occurrences
                                 associated with EHS trigger.";
                        }

                        leaf error-no-entry {
                            type yang:counter32;
                            description
                                "Indicates the number of ignored logger event occurrences associated
                                 with EHS trigger.

                                 Event is ignored due to no trigger entry configured for this trigger.";
                        }

                        leaf error-admin-state {
                            type yang:counter32;
                            description
                                "Indicates the number of ignored logger event occurrences associated
                                 with EHS trigger.

                                 Event is ignored due to trigger may be out-of-service.";
                        }

                        leaf total {
                            type yang:counter32;
                            description "Sum of success + error-no-entry + error-admin-state.";
                        }

                    } // container statistics

                    container summary-entry-statistics {
                        description "Enter the summary-entry-statistics context";

                        leaf filter-match {
                            type yang:counter32;
                            description "Indicates the number of times a filter matches an logger event.";
                        }

                        leaf filter-fail {
                            type yang:counter32;
                            description "Indicates the number of times a filter does not match an logger event.";
                        }

                        leaf error-admin-state {
                            type yang:counter32;
                            description
                                "Indicates the number of times the logger event will be ignored due to
                                 admin state of EHS trigger entries is out-of-service.";
                        }

                        leaf error-filter {
                            type yang:counter32;
                            description
                                "Indicates the number of times the logger event will be ignored due to filter
                                 is not operational or is not configured in EHS trigger entries.";
                        }

                        leaf error-handler {
                            type yang:counter32;
                            description
                                "Indicates the number of times the logger event will be ignored due to handler
                                 is not operational or is not configured in EHS trigger entries.";
                        }

                        leaf trigger-count {
                            type yang:counter32;
                            description "Indicates the number of times script execution is triggered after filter match.";
                        }

                        leaf debounce-count {
                            type yang:counter32;
                            description "Indicates the number of times script is not executed due to debounce rule.";
                        }

                    } // container summary-entry-statistics

                    list entry {
                        key "id";
                        description "Enter the entry list instance";

                        leaf id {
                            type uint32 {
                                range "1..1500";
                            }
                            description "ID of the EHS event trigger entry";
                        }

                        leaf oper-state {
                            type types-sros:oper-state;
                            description "Indicates the operational state of the EHS Event Trigger Entry.";
                        }

                        container statistics {
                            description "Enter the statistics context";

                            leaf filter-match {
                                type yang:counter32;
                                description
                                    "Indicates the number of times a filter, for the specified trigger entry,
                                     matches an logger event.";
                            }

                            leaf filter-fail {
                                type yang:counter32;
                                description
                                    "Indicates the number of times a filter, for the specified trigger entry,
                                     does not match an logger event.";
                            }

                            leaf error-admin-state {
                                type yang:counter32;
                                description
                                    "Indicates the number of times the logger event will be ignored due to
                                     admin state of EHS trigger entry is out-of-service.";
                            }

                            leaf error-filter {
                                type yang:counter32;
                                description
                                    "Indicates the number of times the logger event will be ignored due to filter
                                     is not operational or is not configured in EHS trigger entry.";
                            }

                            leaf error-handler {
                                type yang:counter32;
                                description
                                    "Indicates the number of times the logger event will be ignored due to handler
                                     is not operational or is not configured in EHS trigger entry.";
                            }

                            leaf trigger-count {
                                type yang:counter32;
                                description
                                    "Indicates the number of times script execution is triggered after filter match
                                     for the specified trigger entry.";
                            }

                            leaf debounce-count {
                                type yang:counter32;
                                description
                                    "Indicates the number of times script is not executed due to debounce rule
                                     for the specified trigger entry.";
                            }

                        } // container statistics

                    } // list entry

                } // list pppoe

                list pppoe-clnt {
                    key "event";
                    description "Enter the pppoe-clnt list instance";

                    leaf event {
                        type types-log:pppoe-clnt-events;
                        description "Log event as a trigger for one or more EHS handlers";
                    }

                    leaf oper-state {
                        type types-sros:oper-state;
                        description "Indicates the operational state of the EHS Event Trigger.";
                    }

                    container statistics {
                        description "Enter the statistics context";

                        leaf success {
                            type yang:counter32;
                            description
                                "Indicates the number of not ignored logger event occurrences
                                 associated with EHS trigger.";
                        }

                        leaf error-no-entry {
                            type yang:counter32;
                            description
                                "Indicates the number of ignored logger event occurrences associated
                                 with EHS trigger.

                                 Event is ignored due to no trigger entry configured for this trigger.";
                        }

                        leaf error-admin-state {
                            type yang:counter32;
                            description
                                "Indicates the number of ignored logger event occurrences associated
                                 with EHS trigger.

                                 Event is ignored due to trigger may be out-of-service.";
                        }

                        leaf total {
                            type yang:counter32;
                            description "Sum of success + error-no-entry + error-admin-state.";
                        }

                    } // container statistics

                    container summary-entry-statistics {
                        description "Enter the summary-entry-statistics context";

                        leaf filter-match {
                            type yang:counter32;
                            description "Indicates the number of times a filter matches an logger event.";
                        }

                        leaf filter-fail {
                            type yang:counter32;
                            description "Indicates the number of times a filter does not match an logger event.";
                        }

                        leaf error-admin-state {
                            type yang:counter32;
                            description
                                "Indicates the number of times the logger event will be ignored due to
                                 admin state of EHS trigger entries is out-of-service.";
                        }

                        leaf error-filter {
                            type yang:counter32;
                            description
                                "Indicates the number of times the logger event will be ignored due to filter
                                 is not operational or is not configured in EHS trigger entries.";
                        }

                        leaf error-handler {
                            type yang:counter32;
                            description
                                "Indicates the number of times the logger event will be ignored due to handler
                                 is not operational or is not configured in EHS trigger entries.";
                        }

                        leaf trigger-count {
                            type yang:counter32;
                            description "Indicates the number of times script execution is triggered after filter match.";
                        }

                        leaf debounce-count {
                            type yang:counter32;
                            description "Indicates the number of times script is not executed due to debounce rule.";
                        }

                    } // container summary-entry-statistics

                    list entry {
                        key "id";
                        description "Enter the entry list instance";

                        leaf id {
                            type uint32 {
                                range "1..1500";
                            }
                            description "ID of the EHS event trigger entry";
                        }

                        leaf oper-state {
                            type types-sros:oper-state;
                            description "Indicates the operational state of the EHS Event Trigger Entry.";
                        }

                        container statistics {
                            description "Enter the statistics context";

                            leaf filter-match {
                                type yang:counter32;
                                description
                                    "Indicates the number of times a filter, for the specified trigger entry,
                                     matches an logger event.";
                            }

                            leaf filter-fail {
                                type yang:counter32;
                                description
                                    "Indicates the number of times a filter, for the specified trigger entry,
                                     does not match an logger event.";
                            }

                            leaf error-admin-state {
                                type yang:counter32;
                                description
                                    "Indicates the number of times the logger event will be ignored due to
                                     admin state of EHS trigger entry is out-of-service.";
                            }

                            leaf error-filter {
                                type yang:counter32;
                                description
                                    "Indicates the number of times the logger event will be ignored due to filter
                                     is not operational or is not configured in EHS trigger entry.";
                            }

                            leaf error-handler {
                                type yang:counter32;
                                description
                                    "Indicates the number of times the logger event will be ignored due to handler
                                     is not operational or is not configured in EHS trigger entry.";
                            }

                            leaf trigger-count {
                                type yang:counter32;
                                description
                                    "Indicates the number of times script execution is triggered after filter match
                                     for the specified trigger entry.";
                            }

                            leaf debounce-count {
                                type yang:counter32;
                                description
                                    "Indicates the number of times script is not executed due to debounce rule
                                     for the specified trigger entry.";
                            }

                        } // container statistics

                    } // list entry

                } // list pppoe-clnt

                list ptp {
                    key "event";
                    description "Enter the ptp list instance";

                    leaf event {
                        type types-log:ptp-events;
                        description "Log event as a trigger for one or more EHS handlers";
                    }

                    leaf oper-state {
                        type types-sros:oper-state;
                        description "Indicates the operational state of the EHS Event Trigger.";
                    }

                    container statistics {
                        description "Enter the statistics context";

                        leaf success {
                            type yang:counter32;
                            description
                                "Indicates the number of not ignored logger event occurrences
                                 associated with EHS trigger.";
                        }

                        leaf error-no-entry {
                            type yang:counter32;
                            description
                                "Indicates the number of ignored logger event occurrences associated
                                 with EHS trigger.

                                 Event is ignored due to no trigger entry configured for this trigger.";
                        }

                        leaf error-admin-state {
                            type yang:counter32;
                            description
                                "Indicates the number of ignored logger event occurrences associated
                                 with EHS trigger.

                                 Event is ignored due to trigger may be out-of-service.";
                        }

                        leaf total {
                            type yang:counter32;
                            description "Sum of success + error-no-entry + error-admin-state.";
                        }

                    } // container statistics

                    container summary-entry-statistics {
                        description "Enter the summary-entry-statistics context";

                        leaf filter-match {
                            type yang:counter32;
                            description "Indicates the number of times a filter matches an logger event.";
                        }

                        leaf filter-fail {
                            type yang:counter32;
                            description "Indicates the number of times a filter does not match an logger event.";
                        }

                        leaf error-admin-state {
                            type yang:counter32;
                            description
                                "Indicates the number of times the logger event will be ignored due to
                                 admin state of EHS trigger entries is out-of-service.";
                        }

                        leaf error-filter {
                            type yang:counter32;
                            description
                                "Indicates the number of times the logger event will be ignored due to filter
                                 is not operational or is not configured in EHS trigger entries.";
                        }

                        leaf error-handler {
                            type yang:counter32;
                            description
                                "Indicates the number of times the logger event will be ignored due to handler
                                 is not operational or is not configured in EHS trigger entries.";
                        }

                        leaf trigger-count {
                            type yang:counter32;
                            description "Indicates the number of times script execution is triggered after filter match.";
                        }

                        leaf debounce-count {
                            type yang:counter32;
                            description "Indicates the number of times script is not executed due to debounce rule.";
                        }

                    } // container summary-entry-statistics

                    list entry {
                        key "id";
                        description "Enter the entry list instance";

                        leaf id {
                            type uint32 {
                                range "1..1500";
                            }
                            description "ID of the EHS event trigger entry";
                        }

                        leaf oper-state {
                            type types-sros:oper-state;
                            description "Indicates the operational state of the EHS Event Trigger Entry.";
                        }

                        container statistics {
                            description "Enter the statistics context";

                            leaf filter-match {
                                type yang:counter32;
                                description
                                    "Indicates the number of times a filter, for the specified trigger entry,
                                     matches an logger event.";
                            }

                            leaf filter-fail {
                                type yang:counter32;
                                description
                                    "Indicates the number of times a filter, for the specified trigger entry,
                                     does not match an logger event.";
                            }

                            leaf error-admin-state {
                                type yang:counter32;
                                description
                                    "Indicates the number of times the logger event will be ignored due to
                                     admin state of EHS trigger entry is out-of-service.";
                            }

                            leaf error-filter {
                                type yang:counter32;
                                description
                                    "Indicates the number of times the logger event will be ignored due to filter
                                     is not operational or is not configured in EHS trigger entry.";
                            }

                            leaf error-handler {
                                type yang:counter32;
                                description
                                    "Indicates the number of times the logger event will be ignored due to handler
                                     is not operational or is not configured in EHS trigger entry.";
                            }

                            leaf trigger-count {
                                type yang:counter32;
                                description
                                    "Indicates the number of times script execution is triggered after filter match
                                     for the specified trigger entry.";
                            }

                            leaf debounce-count {
                                type yang:counter32;
                                description
                                    "Indicates the number of times script is not executed due to debounce rule
                                     for the specified trigger entry.";
                            }

                        } // container statistics

                    } // list entry

                } // list ptp

                list python {
                    key "event";
                    description "Enter the python list instance";

                    leaf event {
                        type types-log:python-events;
                        description "Python module events";
                    }

                    leaf oper-state {
                        type types-sros:oper-state;
                        description "Indicates the operational state of the EHS Event Trigger.";
                    }

                    container statistics {
                        description "Enter the statistics context";

                        leaf success {
                            type yang:counter32;
                            description
                                "Indicates the number of not ignored logger event occurrences
                                 associated with EHS trigger.";
                        }

                        leaf error-no-entry {
                            type yang:counter32;
                            description
                                "Indicates the number of ignored logger event occurrences associated
                                 with EHS trigger.

                                 Event is ignored due to no trigger entry configured for this trigger.";
                        }

                        leaf error-admin-state {
                            type yang:counter32;
                            description
                                "Indicates the number of ignored logger event occurrences associated
                                 with EHS trigger.

                                 Event is ignored due to trigger may be out-of-service.";
                        }

                        leaf total {
                            type yang:counter32;
                            description "Sum of success + error-no-entry + error-admin-state.";
                        }

                    } // container statistics

                    container summary-entry-statistics {
                        description "Enter the summary-entry-statistics context";

                        leaf filter-match {
                            type yang:counter32;
                            description "Indicates the number of times a filter matches an logger event.";
                        }

                        leaf filter-fail {
                            type yang:counter32;
                            description "Indicates the number of times a filter does not match an logger event.";
                        }

                        leaf error-admin-state {
                            type yang:counter32;
                            description
                                "Indicates the number of times the logger event will be ignored due to
                                 admin state of EHS trigger entries is out-of-service.";
                        }

                        leaf error-filter {
                            type yang:counter32;
                            description
                                "Indicates the number of times the logger event will be ignored due to filter
                                 is not operational or is not configured in EHS trigger entries.";
                        }

                        leaf error-handler {
                            type yang:counter32;
                            description
                                "Indicates the number of times the logger event will be ignored due to handler
                                 is not operational or is not configured in EHS trigger entries.";
                        }

                        leaf trigger-count {
                            type yang:counter32;
                            description "Indicates the number of times script execution is triggered after filter match.";
                        }

                        leaf debounce-count {
                            type yang:counter32;
                            description "Indicates the number of times script is not executed due to debounce rule.";
                        }

                    } // container summary-entry-statistics

                    list entry {
                        key "id";
                        description "Enter the entry list instance";

                        leaf id {
                            type uint32 {
                                range "1..1500";
                            }
                            description "ID of the EHS event trigger entry";
                        }

                        leaf oper-state {
                            type types-sros:oper-state;
                            description "Indicates the operational state of the EHS Event Trigger Entry.";
                        }

                        container statistics {
                            description "Enter the statistics context";

                            leaf filter-match {
                                type yang:counter32;
                                description
                                    "Indicates the number of times a filter, for the specified trigger entry,
                                     matches an logger event.";
                            }

                            leaf filter-fail {
                                type yang:counter32;
                                description
                                    "Indicates the number of times a filter, for the specified trigger entry,
                                     does not match an logger event.";
                            }

                            leaf error-admin-state {
                                type yang:counter32;
                                description
                                    "Indicates the number of times the logger event will be ignored due to
                                     admin state of EHS trigger entry is out-of-service.";
                            }

                            leaf error-filter {
                                type yang:counter32;
                                description
                                    "Indicates the number of times the logger event will be ignored due to filter
                                     is not operational or is not configured in EHS trigger entry.";
                            }

                            leaf error-handler {
                                type yang:counter32;
                                description
                                    "Indicates the number of times the logger event will be ignored due to handler
                                     is not operational or is not configured in EHS trigger entry.";
                            }

                            leaf trigger-count {
                                type yang:counter32;
                                description
                                    "Indicates the number of times script execution is triggered after filter match
                                     for the specified trigger entry.";
                            }

                            leaf debounce-count {
                                type yang:counter32;
                                description
                                    "Indicates the number of times script is not executed due to debounce rule
                                     for the specified trigger entry.";
                            }

                        } // container statistics

                    } // list entry

                } // list python

                list radius {
                    key "event";
                    description "Enter the radius list instance";

                    leaf event {
                        type types-log:radius-events;
                        description "Log event as a trigger for one or more EHS handlers";
                    }

                    leaf oper-state {
                        type types-sros:oper-state;
                        description "Indicates the operational state of the EHS Event Trigger.";
                    }

                    container statistics {
                        description "Enter the statistics context";

                        leaf success {
                            type yang:counter32;
                            description
                                "Indicates the number of not ignored logger event occurrences
                                 associated with EHS trigger.";
                        }

                        leaf error-no-entry {
                            type yang:counter32;
                            description
                                "Indicates the number of ignored logger event occurrences associated
                                 with EHS trigger.

                                 Event is ignored due to no trigger entry configured for this trigger.";
                        }

                        leaf error-admin-state {
                            type yang:counter32;
                            description
                                "Indicates the number of ignored logger event occurrences associated
                                 with EHS trigger.

                                 Event is ignored due to trigger may be out-of-service.";
                        }

                        leaf total {
                            type yang:counter32;
                            description "Sum of success + error-no-entry + error-admin-state.";
                        }

                    } // container statistics

                    container summary-entry-statistics {
                        description "Enter the summary-entry-statistics context";

                        leaf filter-match {
                            type yang:counter32;
                            description "Indicates the number of times a filter matches an logger event.";
                        }

                        leaf filter-fail {
                            type yang:counter32;
                            description "Indicates the number of times a filter does not match an logger event.";
                        }

                        leaf error-admin-state {
                            type yang:counter32;
                            description
                                "Indicates the number of times the logger event will be ignored due to
                                 admin state of EHS trigger entries is out-of-service.";
                        }

                        leaf error-filter {
                            type yang:counter32;
                            description
                                "Indicates the number of times the logger event will be ignored due to filter
                                 is not operational or is not configured in EHS trigger entries.";
                        }

                        leaf error-handler {
                            type yang:counter32;
                            description
                                "Indicates the number of times the logger event will be ignored due to handler
                                 is not operational or is not configured in EHS trigger entries.";
                        }

                        leaf trigger-count {
                            type yang:counter32;
                            description "Indicates the number of times script execution is triggered after filter match.";
                        }

                        leaf debounce-count {
                            type yang:counter32;
                            description "Indicates the number of times script is not executed due to debounce rule.";
                        }

                    } // container summary-entry-statistics

                    list entry {
                        key "id";
                        description "Enter the entry list instance";

                        leaf id {
                            type uint32 {
                                range "1..1500";
                            }
                            description "ID of the EHS event trigger entry";
                        }

                        leaf oper-state {
                            type types-sros:oper-state;
                            description "Indicates the operational state of the EHS Event Trigger Entry.";
                        }

                        container statistics {
                            description "Enter the statistics context";

                            leaf filter-match {
                                type yang:counter32;
                                description
                                    "Indicates the number of times a filter, for the specified trigger entry,
                                     matches an logger event.";
                            }

                            leaf filter-fail {
                                type yang:counter32;
                                description
                                    "Indicates the number of times a filter, for the specified trigger entry,
                                     does not match an logger event.";
                            }

                            leaf error-admin-state {
                                type yang:counter32;
                                description
                                    "Indicates the number of times the logger event will be ignored due to
                                     admin state of EHS trigger entry is out-of-service.";
                            }

                            leaf error-filter {
                                type yang:counter32;
                                description
                                    "Indicates the number of times the logger event will be ignored due to filter
                                     is not operational or is not configured in EHS trigger entry.";
                            }

                            leaf error-handler {
                                type yang:counter32;
                                description
                                    "Indicates the number of times the logger event will be ignored due to handler
                                     is not operational or is not configured in EHS trigger entry.";
                            }

                            leaf trigger-count {
                                type yang:counter32;
                                description
                                    "Indicates the number of times script execution is triggered after filter match
                                     for the specified trigger entry.";
                            }

                            leaf debounce-count {
                                type yang:counter32;
                                description
                                    "Indicates the number of times script is not executed due to debounce rule
                                     for the specified trigger entry.";
                            }

                        } // container statistics

                    } // list entry

                } // list radius

                list rip {
                    key "event";
                    description "Enter the rip list instance";

                    leaf event {
                        type types-log:rip-events;
                        description "Log event as a trigger for one or more EHS handlers";
                    }

                    leaf oper-state {
                        type types-sros:oper-state;
                        description "Indicates the operational state of the EHS Event Trigger.";
                    }

                    container statistics {
                        description "Enter the statistics context";

                        leaf success {
                            type yang:counter32;
                            description
                                "Indicates the number of not ignored logger event occurrences
                                 associated with EHS trigger.";
                        }

                        leaf error-no-entry {
                            type yang:counter32;
                            description
                                "Indicates the number of ignored logger event occurrences associated
                                 with EHS trigger.

                                 Event is ignored due to no trigger entry configured for this trigger.";
                        }

                        leaf error-admin-state {
                            type yang:counter32;
                            description
                                "Indicates the number of ignored logger event occurrences associated
                                 with EHS trigger.

                                 Event is ignored due to trigger may be out-of-service.";
                        }

                        leaf total {
                            type yang:counter32;
                            description "Sum of success + error-no-entry + error-admin-state.";
                        }

                    } // container statistics

                    container summary-entry-statistics {
                        description "Enter the summary-entry-statistics context";

                        leaf filter-match {
                            type yang:counter32;
                            description "Indicates the number of times a filter matches an logger event.";
                        }

                        leaf filter-fail {
                            type yang:counter32;
                            description "Indicates the number of times a filter does not match an logger event.";
                        }

                        leaf error-admin-state {
                            type yang:counter32;
                            description
                                "Indicates the number of times the logger event will be ignored due to
                                 admin state of EHS trigger entries is out-of-service.";
                        }

                        leaf error-filter {
                            type yang:counter32;
                            description
                                "Indicates the number of times the logger event will be ignored due to filter
                                 is not operational or is not configured in EHS trigger entries.";
                        }

                        leaf error-handler {
                            type yang:counter32;
                            description
                                "Indicates the number of times the logger event will be ignored due to handler
                                 is not operational or is not configured in EHS trigger entries.";
                        }

                        leaf trigger-count {
                            type yang:counter32;
                            description "Indicates the number of times script execution is triggered after filter match.";
                        }

                        leaf debounce-count {
                            type yang:counter32;
                            description "Indicates the number of times script is not executed due to debounce rule.";
                        }

                    } // container summary-entry-statistics

                    list entry {
                        key "id";
                        description "Enter the entry list instance";

                        leaf id {
                            type uint32 {
                                range "1..1500";
                            }
                            description "ID of the EHS event trigger entry";
                        }

                        leaf oper-state {
                            type types-sros:oper-state;
                            description "Indicates the operational state of the EHS Event Trigger Entry.";
                        }

                        container statistics {
                            description "Enter the statistics context";

                            leaf filter-match {
                                type yang:counter32;
                                description
                                    "Indicates the number of times a filter, for the specified trigger entry,
                                     matches an logger event.";
                            }

                            leaf filter-fail {
                                type yang:counter32;
                                description
                                    "Indicates the number of times a filter, for the specified trigger entry,
                                     does not match an logger event.";
                            }

                            leaf error-admin-state {
                                type yang:counter32;
                                description
                                    "Indicates the number of times the logger event will be ignored due to
                                     admin state of EHS trigger entry is out-of-service.";
                            }

                            leaf error-filter {
                                type yang:counter32;
                                description
                                    "Indicates the number of times the logger event will be ignored due to filter
                                     is not operational or is not configured in EHS trigger entry.";
                            }

                            leaf error-handler {
                                type yang:counter32;
                                description
                                    "Indicates the number of times the logger event will be ignored due to handler
                                     is not operational or is not configured in EHS trigger entry.";
                            }

                            leaf trigger-count {
                                type yang:counter32;
                                description
                                    "Indicates the number of times script execution is triggered after filter match
                                     for the specified trigger entry.";
                            }

                            leaf debounce-count {
                                type yang:counter32;
                                description
                                    "Indicates the number of times script is not executed due to debounce rule
                                     for the specified trigger entry.";
                            }

                        } // container statistics

                    } // list entry

                } // list rip

                list ripng {
                    key "event";
                    description "Enter the ripng list instance";

                    leaf event {
                        type types-log:ripng-events;
                        description "Log event as a trigger for one or more EHS handlers";
                    }

                    leaf oper-state {
                        type types-sros:oper-state;
                        description "Indicates the operational state of the EHS Event Trigger.";
                    }

                    container statistics {
                        description "Enter the statistics context";

                        leaf success {
                            type yang:counter32;
                            description
                                "Indicates the number of not ignored logger event occurrences
                                 associated with EHS trigger.";
                        }

                        leaf error-no-entry {
                            type yang:counter32;
                            description
                                "Indicates the number of ignored logger event occurrences associated
                                 with EHS trigger.

                                 Event is ignored due to no trigger entry configured for this trigger.";
                        }

                        leaf error-admin-state {
                            type yang:counter32;
                            description
                                "Indicates the number of ignored logger event occurrences associated
                                 with EHS trigger.

                                 Event is ignored due to trigger may be out-of-service.";
                        }

                        leaf total {
                            type yang:counter32;
                            description "Sum of success + error-no-entry + error-admin-state.";
                        }

                    } // container statistics

                    container summary-entry-statistics {
                        description "Enter the summary-entry-statistics context";

                        leaf filter-match {
                            type yang:counter32;
                            description "Indicates the number of times a filter matches an logger event.";
                        }

                        leaf filter-fail {
                            type yang:counter32;
                            description "Indicates the number of times a filter does not match an logger event.";
                        }

                        leaf error-admin-state {
                            type yang:counter32;
                            description
                                "Indicates the number of times the logger event will be ignored due to
                                 admin state of EHS trigger entries is out-of-service.";
                        }

                        leaf error-filter {
                            type yang:counter32;
                            description
                                "Indicates the number of times the logger event will be ignored due to filter
                                 is not operational or is not configured in EHS trigger entries.";
                        }

                        leaf error-handler {
                            type yang:counter32;
                            description
                                "Indicates the number of times the logger event will be ignored due to handler
                                 is not operational or is not configured in EHS trigger entries.";
                        }

                        leaf trigger-count {
                            type yang:counter32;
                            description "Indicates the number of times script execution is triggered after filter match.";
                        }

                        leaf debounce-count {
                            type yang:counter32;
                            description "Indicates the number of times script is not executed due to debounce rule.";
                        }

                    } // container summary-entry-statistics

                    list entry {
                        key "id";
                        description "Enter the entry list instance";

                        leaf id {
                            type uint32 {
                                range "1..1500";
                            }
                            description "ID of the EHS event trigger entry";
                        }

                        leaf oper-state {
                            type types-sros:oper-state;
                            description "Indicates the operational state of the EHS Event Trigger Entry.";
                        }

                        container statistics {
                            description "Enter the statistics context";

                            leaf filter-match {
                                type yang:counter32;
                                description
                                    "Indicates the number of times a filter, for the specified trigger entry,
                                     matches an logger event.";
                            }

                            leaf filter-fail {
                                type yang:counter32;
                                description
                                    "Indicates the number of times a filter, for the specified trigger entry,
                                     does not match an logger event.";
                            }

                            leaf error-admin-state {
                                type yang:counter32;
                                description
                                    "Indicates the number of times the logger event will be ignored due to
                                     admin state of EHS trigger entry is out-of-service.";
                            }

                            leaf error-filter {
                                type yang:counter32;
                                description
                                    "Indicates the number of times the logger event will be ignored due to filter
                                     is not operational or is not configured in EHS trigger entry.";
                            }

                            leaf error-handler {
                                type yang:counter32;
                                description
                                    "Indicates the number of times the logger event will be ignored due to handler
                                     is not operational or is not configured in EHS trigger entry.";
                            }

                            leaf trigger-count {
                                type yang:counter32;
                                description
                                    "Indicates the number of times script execution is triggered after filter match
                                     for the specified trigger entry.";
                            }

                            leaf debounce-count {
                                type yang:counter32;
                                description
                                    "Indicates the number of times script is not executed due to debounce rule
                                     for the specified trigger entry.";
                            }

                        } // container statistics

                    } // list entry

                } // list ripng

                list route-policy {
                    key "event";
                    description "Enter the route-policy list instance";

                    leaf event {
                        type types-log:route-policy-events;
                        description "Log event as a trigger for one or more EHS handlers";
                    }

                    leaf oper-state {
                        type types-sros:oper-state;
                        description "Indicates the operational state of the EHS Event Trigger.";
                    }

                    container statistics {
                        description "Enter the statistics context";

                        leaf success {
                            type yang:counter32;
                            description
                                "Indicates the number of not ignored logger event occurrences
                                 associated with EHS trigger.";
                        }

                        leaf error-no-entry {
                            type yang:counter32;
                            description
                                "Indicates the number of ignored logger event occurrences associated
                                 with EHS trigger.

                                 Event is ignored due to no trigger entry configured for this trigger.";
                        }

                        leaf error-admin-state {
                            type yang:counter32;
                            description
                                "Indicates the number of ignored logger event occurrences associated
                                 with EHS trigger.

                                 Event is ignored due to trigger may be out-of-service.";
                        }

                        leaf total {
                            type yang:counter32;
                            description "Sum of success + error-no-entry + error-admin-state.";
                        }

                    } // container statistics

                    container summary-entry-statistics {
                        description "Enter the summary-entry-statistics context";

                        leaf filter-match {
                            type yang:counter32;
                            description "Indicates the number of times a filter matches an logger event.";
                        }

                        leaf filter-fail {
                            type yang:counter32;
                            description "Indicates the number of times a filter does not match an logger event.";
                        }

                        leaf error-admin-state {
                            type yang:counter32;
                            description
                                "Indicates the number of times the logger event will be ignored due to
                                 admin state of EHS trigger entries is out-of-service.";
                        }

                        leaf error-filter {
                            type yang:counter32;
                            description
                                "Indicates the number of times the logger event will be ignored due to filter
                                 is not operational or is not configured in EHS trigger entries.";
                        }

                        leaf error-handler {
                            type yang:counter32;
                            description
                                "Indicates the number of times the logger event will be ignored due to handler
                                 is not operational or is not configured in EHS trigger entries.";
                        }

                        leaf trigger-count {
                            type yang:counter32;
                            description "Indicates the number of times script execution is triggered after filter match.";
                        }

                        leaf debounce-count {
                            type yang:counter32;
                            description "Indicates the number of times script is not executed due to debounce rule.";
                        }

                    } // container summary-entry-statistics

                    list entry {
                        key "id";
                        description "Enter the entry list instance";

                        leaf id {
                            type uint32 {
                                range "1..1500";
                            }
                            description "ID of the EHS event trigger entry";
                        }

                        leaf oper-state {
                            type types-sros:oper-state;
                            description "Indicates the operational state of the EHS Event Trigger Entry.";
                        }

                        container statistics {
                            description "Enter the statistics context";

                            leaf filter-match {
                                type yang:counter32;
                                description
                                    "Indicates the number of times a filter, for the specified trigger entry,
                                     matches an logger event.";
                            }

                            leaf filter-fail {
                                type yang:counter32;
                                description
                                    "Indicates the number of times a filter, for the specified trigger entry,
                                     does not match an logger event.";
                            }

                            leaf error-admin-state {
                                type yang:counter32;
                                description
                                    "Indicates the number of times the logger event will be ignored due to
                                     admin state of EHS trigger entry is out-of-service.";
                            }

                            leaf error-filter {
                                type yang:counter32;
                                description
                                    "Indicates the number of times the logger event will be ignored due to filter
                                     is not operational or is not configured in EHS trigger entry.";
                            }

                            leaf error-handler {
                                type yang:counter32;
                                description
                                    "Indicates the number of times the logger event will be ignored due to handler
                                     is not operational or is not configured in EHS trigger entry.";
                            }

                            leaf trigger-count {
                                type yang:counter32;
                                description
                                    "Indicates the number of times script execution is triggered after filter match
                                     for the specified trigger entry.";
                            }

                            leaf debounce-count {
                                type yang:counter32;
                                description
                                    "Indicates the number of times script is not executed due to debounce rule
                                     for the specified trigger entry.";
                            }

                        } // container statistics

                    } // list entry

                } // list route-policy

                list rpki {
                    key "event";
                    description "Enter the rpki list instance";

                    leaf event {
                        type types-log:rpki-events;
                        description "Log event as a trigger for one or more EHS handlers";
                    }

                    leaf oper-state {
                        type types-sros:oper-state;
                        description "Indicates the operational state of the EHS Event Trigger.";
                    }

                    container statistics {
                        description "Enter the statistics context";

                        leaf success {
                            type yang:counter32;
                            description
                                "Indicates the number of not ignored logger event occurrences
                                 associated with EHS trigger.";
                        }

                        leaf error-no-entry {
                            type yang:counter32;
                            description
                                "Indicates the number of ignored logger event occurrences associated
                                 with EHS trigger.

                                 Event is ignored due to no trigger entry configured for this trigger.";
                        }

                        leaf error-admin-state {
                            type yang:counter32;
                            description
                                "Indicates the number of ignored logger event occurrences associated
                                 with EHS trigger.

                                 Event is ignored due to trigger may be out-of-service.";
                        }

                        leaf total {
                            type yang:counter32;
                            description "Sum of success + error-no-entry + error-admin-state.";
                        }

                    } // container statistics

                    container summary-entry-statistics {
                        description "Enter the summary-entry-statistics context";

                        leaf filter-match {
                            type yang:counter32;
                            description "Indicates the number of times a filter matches an logger event.";
                        }

                        leaf filter-fail {
                            type yang:counter32;
                            description "Indicates the number of times a filter does not match an logger event.";
                        }

                        leaf error-admin-state {
                            type yang:counter32;
                            description
                                "Indicates the number of times the logger event will be ignored due to
                                 admin state of EHS trigger entries is out-of-service.";
                        }

                        leaf error-filter {
                            type yang:counter32;
                            description
                                "Indicates the number of times the logger event will be ignored due to filter
                                 is not operational or is not configured in EHS trigger entries.";
                        }

                        leaf error-handler {
                            type yang:counter32;
                            description
                                "Indicates the number of times the logger event will be ignored due to handler
                                 is not operational or is not configured in EHS trigger entries.";
                        }

                        leaf trigger-count {
                            type yang:counter32;
                            description "Indicates the number of times script execution is triggered after filter match.";
                        }

                        leaf debounce-count {
                            type yang:counter32;
                            description "Indicates the number of times script is not executed due to debounce rule.";
                        }

                    } // container summary-entry-statistics

                    list entry {
                        key "id";
                        description "Enter the entry list instance";

                        leaf id {
                            type uint32 {
                                range "1..1500";
                            }
                            description "ID of the EHS event trigger entry";
                        }

                        leaf oper-state {
                            type types-sros:oper-state;
                            description "Indicates the operational state of the EHS Event Trigger Entry.";
                        }

                        container statistics {
                            description "Enter the statistics context";

                            leaf filter-match {
                                type yang:counter32;
                                description
                                    "Indicates the number of times a filter, for the specified trigger entry,
                                     matches an logger event.";
                            }

                            leaf filter-fail {
                                type yang:counter32;
                                description
                                    "Indicates the number of times a filter, for the specified trigger entry,
                                     does not match an logger event.";
                            }

                            leaf error-admin-state {
                                type yang:counter32;
                                description
                                    "Indicates the number of times the logger event will be ignored due to
                                     admin state of EHS trigger entry is out-of-service.";
                            }

                            leaf error-filter {
                                type yang:counter32;
                                description
                                    "Indicates the number of times the logger event will be ignored due to filter
                                     is not operational or is not configured in EHS trigger entry.";
                            }

                            leaf error-handler {
                                type yang:counter32;
                                description
                                    "Indicates the number of times the logger event will be ignored due to handler
                                     is not operational or is not configured in EHS trigger entry.";
                            }

                            leaf trigger-count {
                                type yang:counter32;
                                description
                                    "Indicates the number of times script execution is triggered after filter match
                                     for the specified trigger entry.";
                            }

                            leaf debounce-count {
                                type yang:counter32;
                                description
                                    "Indicates the number of times script is not executed due to debounce rule
                                     for the specified trigger entry.";
                            }

                        } // container statistics

                    } // list entry

                } // list rpki

                list rsvp {
                    key "event";
                    description "Enter the rsvp list instance";

                    leaf event {
                        type types-log:rsvp-events;
                        description "Log event as a trigger for one or more EHS handlers";
                    }

                    leaf oper-state {
                        type types-sros:oper-state;
                        description "Indicates the operational state of the EHS Event Trigger.";
                    }

                    container statistics {
                        description "Enter the statistics context";

                        leaf success {
                            type yang:counter32;
                            description
                                "Indicates the number of not ignored logger event occurrences
                                 associated with EHS trigger.";
                        }

                        leaf error-no-entry {
                            type yang:counter32;
                            description
                                "Indicates the number of ignored logger event occurrences associated
                                 with EHS trigger.

                                 Event is ignored due to no trigger entry configured for this trigger.";
                        }

                        leaf error-admin-state {
                            type yang:counter32;
                            description
                                "Indicates the number of ignored logger event occurrences associated
                                 with EHS trigger.

                                 Event is ignored due to trigger may be out-of-service.";
                        }

                        leaf total {
                            type yang:counter32;
                            description "Sum of success + error-no-entry + error-admin-state.";
                        }

                    } // container statistics

                    container summary-entry-statistics {
                        description "Enter the summary-entry-statistics context";

                        leaf filter-match {
                            type yang:counter32;
                            description "Indicates the number of times a filter matches an logger event.";
                        }

                        leaf filter-fail {
                            type yang:counter32;
                            description "Indicates the number of times a filter does not match an logger event.";
                        }

                        leaf error-admin-state {
                            type yang:counter32;
                            description
                                "Indicates the number of times the logger event will be ignored due to
                                 admin state of EHS trigger entries is out-of-service.";
                        }

                        leaf error-filter {
                            type yang:counter32;
                            description
                                "Indicates the number of times the logger event will be ignored due to filter
                                 is not operational or is not configured in EHS trigger entries.";
                        }

                        leaf error-handler {
                            type yang:counter32;
                            description
                                "Indicates the number of times the logger event will be ignored due to handler
                                 is not operational or is not configured in EHS trigger entries.";
                        }

                        leaf trigger-count {
                            type yang:counter32;
                            description "Indicates the number of times script execution is triggered after filter match.";
                        }

                        leaf debounce-count {
                            type yang:counter32;
                            description "Indicates the number of times script is not executed due to debounce rule.";
                        }

                    } // container summary-entry-statistics

                    list entry {
                        key "id";
                        description "Enter the entry list instance";

                        leaf id {
                            type uint32 {
                                range "1..1500";
                            }
                            description "ID of the EHS event trigger entry";
                        }

                        leaf oper-state {
                            type types-sros:oper-state;
                            description "Indicates the operational state of the EHS Event Trigger Entry.";
                        }

                        container statistics {
                            description "Enter the statistics context";

                            leaf filter-match {
                                type yang:counter32;
                                description
                                    "Indicates the number of times a filter, for the specified trigger entry,
                                     matches an logger event.";
                            }

                            leaf filter-fail {
                                type yang:counter32;
                                description
                                    "Indicates the number of times a filter, for the specified trigger entry,
                                     does not match an logger event.";
                            }

                            leaf error-admin-state {
                                type yang:counter32;
                                description
                                    "Indicates the number of times the logger event will be ignored due to
                                     admin state of EHS trigger entry is out-of-service.";
                            }

                            leaf error-filter {
                                type yang:counter32;
                                description
                                    "Indicates the number of times the logger event will be ignored due to filter
                                     is not operational or is not configured in EHS trigger entry.";
                            }

                            leaf error-handler {
                                type yang:counter32;
                                description
                                    "Indicates the number of times the logger event will be ignored due to handler
                                     is not operational or is not configured in EHS trigger entry.";
                            }

                            leaf trigger-count {
                                type yang:counter32;
                                description
                                    "Indicates the number of times script execution is triggered after filter match
                                     for the specified trigger entry.";
                            }

                            leaf debounce-count {
                                type yang:counter32;
                                description
                                    "Indicates the number of times script is not executed due to debounce rule
                                     for the specified trigger entry.";
                            }

                        } // container statistics

                    } // list entry

                } // list rsvp

                list satellite {
                    key "event";
                    description "Enter the satellite list instance";

                    leaf event {
                        type types-log:satellite-events;
                        description "Log event as a trigger for one or more EHS handlers";
                    }

                    leaf oper-state {
                        type types-sros:oper-state;
                        description "Indicates the operational state of the EHS Event Trigger.";
                    }

                    container statistics {
                        description "Enter the statistics context";

                        leaf success {
                            type yang:counter32;
                            description
                                "Indicates the number of not ignored logger event occurrences
                                 associated with EHS trigger.";
                        }

                        leaf error-no-entry {
                            type yang:counter32;
                            description
                                "Indicates the number of ignored logger event occurrences associated
                                 with EHS trigger.

                                 Event is ignored due to no trigger entry configured for this trigger.";
                        }

                        leaf error-admin-state {
                            type yang:counter32;
                            description
                                "Indicates the number of ignored logger event occurrences associated
                                 with EHS trigger.

                                 Event is ignored due to trigger may be out-of-service.";
                        }

                        leaf total {
                            type yang:counter32;
                            description "Sum of success + error-no-entry + error-admin-state.";
                        }

                    } // container statistics

                    container summary-entry-statistics {
                        description "Enter the summary-entry-statistics context";

                        leaf filter-match {
                            type yang:counter32;
                            description "Indicates the number of times a filter matches an logger event.";
                        }

                        leaf filter-fail {
                            type yang:counter32;
                            description "Indicates the number of times a filter does not match an logger event.";
                        }

                        leaf error-admin-state {
                            type yang:counter32;
                            description
                                "Indicates the number of times the logger event will be ignored due to
                                 admin state of EHS trigger entries is out-of-service.";
                        }

                        leaf error-filter {
                            type yang:counter32;
                            description
                                "Indicates the number of times the logger event will be ignored due to filter
                                 is not operational or is not configured in EHS trigger entries.";
                        }

                        leaf error-handler {
                            type yang:counter32;
                            description
                                "Indicates the number of times the logger event will be ignored due to handler
                                 is not operational or is not configured in EHS trigger entries.";
                        }

                        leaf trigger-count {
                            type yang:counter32;
                            description "Indicates the number of times script execution is triggered after filter match.";
                        }

                        leaf debounce-count {
                            type yang:counter32;
                            description "Indicates the number of times script is not executed due to debounce rule.";
                        }

                    } // container summary-entry-statistics

                    list entry {
                        key "id";
                        description "Enter the entry list instance";

                        leaf id {
                            type uint32 {
                                range "1..1500";
                            }
                            description "ID of the EHS event trigger entry";
                        }

                        leaf oper-state {
                            type types-sros:oper-state;
                            description "Indicates the operational state of the EHS Event Trigger Entry.";
                        }

                        container statistics {
                            description "Enter the statistics context";

                            leaf filter-match {
                                type yang:counter32;
                                description
                                    "Indicates the number of times a filter, for the specified trigger entry,
                                     matches an logger event.";
                            }

                            leaf filter-fail {
                                type yang:counter32;
                                description
                                    "Indicates the number of times a filter, for the specified trigger entry,
                                     does not match an logger event.";
                            }

                            leaf error-admin-state {
                                type yang:counter32;
                                description
                                    "Indicates the number of times the logger event will be ignored due to
                                     admin state of EHS trigger entry is out-of-service.";
                            }

                            leaf error-filter {
                                type yang:counter32;
                                description
                                    "Indicates the number of times the logger event will be ignored due to filter
                                     is not operational or is not configured in EHS trigger entry.";
                            }

                            leaf error-handler {
                                type yang:counter32;
                                description
                                    "Indicates the number of times the logger event will be ignored due to handler
                                     is not operational or is not configured in EHS trigger entry.";
                            }

                            leaf trigger-count {
                                type yang:counter32;
                                description
                                    "Indicates the number of times script execution is triggered after filter match
                                     for the specified trigger entry.";
                            }

                            leaf debounce-count {
                                type yang:counter32;
                                description
                                    "Indicates the number of times script is not executed due to debounce rule
                                     for the specified trigger entry.";
                            }

                        } // container statistics

                    } // list entry

                } // list satellite

                list security {
                    key "event";
                    description "Enter the security list instance";

                    leaf event {
                        type types-log:security-events;
                        description "Log event as a trigger for one or more EHS handlers";
                    }

                    leaf oper-state {
                        type types-sros:oper-state;
                        description "Indicates the operational state of the EHS Event Trigger.";
                    }

                    container statistics {
                        description "Enter the statistics context";

                        leaf success {
                            type yang:counter32;
                            description
                                "Indicates the number of not ignored logger event occurrences
                                 associated with EHS trigger.";
                        }

                        leaf error-no-entry {
                            type yang:counter32;
                            description
                                "Indicates the number of ignored logger event occurrences associated
                                 with EHS trigger.

                                 Event is ignored due to no trigger entry configured for this trigger.";
                        }

                        leaf error-admin-state {
                            type yang:counter32;
                            description
                                "Indicates the number of ignored logger event occurrences associated
                                 with EHS trigger.

                                 Event is ignored due to trigger may be out-of-service.";
                        }

                        leaf total {
                            type yang:counter32;
                            description "Sum of success + error-no-entry + error-admin-state.";
                        }

                    } // container statistics

                    container summary-entry-statistics {
                        description "Enter the summary-entry-statistics context";

                        leaf filter-match {
                            type yang:counter32;
                            description "Indicates the number of times a filter matches an logger event.";
                        }

                        leaf filter-fail {
                            type yang:counter32;
                            description "Indicates the number of times a filter does not match an logger event.";
                        }

                        leaf error-admin-state {
                            type yang:counter32;
                            description
                                "Indicates the number of times the logger event will be ignored due to
                                 admin state of EHS trigger entries is out-of-service.";
                        }

                        leaf error-filter {
                            type yang:counter32;
                            description
                                "Indicates the number of times the logger event will be ignored due to filter
                                 is not operational or is not configured in EHS trigger entries.";
                        }

                        leaf error-handler {
                            type yang:counter32;
                            description
                                "Indicates the number of times the logger event will be ignored due to handler
                                 is not operational or is not configured in EHS trigger entries.";
                        }

                        leaf trigger-count {
                            type yang:counter32;
                            description "Indicates the number of times script execution is triggered after filter match.";
                        }

                        leaf debounce-count {
                            type yang:counter32;
                            description "Indicates the number of times script is not executed due to debounce rule.";
                        }

                    } // container summary-entry-statistics

                    list entry {
                        key "id";
                        description "Enter the entry list instance";

                        leaf id {
                            type uint32 {
                                range "1..1500";
                            }
                            description "ID of the EHS event trigger entry";
                        }

                        leaf oper-state {
                            type types-sros:oper-state;
                            description "Indicates the operational state of the EHS Event Trigger Entry.";
                        }

                        container statistics {
                            description "Enter the statistics context";

                            leaf filter-match {
                                type yang:counter32;
                                description
                                    "Indicates the number of times a filter, for the specified trigger entry,
                                     matches an logger event.";
                            }

                            leaf filter-fail {
                                type yang:counter32;
                                description
                                    "Indicates the number of times a filter, for the specified trigger entry,
                                     does not match an logger event.";
                            }

                            leaf error-admin-state {
                                type yang:counter32;
                                description
                                    "Indicates the number of times the logger event will be ignored due to
                                     admin state of EHS trigger entry is out-of-service.";
                            }

                            leaf error-filter {
                                type yang:counter32;
                                description
                                    "Indicates the number of times the logger event will be ignored due to filter
                                     is not operational or is not configured in EHS trigger entry.";
                            }

                            leaf error-handler {
                                type yang:counter32;
                                description
                                    "Indicates the number of times the logger event will be ignored due to handler
                                     is not operational or is not configured in EHS trigger entry.";
                            }

                            leaf trigger-count {
                                type yang:counter32;
                                description
                                    "Indicates the number of times script execution is triggered after filter match
                                     for the specified trigger entry.";
                            }

                            leaf debounce-count {
                                type yang:counter32;
                                description
                                    "Indicates the number of times script is not executed due to debounce rule
                                     for the specified trigger entry.";
                            }

                        } // container statistics

                    } // list entry

                } // list security

                list sflow {
                    key "event";
                    description "Enter the sflow list instance";

                    leaf event {
                        type types-log:sflow-events;
                        description "Log event as a trigger for one or more EHS handlers";
                    }

                    leaf oper-state {
                        type types-sros:oper-state;
                        description "Indicates the operational state of the EHS Event Trigger.";
                    }

                    container statistics {
                        description "Enter the statistics context";

                        leaf success {
                            type yang:counter32;
                            description
                                "Indicates the number of not ignored logger event occurrences
                                 associated with EHS trigger.";
                        }

                        leaf error-no-entry {
                            type yang:counter32;
                            description
                                "Indicates the number of ignored logger event occurrences associated
                                 with EHS trigger.

                                 Event is ignored due to no trigger entry configured for this trigger.";
                        }

                        leaf error-admin-state {
                            type yang:counter32;
                            description
                                "Indicates the number of ignored logger event occurrences associated
                                 with EHS trigger.

                                 Event is ignored due to trigger may be out-of-service.";
                        }

                        leaf total {
                            type yang:counter32;
                            description "Sum of success + error-no-entry + error-admin-state.";
                        }

                    } // container statistics

                    container summary-entry-statistics {
                        description "Enter the summary-entry-statistics context";

                        leaf filter-match {
                            type yang:counter32;
                            description "Indicates the number of times a filter matches an logger event.";
                        }

                        leaf filter-fail {
                            type yang:counter32;
                            description "Indicates the number of times a filter does not match an logger event.";
                        }

                        leaf error-admin-state {
                            type yang:counter32;
                            description
                                "Indicates the number of times the logger event will be ignored due to
                                 admin state of EHS trigger entries is out-of-service.";
                        }

                        leaf error-filter {
                            type yang:counter32;
                            description
                                "Indicates the number of times the logger event will be ignored due to filter
                                 is not operational or is not configured in EHS trigger entries.";
                        }

                        leaf error-handler {
                            type yang:counter32;
                            description
                                "Indicates the number of times the logger event will be ignored due to handler
                                 is not operational or is not configured in EHS trigger entries.";
                        }

                        leaf trigger-count {
                            type yang:counter32;
                            description "Indicates the number of times script execution is triggered after filter match.";
                        }

                        leaf debounce-count {
                            type yang:counter32;
                            description "Indicates the number of times script is not executed due to debounce rule.";
                        }

                    } // container summary-entry-statistics

                    list entry {
                        key "id";
                        description "Enter the entry list instance";

                        leaf id {
                            type uint32 {
                                range "1..1500";
                            }
                            description "ID of the EHS event trigger entry";
                        }

                        leaf oper-state {
                            type types-sros:oper-state;
                            description "Indicates the operational state of the EHS Event Trigger Entry.";
                        }

                        container statistics {
                            description "Enter the statistics context";

                            leaf filter-match {
                                type yang:counter32;
                                description
                                    "Indicates the number of times a filter, for the specified trigger entry,
                                     matches an logger event.";
                            }

                            leaf filter-fail {
                                type yang:counter32;
                                description
                                    "Indicates the number of times a filter, for the specified trigger entry,
                                     does not match an logger event.";
                            }

                            leaf error-admin-state {
                                type yang:counter32;
                                description
                                    "Indicates the number of times the logger event will be ignored due to
                                     admin state of EHS trigger entry is out-of-service.";
                            }

                            leaf error-filter {
                                type yang:counter32;
                                description
                                    "Indicates the number of times the logger event will be ignored due to filter
                                     is not operational or is not configured in EHS trigger entry.";
                            }

                            leaf error-handler {
                                type yang:counter32;
                                description
                                    "Indicates the number of times the logger event will be ignored due to handler
                                     is not operational or is not configured in EHS trigger entry.";
                            }

                            leaf trigger-count {
                                type yang:counter32;
                                description
                                    "Indicates the number of times script execution is triggered after filter match
                                     for the specified trigger entry.";
                            }

                            leaf debounce-count {
                                type yang:counter32;
                                description
                                    "Indicates the number of times script is not executed due to debounce rule
                                     for the specified trigger entry.";
                            }

                        } // container statistics

                    } // list entry

                } // list sflow

                list snmp {
                    key "event";
                    description "Enter the snmp list instance";

                    leaf event {
                        type types-log:snmp-events;
                        description "Log event as a trigger for one or more EHS handlers";
                    }

                    leaf oper-state {
                        type types-sros:oper-state;
                        description "Indicates the operational state of the EHS Event Trigger.";
                    }

                    container statistics {
                        description "Enter the statistics context";

                        leaf success {
                            type yang:counter32;
                            description
                                "Indicates the number of not ignored logger event occurrences
                                 associated with EHS trigger.";
                        }

                        leaf error-no-entry {
                            type yang:counter32;
                            description
                                "Indicates the number of ignored logger event occurrences associated
                                 with EHS trigger.

                                 Event is ignored due to no trigger entry configured for this trigger.";
                        }

                        leaf error-admin-state {
                            type yang:counter32;
                            description
                                "Indicates the number of ignored logger event occurrences associated
                                 with EHS trigger.

                                 Event is ignored due to trigger may be out-of-service.";
                        }

                        leaf total {
                            type yang:counter32;
                            description "Sum of success + error-no-entry + error-admin-state.";
                        }

                    } // container statistics

                    container summary-entry-statistics {
                        description "Enter the summary-entry-statistics context";

                        leaf filter-match {
                            type yang:counter32;
                            description "Indicates the number of times a filter matches an logger event.";
                        }

                        leaf filter-fail {
                            type yang:counter32;
                            description "Indicates the number of times a filter does not match an logger event.";
                        }

                        leaf error-admin-state {
                            type yang:counter32;
                            description
                                "Indicates the number of times the logger event will be ignored due to
                                 admin state of EHS trigger entries is out-of-service.";
                        }

                        leaf error-filter {
                            type yang:counter32;
                            description
                                "Indicates the number of times the logger event will be ignored due to filter
                                 is not operational or is not configured in EHS trigger entries.";
                        }

                        leaf error-handler {
                            type yang:counter32;
                            description
                                "Indicates the number of times the logger event will be ignored due to handler
                                 is not operational or is not configured in EHS trigger entries.";
                        }

                        leaf trigger-count {
                            type yang:counter32;
                            description "Indicates the number of times script execution is triggered after filter match.";
                        }

                        leaf debounce-count {
                            type yang:counter32;
                            description "Indicates the number of times script is not executed due to debounce rule.";
                        }

                    } // container summary-entry-statistics

                    list entry {
                        key "id";
                        description "Enter the entry list instance";

                        leaf id {
                            type uint32 {
                                range "1..1500";
                            }
                            description "ID of the EHS event trigger entry";
                        }

                        leaf oper-state {
                            type types-sros:oper-state;
                            description "Indicates the operational state of the EHS Event Trigger Entry.";
                        }

                        container statistics {
                            description "Enter the statistics context";

                            leaf filter-match {
                                type yang:counter32;
                                description
                                    "Indicates the number of times a filter, for the specified trigger entry,
                                     matches an logger event.";
                            }

                            leaf filter-fail {
                                type yang:counter32;
                                description
                                    "Indicates the number of times a filter, for the specified trigger entry,
                                     does not match an logger event.";
                            }

                            leaf error-admin-state {
                                type yang:counter32;
                                description
                                    "Indicates the number of times the logger event will be ignored due to
                                     admin state of EHS trigger entry is out-of-service.";
                            }

                            leaf error-filter {
                                type yang:counter32;
                                description
                                    "Indicates the number of times the logger event will be ignored due to filter
                                     is not operational or is not configured in EHS trigger entry.";
                            }

                            leaf error-handler {
                                type yang:counter32;
                                description
                                    "Indicates the number of times the logger event will be ignored due to handler
                                     is not operational or is not configured in EHS trigger entry.";
                            }

                            leaf trigger-count {
                                type yang:counter32;
                                description
                                    "Indicates the number of times script execution is triggered after filter match
                                     for the specified trigger entry.";
                            }

                            leaf debounce-count {
                                type yang:counter32;
                                description
                                    "Indicates the number of times script is not executed due to debounce rule
                                     for the specified trigger entry.";
                            }

                        } // container statistics

                    } // list entry

                } // list snmp

                list sr-mpls {
                    key "event";
                    description "Enter the sr-mpls list instance";

                    leaf event {
                        type types-log:sr-mpls-events;
                        description "SR MPLS event";
                    }

                    leaf oper-state {
                        type types-sros:oper-state;
                        description "Indicates the operational state of the EHS Event Trigger.";
                    }

                    container statistics {
                        description "Enter the statistics context";

                        leaf success {
                            type yang:counter32;
                            description
                                "Indicates the number of not ignored logger event occurrences
                                 associated with EHS trigger.";
                        }

                        leaf error-no-entry {
                            type yang:counter32;
                            description
                                "Indicates the number of ignored logger event occurrences associated
                                 with EHS trigger.

                                 Event is ignored due to no trigger entry configured for this trigger.";
                        }

                        leaf error-admin-state {
                            type yang:counter32;
                            description
                                "Indicates the number of ignored logger event occurrences associated
                                 with EHS trigger.

                                 Event is ignored due to trigger may be out-of-service.";
                        }

                        leaf total {
                            type yang:counter32;
                            description "Sum of success + error-no-entry + error-admin-state.";
                        }

                    } // container statistics

                    container summary-entry-statistics {
                        description "Enter the summary-entry-statistics context";

                        leaf filter-match {
                            type yang:counter32;
                            description "Indicates the number of times a filter matches an logger event.";
                        }

                        leaf filter-fail {
                            type yang:counter32;
                            description "Indicates the number of times a filter does not match an logger event.";
                        }

                        leaf error-admin-state {
                            type yang:counter32;
                            description
                                "Indicates the number of times the logger event will be ignored due to
                                 admin state of EHS trigger entries is out-of-service.";
                        }

                        leaf error-filter {
                            type yang:counter32;
                            description
                                "Indicates the number of times the logger event will be ignored due to filter
                                 is not operational or is not configured in EHS trigger entries.";
                        }

                        leaf error-handler {
                            type yang:counter32;
                            description
                                "Indicates the number of times the logger event will be ignored due to handler
                                 is not operational or is not configured in EHS trigger entries.";
                        }

                        leaf trigger-count {
                            type yang:counter32;
                            description "Indicates the number of times script execution is triggered after filter match.";
                        }

                        leaf debounce-count {
                            type yang:counter32;
                            description "Indicates the number of times script is not executed due to debounce rule.";
                        }

                    } // container summary-entry-statistics

                    list entry {
                        key "id";
                        description "Enter the entry list instance";

                        leaf id {
                            type uint32 {
                                range "1..1500";
                            }
                            description "ID of the EHS event trigger entry";
                        }

                        leaf oper-state {
                            type types-sros:oper-state;
                            description "Indicates the operational state of the EHS Event Trigger Entry.";
                        }

                        container statistics {
                            description "Enter the statistics context";

                            leaf filter-match {
                                type yang:counter32;
                                description
                                    "Indicates the number of times a filter, for the specified trigger entry,
                                     matches an logger event.";
                            }

                            leaf filter-fail {
                                type yang:counter32;
                                description
                                    "Indicates the number of times a filter, for the specified trigger entry,
                                     does not match an logger event.";
                            }

                            leaf error-admin-state {
                                type yang:counter32;
                                description
                                    "Indicates the number of times the logger event will be ignored due to
                                     admin state of EHS trigger entry is out-of-service.";
                            }

                            leaf error-filter {
                                type yang:counter32;
                                description
                                    "Indicates the number of times the logger event will be ignored due to filter
                                     is not operational or is not configured in EHS trigger entry.";
                            }

                            leaf error-handler {
                                type yang:counter32;
                                description
                                    "Indicates the number of times the logger event will be ignored due to handler
                                     is not operational or is not configured in EHS trigger entry.";
                            }

                            leaf trigger-count {
                                type yang:counter32;
                                description
                                    "Indicates the number of times script execution is triggered after filter match
                                     for the specified trigger entry.";
                            }

                            leaf debounce-count {
                                type yang:counter32;
                                description
                                    "Indicates the number of times script is not executed due to debounce rule
                                     for the specified trigger entry.";
                            }

                        } // container statistics

                    } // list entry

                } // list sr-mpls

                list srv6 {
                    key "event";
                    description "Enter the srv6 list instance";

                    leaf event {
                        type types-log:srv6-events;
                        description "Log event as a trigger for one or more EHS handlers";
                    }

                    leaf oper-state {
                        type types-sros:oper-state;
                        description "Indicates the operational state of the EHS Event Trigger.";
                    }

                    container statistics {
                        description "Enter the statistics context";

                        leaf success {
                            type yang:counter32;
                            description
                                "Indicates the number of not ignored logger event occurrences
                                 associated with EHS trigger.";
                        }

                        leaf error-no-entry {
                            type yang:counter32;
                            description
                                "Indicates the number of ignored logger event occurrences associated
                                 with EHS trigger.

                                 Event is ignored due to no trigger entry configured for this trigger.";
                        }

                        leaf error-admin-state {
                            type yang:counter32;
                            description
                                "Indicates the number of ignored logger event occurrences associated
                                 with EHS trigger.

                                 Event is ignored due to trigger may be out-of-service.";
                        }

                        leaf total {
                            type yang:counter32;
                            description "Sum of success + error-no-entry + error-admin-state.";
                        }

                    } // container statistics

                    container summary-entry-statistics {
                        description "Enter the summary-entry-statistics context";

                        leaf filter-match {
                            type yang:counter32;
                            description "Indicates the number of times a filter matches an logger event.";
                        }

                        leaf filter-fail {
                            type yang:counter32;
                            description "Indicates the number of times a filter does not match an logger event.";
                        }

                        leaf error-admin-state {
                            type yang:counter32;
                            description
                                "Indicates the number of times the logger event will be ignored due to
                                 admin state of EHS trigger entries is out-of-service.";
                        }

                        leaf error-filter {
                            type yang:counter32;
                            description
                                "Indicates the number of times the logger event will be ignored due to filter
                                 is not operational or is not configured in EHS trigger entries.";
                        }

                        leaf error-handler {
                            type yang:counter32;
                            description
                                "Indicates the number of times the logger event will be ignored due to handler
                                 is not operational or is not configured in EHS trigger entries.";
                        }

                        leaf trigger-count {
                            type yang:counter32;
                            description "Indicates the number of times script execution is triggered after filter match.";
                        }

                        leaf debounce-count {
                            type yang:counter32;
                            description "Indicates the number of times script is not executed due to debounce rule.";
                        }

                    } // container summary-entry-statistics

                    list entry {
                        key "id";
                        description "Enter the entry list instance";

                        leaf id {
                            type uint32 {
                                range "1..1500";
                            }
                            description "ID of the EHS event trigger entry";
                        }

                        leaf oper-state {
                            type types-sros:oper-state;
                            description "Indicates the operational state of the EHS Event Trigger Entry.";
                        }

                        container statistics {
                            description "Enter the statistics context";

                            leaf filter-match {
                                type yang:counter32;
                                description
                                    "Indicates the number of times a filter, for the specified trigger entry,
                                     matches an logger event.";
                            }

                            leaf filter-fail {
                                type yang:counter32;
                                description
                                    "Indicates the number of times a filter, for the specified trigger entry,
                                     does not match an logger event.";
                            }

                            leaf error-admin-state {
                                type yang:counter32;
                                description
                                    "Indicates the number of times the logger event will be ignored due to
                                     admin state of EHS trigger entry is out-of-service.";
                            }

                            leaf error-filter {
                                type yang:counter32;
                                description
                                    "Indicates the number of times the logger event will be ignored due to filter
                                     is not operational or is not configured in EHS trigger entry.";
                            }

                            leaf error-handler {
                                type yang:counter32;
                                description
                                    "Indicates the number of times the logger event will be ignored due to handler
                                     is not operational or is not configured in EHS trigger entry.";
                            }

                            leaf trigger-count {
                                type yang:counter32;
                                description
                                    "Indicates the number of times script execution is triggered after filter match
                                     for the specified trigger entry.";
                            }

                            leaf debounce-count {
                                type yang:counter32;
                                description
                                    "Indicates the number of times script is not executed due to debounce rule
                                     for the specified trigger entry.";
                            }

                        } // container statistics

                    } // list entry

                } // list srv6

                list stp {
                    key "event";
                    description "Enter the stp list instance";

                    leaf event {
                        type types-log:stp-events;
                        description "Log event as a trigger for one or more EHS handlers";
                    }

                    leaf oper-state {
                        type types-sros:oper-state;
                        description "Indicates the operational state of the EHS Event Trigger.";
                    }

                    container statistics {
                        description "Enter the statistics context";

                        leaf success {
                            type yang:counter32;
                            description
                                "Indicates the number of not ignored logger event occurrences
                                 associated with EHS trigger.";
                        }

                        leaf error-no-entry {
                            type yang:counter32;
                            description
                                "Indicates the number of ignored logger event occurrences associated
                                 with EHS trigger.

                                 Event is ignored due to no trigger entry configured for this trigger.";
                        }

                        leaf error-admin-state {
                            type yang:counter32;
                            description
                                "Indicates the number of ignored logger event occurrences associated
                                 with EHS trigger.

                                 Event is ignored due to trigger may be out-of-service.";
                        }

                        leaf total {
                            type yang:counter32;
                            description "Sum of success + error-no-entry + error-admin-state.";
                        }

                    } // container statistics

                    container summary-entry-statistics {
                        description "Enter the summary-entry-statistics context";

                        leaf filter-match {
                            type yang:counter32;
                            description "Indicates the number of times a filter matches an logger event.";
                        }

                        leaf filter-fail {
                            type yang:counter32;
                            description "Indicates the number of times a filter does not match an logger event.";
                        }

                        leaf error-admin-state {
                            type yang:counter32;
                            description
                                "Indicates the number of times the logger event will be ignored due to
                                 admin state of EHS trigger entries is out-of-service.";
                        }

                        leaf error-filter {
                            type yang:counter32;
                            description
                                "Indicates the number of times the logger event will be ignored due to filter
                                 is not operational or is not configured in EHS trigger entries.";
                        }

                        leaf error-handler {
                            type yang:counter32;
                            description
                                "Indicates the number of times the logger event will be ignored due to handler
                                 is not operational or is not configured in EHS trigger entries.";
                        }

                        leaf trigger-count {
                            type yang:counter32;
                            description "Indicates the number of times script execution is triggered after filter match.";
                        }

                        leaf debounce-count {
                            type yang:counter32;
                            description "Indicates the number of times script is not executed due to debounce rule.";
                        }

                    } // container summary-entry-statistics

                    list entry {
                        key "id";
                        description "Enter the entry list instance";

                        leaf id {
                            type uint32 {
                                range "1..1500";
                            }
                            description "ID of the EHS event trigger entry";
                        }

                        leaf oper-state {
                            type types-sros:oper-state;
                            description "Indicates the operational state of the EHS Event Trigger Entry.";
                        }

                        container statistics {
                            description "Enter the statistics context";

                            leaf filter-match {
                                type yang:counter32;
                                description
                                    "Indicates the number of times a filter, for the specified trigger entry,
                                     matches an logger event.";
                            }

                            leaf filter-fail {
                                type yang:counter32;
                                description
                                    "Indicates the number of times a filter, for the specified trigger entry,
                                     does not match an logger event.";
                            }

                            leaf error-admin-state {
                                type yang:counter32;
                                description
                                    "Indicates the number of times the logger event will be ignored due to
                                     admin state of EHS trigger entry is out-of-service.";
                            }

                            leaf error-filter {
                                type yang:counter32;
                                description
                                    "Indicates the number of times the logger event will be ignored due to filter
                                     is not operational or is not configured in EHS trigger entry.";
                            }

                            leaf error-handler {
                                type yang:counter32;
                                description
                                    "Indicates the number of times the logger event will be ignored due to handler
                                     is not operational or is not configured in EHS trigger entry.";
                            }

                            leaf trigger-count {
                                type yang:counter32;
                                description
                                    "Indicates the number of times script execution is triggered after filter match
                                     for the specified trigger entry.";
                            }

                            leaf debounce-count {
                                type yang:counter32;
                                description
                                    "Indicates the number of times script is not executed due to debounce rule
                                     for the specified trigger entry.";
                            }

                        } // container statistics

                    } // list entry

                } // list stp

                list svcmgr {
                    key "event";
                    description "Enter the svcmgr list instance";

                    leaf event {
                        type types-log:svcmgr-events;
                        description "Log event as a trigger for one or more EHS handlers";
                    }

                    leaf oper-state {
                        type types-sros:oper-state;
                        description "Indicates the operational state of the EHS Event Trigger.";
                    }

                    container statistics {
                        description "Enter the statistics context";

                        leaf success {
                            type yang:counter32;
                            description
                                "Indicates the number of not ignored logger event occurrences
                                 associated with EHS trigger.";
                        }

                        leaf error-no-entry {
                            type yang:counter32;
                            description
                                "Indicates the number of ignored logger event occurrences associated
                                 with EHS trigger.

                                 Event is ignored due to no trigger entry configured for this trigger.";
                        }

                        leaf error-admin-state {
                            type yang:counter32;
                            description
                                "Indicates the number of ignored logger event occurrences associated
                                 with EHS trigger.

                                 Event is ignored due to trigger may be out-of-service.";
                        }

                        leaf total {
                            type yang:counter32;
                            description "Sum of success + error-no-entry + error-admin-state.";
                        }

                    } // container statistics

                    container summary-entry-statistics {
                        description "Enter the summary-entry-statistics context";

                        leaf filter-match {
                            type yang:counter32;
                            description "Indicates the number of times a filter matches an logger event.";
                        }

                        leaf filter-fail {
                            type yang:counter32;
                            description "Indicates the number of times a filter does not match an logger event.";
                        }

                        leaf error-admin-state {
                            type yang:counter32;
                            description
                                "Indicates the number of times the logger event will be ignored due to
                                 admin state of EHS trigger entries is out-of-service.";
                        }

                        leaf error-filter {
                            type yang:counter32;
                            description
                                "Indicates the number of times the logger event will be ignored due to filter
                                 is not operational or is not configured in EHS trigger entries.";
                        }

                        leaf error-handler {
                            type yang:counter32;
                            description
                                "Indicates the number of times the logger event will be ignored due to handler
                                 is not operational or is not configured in EHS trigger entries.";
                        }

                        leaf trigger-count {
                            type yang:counter32;
                            description "Indicates the number of times script execution is triggered after filter match.";
                        }

                        leaf debounce-count {
                            type yang:counter32;
                            description "Indicates the number of times script is not executed due to debounce rule.";
                        }

                    } // container summary-entry-statistics

                    list entry {
                        key "id";
                        description "Enter the entry list instance";

                        leaf id {
                            type uint32 {
                                range "1..1500";
                            }
                            description "ID of the EHS event trigger entry";
                        }

                        leaf oper-state {
                            type types-sros:oper-state;
                            description "Indicates the operational state of the EHS Event Trigger Entry.";
                        }

                        container statistics {
                            description "Enter the statistics context";

                            leaf filter-match {
                                type yang:counter32;
                                description
                                    "Indicates the number of times a filter, for the specified trigger entry,
                                     matches an logger event.";
                            }

                            leaf filter-fail {
                                type yang:counter32;
                                description
                                    "Indicates the number of times a filter, for the specified trigger entry,
                                     does not match an logger event.";
                            }

                            leaf error-admin-state {
                                type yang:counter32;
                                description
                                    "Indicates the number of times the logger event will be ignored due to
                                     admin state of EHS trigger entry is out-of-service.";
                            }

                            leaf error-filter {
                                type yang:counter32;
                                description
                                    "Indicates the number of times the logger event will be ignored due to filter
                                     is not operational or is not configured in EHS trigger entry.";
                            }

                            leaf error-handler {
                                type yang:counter32;
                                description
                                    "Indicates the number of times the logger event will be ignored due to handler
                                     is not operational or is not configured in EHS trigger entry.";
                            }

                            leaf trigger-count {
                                type yang:counter32;
                                description
                                    "Indicates the number of times script execution is triggered after filter match
                                     for the specified trigger entry.";
                            }

                            leaf debounce-count {
                                type yang:counter32;
                                description
                                    "Indicates the number of times script is not executed due to debounce rule
                                     for the specified trigger entry.";
                            }

                        } // container statistics

                    } // list entry

                } // list svcmgr

                list system {
                    key "event";
                    description "Enter the system list instance";

                    leaf event {
                        type types-log:system-events;
                        description "Log event as a trigger for one or more EHS handlers";
                    }

                    leaf oper-state {
                        type types-sros:oper-state;
                        description "Indicates the operational state of the EHS Event Trigger.";
                    }

                    container statistics {
                        description "Enter the statistics context";

                        leaf success {
                            type yang:counter32;
                            description
                                "Indicates the number of not ignored logger event occurrences
                                 associated with EHS trigger.";
                        }

                        leaf error-no-entry {
                            type yang:counter32;
                            description
                                "Indicates the number of ignored logger event occurrences associated
                                 with EHS trigger.

                                 Event is ignored due to no trigger entry configured for this trigger.";
                        }

                        leaf error-admin-state {
                            type yang:counter32;
                            description
                                "Indicates the number of ignored logger event occurrences associated
                                 with EHS trigger.

                                 Event is ignored due to trigger may be out-of-service.";
                        }

                        leaf total {
                            type yang:counter32;
                            description "Sum of success + error-no-entry + error-admin-state.";
                        }

                    } // container statistics

                    container summary-entry-statistics {
                        description "Enter the summary-entry-statistics context";

                        leaf filter-match {
                            type yang:counter32;
                            description "Indicates the number of times a filter matches an logger event.";
                        }

                        leaf filter-fail {
                            type yang:counter32;
                            description "Indicates the number of times a filter does not match an logger event.";
                        }

                        leaf error-admin-state {
                            type yang:counter32;
                            description
                                "Indicates the number of times the logger event will be ignored due to
                                 admin state of EHS trigger entries is out-of-service.";
                        }

                        leaf error-filter {
                            type yang:counter32;
                            description
                                "Indicates the number of times the logger event will be ignored due to filter
                                 is not operational or is not configured in EHS trigger entries.";
                        }

                        leaf error-handler {
                            type yang:counter32;
                            description
                                "Indicates the number of times the logger event will be ignored due to handler
                                 is not operational or is not configured in EHS trigger entries.";
                        }

                        leaf trigger-count {
                            type yang:counter32;
                            description "Indicates the number of times script execution is triggered after filter match.";
                        }

                        leaf debounce-count {
                            type yang:counter32;
                            description "Indicates the number of times script is not executed due to debounce rule.";
                        }

                    } // container summary-entry-statistics

                    list entry {
                        key "id";
                        description "Enter the entry list instance";

                        leaf id {
                            type uint32 {
                                range "1..1500";
                            }
                            description "ID of the EHS event trigger entry";
                        }

                        leaf oper-state {
                            type types-sros:oper-state;
                            description "Indicates the operational state of the EHS Event Trigger Entry.";
                        }

                        container statistics {
                            description "Enter the statistics context";

                            leaf filter-match {
                                type yang:counter32;
                                description
                                    "Indicates the number of times a filter, for the specified trigger entry,
                                     matches an logger event.";
                            }

                            leaf filter-fail {
                                type yang:counter32;
                                description
                                    "Indicates the number of times a filter, for the specified trigger entry,
                                     does not match an logger event.";
                            }

                            leaf error-admin-state {
                                type yang:counter32;
                                description
                                    "Indicates the number of times the logger event will be ignored due to
                                     admin state of EHS trigger entry is out-of-service.";
                            }

                            leaf error-filter {
                                type yang:counter32;
                                description
                                    "Indicates the number of times the logger event will be ignored due to filter
                                     is not operational or is not configured in EHS trigger entry.";
                            }

                            leaf error-handler {
                                type yang:counter32;
                                description
                                    "Indicates the number of times the logger event will be ignored due to handler
                                     is not operational or is not configured in EHS trigger entry.";
                            }

                            leaf trigger-count {
                                type yang:counter32;
                                description
                                    "Indicates the number of times script execution is triggered after filter match
                                     for the specified trigger entry.";
                            }

                            leaf debounce-count {
                                type yang:counter32;
                                description
                                    "Indicates the number of times script is not executed due to debounce rule
                                     for the specified trigger entry.";
                            }

                        } // container statistics

                    } // list entry

                } // list system

                list tls {
                    key "event";
                    description "Enter the tls list instance";

                    leaf event {
                        type types-log:tls-events;
                        description "Log event as a trigger for one or more EHS handlers";
                    }

                    leaf oper-state {
                        type types-sros:oper-state;
                        description "Indicates the operational state of the EHS Event Trigger.";
                    }

                    container statistics {
                        description "Enter the statistics context";

                        leaf success {
                            type yang:counter32;
                            description
                                "Indicates the number of not ignored logger event occurrences
                                 associated with EHS trigger.";
                        }

                        leaf error-no-entry {
                            type yang:counter32;
                            description
                                "Indicates the number of ignored logger event occurrences associated
                                 with EHS trigger.

                                 Event is ignored due to no trigger entry configured for this trigger.";
                        }

                        leaf error-admin-state {
                            type yang:counter32;
                            description
                                "Indicates the number of ignored logger event occurrences associated
                                 with EHS trigger.

                                 Event is ignored due to trigger may be out-of-service.";
                        }

                        leaf total {
                            type yang:counter32;
                            description "Sum of success + error-no-entry + error-admin-state.";
                        }

                    } // container statistics

                    container summary-entry-statistics {
                        description "Enter the summary-entry-statistics context";

                        leaf filter-match {
                            type yang:counter32;
                            description "Indicates the number of times a filter matches an logger event.";
                        }

                        leaf filter-fail {
                            type yang:counter32;
                            description "Indicates the number of times a filter does not match an logger event.";
                        }

                        leaf error-admin-state {
                            type yang:counter32;
                            description
                                "Indicates the number of times the logger event will be ignored due to
                                 admin state of EHS trigger entries is out-of-service.";
                        }

                        leaf error-filter {
                            type yang:counter32;
                            description
                                "Indicates the number of times the logger event will be ignored due to filter
                                 is not operational or is not configured in EHS trigger entries.";
                        }

                        leaf error-handler {
                            type yang:counter32;
                            description
                                "Indicates the number of times the logger event will be ignored due to handler
                                 is not operational or is not configured in EHS trigger entries.";
                        }

                        leaf trigger-count {
                            type yang:counter32;
                            description "Indicates the number of times script execution is triggered after filter match.";
                        }

                        leaf debounce-count {
                            type yang:counter32;
                            description "Indicates the number of times script is not executed due to debounce rule.";
                        }

                    } // container summary-entry-statistics

                    list entry {
                        key "id";
                        description "Enter the entry list instance";

                        leaf id {
                            type uint32 {
                                range "1..1500";
                            }
                            description "ID of the EHS event trigger entry";
                        }

                        leaf oper-state {
                            type types-sros:oper-state;
                            description "Indicates the operational state of the EHS Event Trigger Entry.";
                        }

                        container statistics {
                            description "Enter the statistics context";

                            leaf filter-match {
                                type yang:counter32;
                                description
                                    "Indicates the number of times a filter, for the specified trigger entry,
                                     matches an logger event.";
                            }

                            leaf filter-fail {
                                type yang:counter32;
                                description
                                    "Indicates the number of times a filter, for the specified trigger entry,
                                     does not match an logger event.";
                            }

                            leaf error-admin-state {
                                type yang:counter32;
                                description
                                    "Indicates the number of times the logger event will be ignored due to
                                     admin state of EHS trigger entry is out-of-service.";
                            }

                            leaf error-filter {
                                type yang:counter32;
                                description
                                    "Indicates the number of times the logger event will be ignored due to filter
                                     is not operational or is not configured in EHS trigger entry.";
                            }

                            leaf error-handler {
                                type yang:counter32;
                                description
                                    "Indicates the number of times the logger event will be ignored due to handler
                                     is not operational or is not configured in EHS trigger entry.";
                            }

                            leaf trigger-count {
                                type yang:counter32;
                                description
                                    "Indicates the number of times script execution is triggered after filter match
                                     for the specified trigger entry.";
                            }

                            leaf debounce-count {
                                type yang:counter32;
                                description
                                    "Indicates the number of times script is not executed due to debounce rule
                                     for the specified trigger entry.";
                            }

                        } // container statistics

                    } // list entry

                } // list tls

                list tree-sid {
                    key "event";
                    description "Enter the tree-sid list instance";

                    leaf event {
                        type types-log:treesid-events;
                        description "Log event as a trigger for one or more EHS handlers";
                    }

                    leaf oper-state {
                        type types-sros:oper-state;
                        description "Indicates the operational state of the EHS Event Trigger.";
                    }

                    container statistics {
                        description "Enter the statistics context";

                        leaf success {
                            type yang:counter32;
                            description
                                "Indicates the number of not ignored logger event occurrences
                                 associated with EHS trigger.";
                        }

                        leaf error-no-entry {
                            type yang:counter32;
                            description
                                "Indicates the number of ignored logger event occurrences associated
                                 with EHS trigger.

                                 Event is ignored due to no trigger entry configured for this trigger.";
                        }

                        leaf error-admin-state {
                            type yang:counter32;
                            description
                                "Indicates the number of ignored logger event occurrences associated
                                 with EHS trigger.

                                 Event is ignored due to trigger may be out-of-service.";
                        }

                        leaf total {
                            type yang:counter32;
                            description "Sum of success + error-no-entry + error-admin-state.";
                        }

                    } // container statistics

                    container summary-entry-statistics {
                        description "Enter the summary-entry-statistics context";

                        leaf filter-match {
                            type yang:counter32;
                            description "Indicates the number of times a filter matches an logger event.";
                        }

                        leaf filter-fail {
                            type yang:counter32;
                            description "Indicates the number of times a filter does not match an logger event.";
                        }

                        leaf error-admin-state {
                            type yang:counter32;
                            description
                                "Indicates the number of times the logger event will be ignored due to
                                 admin state of EHS trigger entries is out-of-service.";
                        }

                        leaf error-filter {
                            type yang:counter32;
                            description
                                "Indicates the number of times the logger event will be ignored due to filter
                                 is not operational or is not configured in EHS trigger entries.";
                        }

                        leaf error-handler {
                            type yang:counter32;
                            description
                                "Indicates the number of times the logger event will be ignored due to handler
                                 is not operational or is not configured in EHS trigger entries.";
                        }

                        leaf trigger-count {
                            type yang:counter32;
                            description "Indicates the number of times script execution is triggered after filter match.";
                        }

                        leaf debounce-count {
                            type yang:counter32;
                            description "Indicates the number of times script is not executed due to debounce rule.";
                        }

                    } // container summary-entry-statistics

                    list entry {
                        key "id";
                        description "Enter the entry list instance";

                        leaf id {
                            type uint32 {
                                range "1..1500";
                            }
                            description "ID of the EHS event trigger entry";
                        }

                        leaf oper-state {
                            type types-sros:oper-state;
                            description "Indicates the operational state of the EHS Event Trigger Entry.";
                        }

                        container statistics {
                            description "Enter the statistics context";

                            leaf filter-match {
                                type yang:counter32;
                                description
                                    "Indicates the number of times a filter, for the specified trigger entry,
                                     matches an logger event.";
                            }

                            leaf filter-fail {
                                type yang:counter32;
                                description
                                    "Indicates the number of times a filter, for the specified trigger entry,
                                     does not match an logger event.";
                            }

                            leaf error-admin-state {
                                type yang:counter32;
                                description
                                    "Indicates the number of times the logger event will be ignored due to
                                     admin state of EHS trigger entry is out-of-service.";
                            }

                            leaf error-filter {
                                type yang:counter32;
                                description
                                    "Indicates the number of times the logger event will be ignored due to filter
                                     is not operational or is not configured in EHS trigger entry.";
                            }

                            leaf error-handler {
                                type yang:counter32;
                                description
                                    "Indicates the number of times the logger event will be ignored due to handler
                                     is not operational or is not configured in EHS trigger entry.";
                            }

                            leaf trigger-count {
                                type yang:counter32;
                                description
                                    "Indicates the number of times script execution is triggered after filter match
                                     for the specified trigger entry.";
                            }

                            leaf debounce-count {
                                type yang:counter32;
                                description
                                    "Indicates the number of times script is not executed due to debounce rule
                                     for the specified trigger entry.";
                            }

                        } // container statistics

                    } // list entry

                } // list tree-sid

                list user {
                    key "event";
                    description "Enter the user list instance";

                    leaf event {
                        type types-log:user-events;
                        description "Log event as a trigger for one or more EHS handlers";
                    }

                    leaf oper-state {
                        type types-sros:oper-state;
                        description "Indicates the operational state of the EHS Event Trigger.";
                    }

                    container statistics {
                        description "Enter the statistics context";

                        leaf success {
                            type yang:counter32;
                            description
                                "Indicates the number of not ignored logger event occurrences
                                 associated with EHS trigger.";
                        }

                        leaf error-no-entry {
                            type yang:counter32;
                            description
                                "Indicates the number of ignored logger event occurrences associated
                                 with EHS trigger.

                                 Event is ignored due to no trigger entry configured for this trigger.";
                        }

                        leaf error-admin-state {
                            type yang:counter32;
                            description
                                "Indicates the number of ignored logger event occurrences associated
                                 with EHS trigger.

                                 Event is ignored due to trigger may be out-of-service.";
                        }

                        leaf total {
                            type yang:counter32;
                            description "Sum of success + error-no-entry + error-admin-state.";
                        }

                    } // container statistics

                    container summary-entry-statistics {
                        description "Enter the summary-entry-statistics context";

                        leaf filter-match {
                            type yang:counter32;
                            description "Indicates the number of times a filter matches an logger event.";
                        }

                        leaf filter-fail {
                            type yang:counter32;
                            description "Indicates the number of times a filter does not match an logger event.";
                        }

                        leaf error-admin-state {
                            type yang:counter32;
                            description
                                "Indicates the number of times the logger event will be ignored due to
                                 admin state of EHS trigger entries is out-of-service.";
                        }

                        leaf error-filter {
                            type yang:counter32;
                            description
                                "Indicates the number of times the logger event will be ignored due to filter
                                 is not operational or is not configured in EHS trigger entries.";
                        }

                        leaf error-handler {
                            type yang:counter32;
                            description
                                "Indicates the number of times the logger event will be ignored due to handler
                                 is not operational or is not configured in EHS trigger entries.";
                        }

                        leaf trigger-count {
                            type yang:counter32;
                            description "Indicates the number of times script execution is triggered after filter match.";
                        }

                        leaf debounce-count {
                            type yang:counter32;
                            description "Indicates the number of times script is not executed due to debounce rule.";
                        }

                    } // container summary-entry-statistics

                    list entry {
                        key "id";
                        description "Enter the entry list instance";

                        leaf id {
                            type uint32 {
                                range "1..1500";
                            }
                            description "ID of the EHS event trigger entry";
                        }

                        leaf oper-state {
                            type types-sros:oper-state;
                            description "Indicates the operational state of the EHS Event Trigger Entry.";
                        }

                        container statistics {
                            description "Enter the statistics context";

                            leaf filter-match {
                                type yang:counter32;
                                description
                                    "Indicates the number of times a filter, for the specified trigger entry,
                                     matches an logger event.";
                            }

                            leaf filter-fail {
                                type yang:counter32;
                                description
                                    "Indicates the number of times a filter, for the specified trigger entry,
                                     does not match an logger event.";
                            }

                            leaf error-admin-state {
                                type yang:counter32;
                                description
                                    "Indicates the number of times the logger event will be ignored due to
                                     admin state of EHS trigger entry is out-of-service.";
                            }

                            leaf error-filter {
                                type yang:counter32;
                                description
                                    "Indicates the number of times the logger event will be ignored due to filter
                                     is not operational or is not configured in EHS trigger entry.";
                            }

                            leaf error-handler {
                                type yang:counter32;
                                description
                                    "Indicates the number of times the logger event will be ignored due to handler
                                     is not operational or is not configured in EHS trigger entry.";
                            }

                            leaf trigger-count {
                                type yang:counter32;
                                description
                                    "Indicates the number of times script execution is triggered after filter match
                                     for the specified trigger entry.";
                            }

                            leaf debounce-count {
                                type yang:counter32;
                                description
                                    "Indicates the number of times script is not executed due to debounce rule
                                     for the specified trigger entry.";
                            }

                        } // container statistics

                    } // list entry

                } // list user

                list video {
                    key "event";
                    description "Enter the video list instance";

                    leaf event {
                        type types-log:video-events;
                        description "Log event as a trigger for one or more EHS handlers";
                    }

                    leaf oper-state {
                        type types-sros:oper-state;
                        description "Indicates the operational state of the EHS Event Trigger.";
                    }

                    container statistics {
                        description "Enter the statistics context";

                        leaf success {
                            type yang:counter32;
                            description
                                "Indicates the number of not ignored logger event occurrences
                                 associated with EHS trigger.";
                        }

                        leaf error-no-entry {
                            type yang:counter32;
                            description
                                "Indicates the number of ignored logger event occurrences associated
                                 with EHS trigger.

                                 Event is ignored due to no trigger entry configured for this trigger.";
                        }

                        leaf error-admin-state {
                            type yang:counter32;
                            description
                                "Indicates the number of ignored logger event occurrences associated
                                 with EHS trigger.

                                 Event is ignored due to trigger may be out-of-service.";
                        }

                        leaf total {
                            type yang:counter32;
                            description "Sum of success + error-no-entry + error-admin-state.";
                        }

                    } // container statistics

                    container summary-entry-statistics {
                        description "Enter the summary-entry-statistics context";

                        leaf filter-match {
                            type yang:counter32;
                            description "Indicates the number of times a filter matches an logger event.";
                        }

                        leaf filter-fail {
                            type yang:counter32;
                            description "Indicates the number of times a filter does not match an logger event.";
                        }

                        leaf error-admin-state {
                            type yang:counter32;
                            description
                                "Indicates the number of times the logger event will be ignored due to
                                 admin state of EHS trigger entries is out-of-service.";
                        }

                        leaf error-filter {
                            type yang:counter32;
                            description
                                "Indicates the number of times the logger event will be ignored due to filter
                                 is not operational or is not configured in EHS trigger entries.";
                        }

                        leaf error-handler {
                            type yang:counter32;
                            description
                                "Indicates the number of times the logger event will be ignored due to handler
                                 is not operational or is not configured in EHS trigger entries.";
                        }

                        leaf trigger-count {
                            type yang:counter32;
                            description "Indicates the number of times script execution is triggered after filter match.";
                        }

                        leaf debounce-count {
                            type yang:counter32;
                            description "Indicates the number of times script is not executed due to debounce rule.";
                        }

                    } // container summary-entry-statistics

                    list entry {
                        key "id";
                        description "Enter the entry list instance";

                        leaf id {
                            type uint32 {
                                range "1..1500";
                            }
                            description "ID of the EHS event trigger entry";
                        }

                        leaf oper-state {
                            type types-sros:oper-state;
                            description "Indicates the operational state of the EHS Event Trigger Entry.";
                        }

                        container statistics {
                            description "Enter the statistics context";

                            leaf filter-match {
                                type yang:counter32;
                                description
                                    "Indicates the number of times a filter, for the specified trigger entry,
                                     matches an logger event.";
                            }

                            leaf filter-fail {
                                type yang:counter32;
                                description
                                    "Indicates the number of times a filter, for the specified trigger entry,
                                     does not match an logger event.";
                            }

                            leaf error-admin-state {
                                type yang:counter32;
                                description
                                    "Indicates the number of times the logger event will be ignored due to
                                     admin state of EHS trigger entry is out-of-service.";
                            }

                            leaf error-filter {
                                type yang:counter32;
                                description
                                    "Indicates the number of times the logger event will be ignored due to filter
                                     is not operational or is not configured in EHS trigger entry.";
                            }

                            leaf error-handler {
                                type yang:counter32;
                                description
                                    "Indicates the number of times the logger event will be ignored due to handler
                                     is not operational or is not configured in EHS trigger entry.";
                            }

                            leaf trigger-count {
                                type yang:counter32;
                                description
                                    "Indicates the number of times script execution is triggered after filter match
                                     for the specified trigger entry.";
                            }

                            leaf debounce-count {
                                type yang:counter32;
                                description
                                    "Indicates the number of times script is not executed due to debounce rule
                                     for the specified trigger entry.";
                            }

                        } // container statistics

                    } // list entry

                } // list video

                list vrrp {
                    key "event";
                    description "Enter the vrrp list instance";

                    leaf event {
                        type types-log:vrrp-events;
                        description "Log event as a trigger for one or more EHS handlers";
                    }

                    leaf oper-state {
                        type types-sros:oper-state;
                        description "Indicates the operational state of the EHS Event Trigger.";
                    }

                    container statistics {
                        description "Enter the statistics context";

                        leaf success {
                            type yang:counter32;
                            description
                                "Indicates the number of not ignored logger event occurrences
                                 associated with EHS trigger.";
                        }

                        leaf error-no-entry {
                            type yang:counter32;
                            description
                                "Indicates the number of ignored logger event occurrences associated
                                 with EHS trigger.

                                 Event is ignored due to no trigger entry configured for this trigger.";
                        }

                        leaf error-admin-state {
                            type yang:counter32;
                            description
                                "Indicates the number of ignored logger event occurrences associated
                                 with EHS trigger.

                                 Event is ignored due to trigger may be out-of-service.";
                        }

                        leaf total {
                            type yang:counter32;
                            description "Sum of success + error-no-entry + error-admin-state.";
                        }

                    } // container statistics

                    container summary-entry-statistics {
                        description "Enter the summary-entry-statistics context";

                        leaf filter-match {
                            type yang:counter32;
                            description "Indicates the number of times a filter matches an logger event.";
                        }

                        leaf filter-fail {
                            type yang:counter32;
                            description "Indicates the number of times a filter does not match an logger event.";
                        }

                        leaf error-admin-state {
                            type yang:counter32;
                            description
                                "Indicates the number of times the logger event will be ignored due to
                                 admin state of EHS trigger entries is out-of-service.";
                        }

                        leaf error-filter {
                            type yang:counter32;
                            description
                                "Indicates the number of times the logger event will be ignored due to filter
                                 is not operational or is not configured in EHS trigger entries.";
                        }

                        leaf error-handler {
                            type yang:counter32;
                            description
                                "Indicates the number of times the logger event will be ignored due to handler
                                 is not operational or is not configured in EHS trigger entries.";
                        }

                        leaf trigger-count {
                            type yang:counter32;
                            description "Indicates the number of times script execution is triggered after filter match.";
                        }

                        leaf debounce-count {
                            type yang:counter32;
                            description "Indicates the number of times script is not executed due to debounce rule.";
                        }

                    } // container summary-entry-statistics

                    list entry {
                        key "id";
                        description "Enter the entry list instance";

                        leaf id {
                            type uint32 {
                                range "1..1500";
                            }
                            description "ID of the EHS event trigger entry";
                        }

                        leaf oper-state {
                            type types-sros:oper-state;
                            description "Indicates the operational state of the EHS Event Trigger Entry.";
                        }

                        container statistics {
                            description "Enter the statistics context";

                            leaf filter-match {
                                type yang:counter32;
                                description
                                    "Indicates the number of times a filter, for the specified trigger entry,
                                     matches an logger event.";
                            }

                            leaf filter-fail {
                                type yang:counter32;
                                description
                                    "Indicates the number of times a filter, for the specified trigger entry,
                                     does not match an logger event.";
                            }

                            leaf error-admin-state {
                                type yang:counter32;
                                description
                                    "Indicates the number of times the logger event will be ignored due to
                                     admin state of EHS trigger entry is out-of-service.";
                            }

                            leaf error-filter {
                                type yang:counter32;
                                description
                                    "Indicates the number of times the logger event will be ignored due to filter
                                     is not operational or is not configured in EHS trigger entry.";
                            }

                            leaf error-handler {
                                type yang:counter32;
                                description
                                    "Indicates the number of times the logger event will be ignored due to handler
                                     is not operational or is not configured in EHS trigger entry.";
                            }

                            leaf trigger-count {
                                type yang:counter32;
                                description
                                    "Indicates the number of times script execution is triggered after filter match
                                     for the specified trigger entry.";
                            }

                            leaf debounce-count {
                                type yang:counter32;
                                description
                                    "Indicates the number of times script is not executed due to debounce rule
                                     for the specified trigger entry.";
                            }

                        } // container statistics

                    } // list entry

                } // list vrrp

                list vrtr {
                    key "event";
                    description "Enter the vrtr list instance";

                    leaf event {
                        type types-log:vrtr-events;
                        description "Log event as a trigger for one or more EHS handlers";
                    }

                    leaf oper-state {
                        type types-sros:oper-state;
                        description "Indicates the operational state of the EHS Event Trigger.";
                    }

                    container statistics {
                        description "Enter the statistics context";

                        leaf success {
                            type yang:counter32;
                            description
                                "Indicates the number of not ignored logger event occurrences
                                 associated with EHS trigger.";
                        }

                        leaf error-no-entry {
                            type yang:counter32;
                            description
                                "Indicates the number of ignored logger event occurrences associated
                                 with EHS trigger.

                                 Event is ignored due to no trigger entry configured for this trigger.";
                        }

                        leaf error-admin-state {
                            type yang:counter32;
                            description
                                "Indicates the number of ignored logger event occurrences associated
                                 with EHS trigger.

                                 Event is ignored due to trigger may be out-of-service.";
                        }

                        leaf total {
                            type yang:counter32;
                            description "Sum of success + error-no-entry + error-admin-state.";
                        }

                    } // container statistics

                    container summary-entry-statistics {
                        description "Enter the summary-entry-statistics context";

                        leaf filter-match {
                            type yang:counter32;
                            description "Indicates the number of times a filter matches an logger event.";
                        }

                        leaf filter-fail {
                            type yang:counter32;
                            description "Indicates the number of times a filter does not match an logger event.";
                        }

                        leaf error-admin-state {
                            type yang:counter32;
                            description
                                "Indicates the number of times the logger event will be ignored due to
                                 admin state of EHS trigger entries is out-of-service.";
                        }

                        leaf error-filter {
                            type yang:counter32;
                            description
                                "Indicates the number of times the logger event will be ignored due to filter
                                 is not operational or is not configured in EHS trigger entries.";
                        }

                        leaf error-handler {
                            type yang:counter32;
                            description
                                "Indicates the number of times the logger event will be ignored due to handler
                                 is not operational or is not configured in EHS trigger entries.";
                        }

                        leaf trigger-count {
                            type yang:counter32;
                            description "Indicates the number of times script execution is triggered after filter match.";
                        }

                        leaf debounce-count {
                            type yang:counter32;
                            description "Indicates the number of times script is not executed due to debounce rule.";
                        }

                    } // container summary-entry-statistics

                    list entry {
                        key "id";
                        description "Enter the entry list instance";

                        leaf id {
                            type uint32 {
                                range "1..1500";
                            }
                            description "ID of the EHS event trigger entry";
                        }

                        leaf oper-state {
                            type types-sros:oper-state;
                            description "Indicates the operational state of the EHS Event Trigger Entry.";
                        }

                        container statistics {
                            description "Enter the statistics context";

                            leaf filter-match {
                                type yang:counter32;
                                description
                                    "Indicates the number of times a filter, for the specified trigger entry,
                                     matches an logger event.";
                            }

                            leaf filter-fail {
                                type yang:counter32;
                                description
                                    "Indicates the number of times a filter, for the specified trigger entry,
                                     does not match an logger event.";
                            }

                            leaf error-admin-state {
                                type yang:counter32;
                                description
                                    "Indicates the number of times the logger event will be ignored due to
                                     admin state of EHS trigger entry is out-of-service.";
                            }

                            leaf error-filter {
                                type yang:counter32;
                                description
                                    "Indicates the number of times the logger event will be ignored due to filter
                                     is not operational or is not configured in EHS trigger entry.";
                            }

                            leaf error-handler {
                                type yang:counter32;
                                description
                                    "Indicates the number of times the logger event will be ignored due to handler
                                     is not operational or is not configured in EHS trigger entry.";
                            }

                            leaf trigger-count {
                                type yang:counter32;
                                description
                                    "Indicates the number of times script execution is triggered after filter match
                                     for the specified trigger entry.";
                            }

                            leaf debounce-count {
                                type yang:counter32;
                                description
                                    "Indicates the number of times script is not executed due to debounce rule
                                     for the specified trigger entry.";
                            }

                        } // container statistics

                    } // list entry

                } // list vrtr

                list wlan-gw {
                    key "event";
                    description "Enter the wlan-gw list instance";

                    leaf event {
                        type types-log:wlan-gw-events;
                        description "Log event as a trigger for one or more EHS handlers";
                    }

                    leaf oper-state {
                        type types-sros:oper-state;
                        description "Indicates the operational state of the EHS Event Trigger.";
                    }

                    container statistics {
                        description "Enter the statistics context";

                        leaf success {
                            type yang:counter32;
                            description
                                "Indicates the number of not ignored logger event occurrences
                                 associated with EHS trigger.";
                        }

                        leaf error-no-entry {
                            type yang:counter32;
                            description
                                "Indicates the number of ignored logger event occurrences associated
                                 with EHS trigger.

                                 Event is ignored due to no trigger entry configured for this trigger.";
                        }

                        leaf error-admin-state {
                            type yang:counter32;
                            description
                                "Indicates the number of ignored logger event occurrences associated
                                 with EHS trigger.

                                 Event is ignored due to trigger may be out-of-service.";
                        }

                        leaf total {
                            type yang:counter32;
                            description "Sum of success + error-no-entry + error-admin-state.";
                        }

                    } // container statistics

                    container summary-entry-statistics {
                        description "Enter the summary-entry-statistics context";

                        leaf filter-match {
                            type yang:counter32;
                            description "Indicates the number of times a filter matches an logger event.";
                        }

                        leaf filter-fail {
                            type yang:counter32;
                            description "Indicates the number of times a filter does not match an logger event.";
                        }

                        leaf error-admin-state {
                            type yang:counter32;
                            description
                                "Indicates the number of times the logger event will be ignored due to
                                 admin state of EHS trigger entries is out-of-service.";
                        }

                        leaf error-filter {
                            type yang:counter32;
                            description
                                "Indicates the number of times the logger event will be ignored due to filter
                                 is not operational or is not configured in EHS trigger entries.";
                        }

                        leaf error-handler {
                            type yang:counter32;
                            description
                                "Indicates the number of times the logger event will be ignored due to handler
                                 is not operational or is not configured in EHS trigger entries.";
                        }

                        leaf trigger-count {
                            type yang:counter32;
                            description "Indicates the number of times script execution is triggered after filter match.";
                        }

                        leaf debounce-count {
                            type yang:counter32;
                            description "Indicates the number of times script is not executed due to debounce rule.";
                        }

                    } // container summary-entry-statistics

                    list entry {
                        key "id";
                        description "Enter the entry list instance";

                        leaf id {
                            type uint32 {
                                range "1..1500";
                            }
                            description "ID of the EHS event trigger entry";
                        }

                        leaf oper-state {
                            type types-sros:oper-state;
                            description "Indicates the operational state of the EHS Event Trigger Entry.";
                        }

                        container statistics {
                            description "Enter the statistics context";

                            leaf filter-match {
                                type yang:counter32;
                                description
                                    "Indicates the number of times a filter, for the specified trigger entry,
                                     matches an logger event.";
                            }

                            leaf filter-fail {
                                type yang:counter32;
                                description
                                    "Indicates the number of times a filter, for the specified trigger entry,
                                     does not match an logger event.";
                            }

                            leaf error-admin-state {
                                type yang:counter32;
                                description
                                    "Indicates the number of times the logger event will be ignored due to
                                     admin state of EHS trigger entry is out-of-service.";
                            }

                            leaf error-filter {
                                type yang:counter32;
                                description
                                    "Indicates the number of times the logger event will be ignored due to filter
                                     is not operational or is not configured in EHS trigger entry.";
                            }

                            leaf error-handler {
                                type yang:counter32;
                                description
                                    "Indicates the number of times the logger event will be ignored due to handler
                                     is not operational or is not configured in EHS trigger entry.";
                            }

                            leaf trigger-count {
                                type yang:counter32;
                                description
                                    "Indicates the number of times script execution is triggered after filter match
                                     for the specified trigger entry.";
                            }

                            leaf debounce-count {
                                type yang:counter32;
                                description
                                    "Indicates the number of times script is not executed due to debounce rule
                                     for the specified trigger entry.";
                            }

                        } // container statistics

                    } // list entry

                } // list wlan-gw

                list wpp {
                    key "event";
                    description "Enter the wpp list instance";

                    leaf event {
                        type types-log:wpp-events;
                        description "Log event as a trigger for one or more EHS handlers";
                    }

                    leaf oper-state {
                        type types-sros:oper-state;
                        description "Indicates the operational state of the EHS Event Trigger.";
                    }

                    container statistics {
                        description "Enter the statistics context";

                        leaf success {
                            type yang:counter32;
                            description
                                "Indicates the number of not ignored logger event occurrences
                                 associated with EHS trigger.";
                        }

                        leaf error-no-entry {
                            type yang:counter32;
                            description
                                "Indicates the number of ignored logger event occurrences associated
                                 with EHS trigger.

                                 Event is ignored due to no trigger entry configured for this trigger.";
                        }

                        leaf error-admin-state {
                            type yang:counter32;
                            description
                                "Indicates the number of ignored logger event occurrences associated
                                 with EHS trigger.

                                 Event is ignored due to trigger may be out-of-service.";
                        }

                        leaf total {
                            type yang:counter32;
                            description "Sum of success + error-no-entry + error-admin-state.";
                        }

                    } // container statistics

                    container summary-entry-statistics {
                        description "Enter the summary-entry-statistics context";

                        leaf filter-match {
                            type yang:counter32;
                            description "Indicates the number of times a filter matches an logger event.";
                        }

                        leaf filter-fail {
                            type yang:counter32;
                            description "Indicates the number of times a filter does not match an logger event.";
                        }

                        leaf error-admin-state {
                            type yang:counter32;
                            description
                                "Indicates the number of times the logger event will be ignored due to
                                 admin state of EHS trigger entries is out-of-service.";
                        }

                        leaf error-filter {
                            type yang:counter32;
                            description
                                "Indicates the number of times the logger event will be ignored due to filter
                                 is not operational or is not configured in EHS trigger entries.";
                        }

                        leaf error-handler {
                            type yang:counter32;
                            description
                                "Indicates the number of times the logger event will be ignored due to handler
                                 is not operational or is not configured in EHS trigger entries.";
                        }

                        leaf trigger-count {
                            type yang:counter32;
                            description "Indicates the number of times script execution is triggered after filter match.";
                        }

                        leaf debounce-count {
                            type yang:counter32;
                            description "Indicates the number of times script is not executed due to debounce rule.";
                        }

                    } // container summary-entry-statistics

                    list entry {
                        key "id";
                        description "Enter the entry list instance";

                        leaf id {
                            type uint32 {
                                range "1..1500";
                            }
                            description "ID of the EHS event trigger entry";
                        }

                        leaf oper-state {
                            type types-sros:oper-state;
                            description "Indicates the operational state of the EHS Event Trigger Entry.";
                        }

                        container statistics {
                            description "Enter the statistics context";

                            leaf filter-match {
                                type yang:counter32;
                                description
                                    "Indicates the number of times a filter, for the specified trigger entry,
                                     matches an logger event.";
                            }

                            leaf filter-fail {
                                type yang:counter32;
                                description
                                    "Indicates the number of times a filter, for the specified trigger entry,
                                     does not match an logger event.";
                            }

                            leaf error-admin-state {
                                type yang:counter32;
                                description
                                    "Indicates the number of times the logger event will be ignored due to
                                     admin state of EHS trigger entry is out-of-service.";
                            }

                            leaf error-filter {
                                type yang:counter32;
                                description
                                    "Indicates the number of times the logger event will be ignored due to filter
                                     is not operational or is not configured in EHS trigger entry.";
                            }

                            leaf error-handler {
                                type yang:counter32;
                                description
                                    "Indicates the number of times the logger event will be ignored due to handler
                                     is not operational or is not configured in EHS trigger entry.";
                            }

                            leaf trigger-count {
                                type yang:counter32;
                                description
                                    "Indicates the number of times script execution is triggered after filter match
                                     for the specified trigger entry.";
                            }

                            leaf debounce-count {
                                type yang:counter32;
                                description
                                    "Indicates the number of times script is not executed due to debounce rule
                                     for the specified trigger entry.";
                            }

                        } // container statistics

                    } // list entry

                } // list wpp

            } // container event-trigger

            list file {
                key "file-policy-name";
                description "Enter the file list instance";

                leaf file-policy-name {
                    type types-log:file-policy-name;
                    description "File ID for a log or accounting file";
                }

                leaf log-type {
                    type types-log:file-log-type;
                    description
                        "The value of log-type indicates the type of information
                         that will be written to this file.";
                }

                leaf used-by {
                    status obsolete;
                    type int32 {
                        range "0..99";
                    }
                    description
                        "The value of log-id indicates the ID of the log or
                         accounting policy this file is attached to.

                         A value of zero (0)
                         indicates that this file definition is not currently used by any
                         log or accounting policy.";
                }

                leaf creation-time {
                    type yang:date-and-time;
                    description
                        "The value of creation-time is the time the currently opened
                         file version used by this file-id entry was created.

                         The value of creation-time is affected by the value of
                         stiPreferLocalTime.";
                }

                leaf current-file-name {
                    type types-sros:named-item-255;
                    description
                        "The value of path-name is the path name of the currently
                         opened file used by this file-id entry.

                         The value of path-name is affected by the value of
                         stiPreferLocalTime.";
                }

                leaf oper-location {
                    type types-log:compact-flash-drive;
                    description "Specify the location for a log file.";
                }

                list associated-files {
                    key "file-name";
                    description "Enter the associated-files list instance";

                    leaf file-name {
                        type string {
                            length "0..255";
                        }
                        description "The complete pathname of the file associated with the log ID.";
                    }

                    leaf expired {
                        type enumeration {
                            enum "yes"                          { value 1; }
                            enum "no"                           { value 2; }
                        }
                        description
                            "Indicates whether or not the retention period for this file has
                             passed.";
                    }

                    leaf state {
                        type enumeration {
                            enum "complete"                     { value 1; }
                            enum "in-progress"                  { value 2; }
                        }
                        description "Indicates the current open or old log file.";
                    }

                } // list associated-files

            } // list file

            list filter {
                key "filter-name";
                description "Enter the filter list instance";

                leaf filter-name {
                    type types-log:log-filter-name;
                    description "Filter name";
                }

                leaf applied {
                    type boolean;
                    description
                        "If 'true', this filter is attached to a log file configuration.
                         The same entry can be attached to more than one log file.";
                }

            } // list filter

            list log-id {
                key "name";
                description "Enter the log-id list instance";

                leaf name {
                    type types-log:log-name;
                    description "Log ID";
                }

                leaf oper-state {
                    type types-sros:oper-state;
                    description "Operational state.";
                }

                leaf wrapped {
                    type boolean;
                    description "The sequence-number for this log has wrapped.";
                }

                leaf next-event {
                    type yang:counter64;
                    description
                        "The sequence-number that will be used for the next log event
                         in this event log.";
                }

                container statistics {
                    description "Enter the statistics context";

                    leaf logged-events {
                        type yang:counter64;
                        description
                            "The value of the this object is the count of the number
                             of events that have been forwarded to this logs's destination.";
                    }

                    leaf dropped-events {
                        type yang:counter64;
                        description
                            "The value of the this object is the count of the number
                             of events that have been sent to this logs source(s) and
                             that have not been forwarded to the log destination because
                             they were filtered out by the log filter.";
                    }

                } // container statistics

                list event {
                    key "sequence-number";
                    description "Enter the event list instance";

                    leaf sequence-number {
                        type uint64;
                        description
                            "A sequence number to indicate the ordering of log events in the log-id.
                             If the event is replayed, the sequence number is replayed as well.";
                    }

                    leaf time {
                        type yang:date-and-time;
                        description "Time when the event was generated.";
                    }

                    leaf severity {
                        type types-log:severity-level;
                        description "The severity level of the log event.";
                    }

                    leaf application {
                        type types-log:application-state;
                        description "The name of the application that reports the log event.";
                    }

                    leaf event-id {
                        type uint32 {
                            range "1..max";
                        }
                        description
                            "The id the event that was generated.
                             Each log event type has a unique identifying number.  This number is
                             unique within a particular software application, such as IP, MPLS,
                             OSPF, etc. but it is not necessarily unique across different software
                             applications.  That is MPLS event #1001 may be different from OSPF
                             event #1001.";
                    }

                    leaf event-name {
                        type types-sros:named-item;
                        description "The name of the log event that was generated.";
                    }

                    leaf vrtr-name {
                        type types-log:vrtr-name;
                        description "The router context name that generated the log event.";
                    }

                    leaf subject {
                        type string {
                            length "0..32";
                        }
                        description
                            "The router context name that generated the log event.
                             The subject is the entity that originated the event, such as the Port ID.";
                    }

                    leaf message {
                        type string {
                            length "1..4100";
                        }
                        description "The log event message.";
                    }

                } // list event

            } // list log-id

            list snmp-trap-group {
                key "log-name";
                description "Enter the snmp-trap-group list instance";

                leaf log-name {
                    type types-log:snmp-trap-group-name;
                    description "Log ID";
                }

                list trap-target {
                    key "name";
                    description "Enter the trap-target list instance";

                    leaf name {
                        type string {
                            length "1..28";
                        }
                        description "Trap target name";
                    }

                    leaf replay-start-id {
                        type uint32;
                        description
                            "Indicates the SNMP notification request ID of the first event
                             that could not be generated because there is no route to this
                              notification target address.";
                    }

                    leaf last-replay-time {
                        type yang:date-and-time;
                        description
                            "Indicates the time when missed events were last replayed
                             to this SNMP notification target address.";
                    }

                } // list trap-target

            } // list snmp-trap-group

            list syslog {
                key "syslog-name";
                description "Enter the syslog list instance";

                leaf syslog-name {
                    type types-log:log-syslog-name;
                    description "Syslog name";
                }

                leaf below-severity-drops {
                    type yang:counter32;
                    description
                        "Identifies the count of messages not sent to this syslog collector
                         target because the severity level of the message was above the configured level.";
                }

            } // list syslog

            container cli-log-subscriptions {
                description "Enter the cli-log-subscriptions context";

                list cli-log-subscribed-session {
                    key "session-id";
                    description "Enter the cli-log-subscribed-session list instance";

                    leaf session-id {
                        type uint32;
                        description "The id of the CLI session.";
                    }

                    leaf connection-type {
                        type enumeration {
                            enum "telnet"                       { value 1; }
                            enum "console"                      { value 2; }
                            enum "ssh"                          { value 4; }
                        }
                        description "The type of the connection used for the cli session.";
                    }

                    leaf connection-ip {
                        type types-sros:ip-address;
                        description "The remote IP address of the connection used for the cli session.";
                    }

                    leaf user {
                        type types-sros:named-item;
                        description "Name of the user.";
                    }

                    leaf login-time {
                        type yang:date-and-time;
                        description "The time the user logged in and created the CLI session.";
                    }

                    list subscription {
                        key "id";
                        description "Enter the subscription list instance";

                        leaf id {
                            type int32 {
                                range "1..101";
                            }
                            description "The value of id uniquely identifies an event stream log.";
                        }

                    } // list subscription

                } // list cli-log-subscribed-session

            } // container cli-log-subscriptions

        } // container log

    } // grouping state-log

}
