submodule nokia-state-system-security-pki {

    yang-version "1.1";

    belongs-to nokia-state { prefix "state"; }

    import ietf-yang-types                { prefix "yang"; }
    import nokia-sros-yang-extensions     { prefix "sros-ext"; }
    import nokia-types-security           { prefix "types-security"; }
    import nokia-types-sros               { prefix "types-sros"; }


    sros-ext:sros-major-release "rel23";

    organization "Nokia";

    contact
        "Nokia SR OS Support
         Web: <http://www.nokia.com>";

    description
        "Nokia YANG Data model with operational state for system security pki parameters. on SR OS based routers.

         Copyright 2016 Nokia. All rights reserved. Reproduction of this document
         is authorized on the condition that the foregoing copyright notice is included.

         This nokia-state-system-security-pki YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";

    revision "2022-12-07";

    grouping state-system-security-pki {
        container pki {
            description "Enter the pki context";

            container statistics {
                description "Enter the statistics context";

                container authentication {
                    description "Enter the authentication context";

                    leaf failed {
                        type yang:counter32;
                        description "The number of authentication failures using the certificates.";
                    }

                    leaf passed {
                        type yang:counter32;
                        description "The number of authentication checks passed using the certificates.";
                    }

                    leaf attempted {
                        type yang:counter32;
                        description "The number of authentication attempts using the certificates.";
                    }

                } // container authentication

            } // container statistics

            list ca-profile {
                key "ca-profile-name";
                description "Enter the ca-profile list instance";

                leaf ca-profile-name {
                    type types-sros:named-item;
                    description "CA profile name";
                }

                leaf oper-state {
                    type types-sros:oper-state;
                    description "Operational state of the CA profile.";
                }

                leaf oper-flags {
                    type bits {
                        bit adminDown                      { position 0; }
                        bit invalid-crl                    { position 1; }
                        bit invalid-cert                   { position 2; }
                        bit invalid-cmpv2-signing-cert     { position 3; }
                        bit expired-crl                    { position 4; }
                        bit expired-cert                   { position 5; }
                        bit expired-cmpv2-signing-cert     { position 6; }
                        bit not-yet-valid-crl              { position 7; }
                        bit not-yet-valid-cert             { position 8; }
                        bit not-yet-valid-cmpv2-signing-cert { position 9; }
                        bit loading-crl                    { position 10; }
                        bit loading-cert                   { position 11; }
                        bit loading-cmpv2-signing-cert     { position 12; }
                    }
                    description "Reason why the CA profile is not in service.";
                }

                container cmpv2 {
                    description "Enter the cmpv2 context";

                    container request {
                        description "Enter the request context";

                        leaf request-start-time {
                            type yang:date-and-time;
                            description "Time when request started";
                        }

                        leaf last-ca-response-time {
                            type yang:date-and-time;
                            description "Time when CA last response";
                        }

                        leaf transaction-status {
                            type types-security:cmpv2-transaction-status;
                            description "CMPv2 transaction status";
                        }

                        leaf transaction-status-code {
                            type types-security:cmpv2-transaction-status-code;
                            description "CMPv2 transaction status code";
                        }

                        leaf transaction-status-string {
                            type string {
                                length "1..255";
                            }
                            description "CMPv2 transaction extra status info";
                        }

                        container request-parameters {
                            description "Enter the request-parameters context";

                            leaf request-type {
                                type types-security:cmpv2-request-type;
                                description "CMPv2 request type";
                            }

                            leaf key-filename {
                                type types-security:pki-file-name;
                                description "The name of the key file used in cmpv2 request";
                            }

                            leaf new-key-filename {
                                type types-security:pki-file-name;
                                description "The name of the new key file used in cmpv2 request";
                            }

                            leaf subject-dn {
                                type string {
                                    length "1..256";
                                }
                                description "Subject of the requesting certificate";
                            }

                            leaf domain-name {
                                type string {
                                    length "1..512";
                                }
                                description "FQDNs for the Subject Alternative Name";
                            }

                            leaf ip-address {
                                type types-sros:ip-address;
                                description "IP address for the Subject Alternative Name";
                            }

                            leaf save-as {
                                type types-sros:cflash-url;
                                description "Path to result certificate file";
                            }

                            choice protection-algorithm {
                                case password {

                                    leaf reference {
                                        type string {
                                            length "1..64";
                                        }
                                        description "Password reference number";
                                    }

                                }
                                case signature {

                                    leaf certificate {
                                        type types-security:pki-file-name;
                                        description "Filename of the certificate for protection key";
                                    }

                                    leaf send-chain {
                                        type boolean;
                                        description "Send certificate chain";
                                    }

                                    leaf send-chain-ca {
                                        type string {
                                            length "1..32";
                                        }
                                        description "Name of the ca-profile whose certificate to be included in the chain";
                                    }

                                    leaf protection-key {
                                        type types-security:pki-file-name;
                                        description "Protection key filename";
                                    }

                                    leaf hash-algorithm {
                                        type types-security:hash-algorithm;
                                        description "The hash algorithm used for certificate signature";
                                    }

                                }
                            }
                        } // container request-parameters

                    } // container request

                } // container cmpv2

                container auto-crl-update {
                    description "Enter the auto-crl-update context";

                    leaf last-success-auto-crl-update-url-id {
                        type union {
                            type uint32 {
                                range "1..8";
                            }
                            type enumeration {
                                enum "not-applicable"               { value 0; }
                            }
                        }
                        description "URL entry ID of the last successful automated CRL update.";
                    }

                    leaf last-success-auto-crl-update-time-start {
                        type uint32;
                        units "seconds";
                        description
                            "Time at which the last successful automated CRL update
                             was initiated. It is measured from 1-Jan-1970 00:00:00 UTC.";
                    }

                    leaf last-success-auto-crl-update-time-end {
                        type uint32;
                        units "seconds";
                        description
                            "Time at which the last successful automated CRL update
                             was finished. It is measured from 1-Jan-1970 00:00:00 UTC.";
                    }

                    leaf next-scheduled-auto-crl-update-time {
                        type uint32;
                        units "seconds";
                        description
                            "Start time of the next scheduled update. It is measured
                             from 1-Jan-1970 00:00:00 UTC.";
                    }

                    container current-crl-update {
                        description "Enter the current-crl-update context";

                        leaf status {
                            type types-security:crl-update-status;
                            description "The CRL update status.";
                        }

                        leaf entry-id {
                            type uint32 {
                                range "1..8";
                            }
                            description "The url-entry which is being used in the current update for a CRL file.";
                        }

                        leaf start-time {
                            type yang:date-and-time;
                            description "The time at which the current automated CRL update was initiated.";
                        }

                        container last-failed-update {
                            description "Enter the last-failed-update context";

                            leaf start-time {
                                type yang:date-and-time;
                                description "The time at which the last failed automated CRL update was initiated.";
                            }

                            leaf end-time {
                                type yang:date-and-time;
                                description "The time at which the last failed automated CRL update was finished.";
                            }

                            leaf entry-id {
                                type uint32 {
                                    range "1..8";
                                }
                                description "The url-entry of the last failed automated CRL update.";
                            }

                            leaf cause {
                                type enumeration {
                                    enum "no-failure"                   { value 0; }
                                    enum "download-failed"              { value 1; }
                                    enum "invalid-crl"                  { value 2; }
                                }
                                description
                                    "The reason of the recent failed automated CRL update.

                                     noFailure      (0) -- The system never fails to update the CRL file
                                     downloadFailed (1) -- The system failed to download the CRL file
                                     invalidCRL     (2) -- The verification of the downloaded CRL file failed.";
                            }

                        } // container last-failed-update

                    } // container current-crl-update

                } // container auto-crl-update

            } // list ca-profile

            list certificate-auto-update {
                key "certificate-file-name";
                description "Enter the certificate-auto-update list instance";

                leaf certificate-file-name {
                    type types-security:pki-file-name;
                    description "Certificate file name";
                }

                leaf update-state {
                    type enumeration {
                        enum "invalid"                      { value 0; }
                        enum "scheduled"                    { value 1; }
                        enum "in-progress"                  { value 2; }
                        enum "wait-for-retry"               { value 3; }
                    }
                    description "State of certificate update.";
                }

                leaf last-update-start-time {
                    type yang:date-and-time;
                    description "Time when last update started";
                }

                leaf last-update-end-time {
                    type yang:date-and-time;
                    description "Time when last update ended";
                }

                leaf next-update-time {
                    type yang:date-and-time;
                    description "Time when last update ended";
                }

            } // list certificate-auto-update

        } // container pki

    } // grouping state-system-security-pki

}
