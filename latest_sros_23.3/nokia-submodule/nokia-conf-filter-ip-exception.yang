submodule nokia-conf-filter-ip-exception {

    yang-version "1.1";

    belongs-to nokia-conf { prefix "conf"; }

    import nokia-sros-yang-extensions     { prefix "sros-ext"; }
    import nokia-types-filter             { prefix "types-filter"; }
    import nokia-types-sros               { prefix "types-sros"; }

    include nokia-conf-filter;
    include nokia-conf-groups;


    sros-ext:sros-major-release "rel23";

    organization "Nokia";

    contact
        "Nokia SR OS Support
         Web: <http://www.nokia.com>";

    description
        "Nokia YANG Data model to configure IP exception filters on SR OS based routers.

         Copyright 2016 Nokia. All rights reserved. Reproduction of this document
         is authorized on the condition that the foregoing copyright notice is included.

         This nokia-conf-filter-ip-exception YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";

    revision "2022-09-29";

    grouping conf-filter-ip-exception {
        list ip-exception {
            key "filter-name";
            description "Enter the ip-exception list instance";

            leaf filter-name {
                type types-filter:filter-name;
                description "Filter name";
            }

            leaf description {
                type types-sros:description;
                description "Text description";
            }

            leaf filter-id {
                type types-filter:filter-id;
                sros-ext:immutable;
                description "Filter ID";
            }

            leaf-list apply-groups {
                type leafref {
                    path "../../../groups/group/name";
                }
                max-elements 8;
                ordered-by user;
                description "Apply a configuration group at this level";
            }

            leaf-list apply-groups-exclude {
                type leafref {
                    path "../../../groups/group/name";
                }
                max-elements 8;
                ordered-by user;
                description "Exclude a configuration group at this level";
            }

            list entry {
                key "entry-id";
                description "Enter the entry list instance";

                leaf entry-id {
                    type types-filter:entry-id;
                    description "ID for a match criteria and the corresponding action";
                }

                leaf description {
                    type types-sros:description;
                    description "Text description";
                }

                leaf-list apply-groups {
                    type leafref {
                        path "../../../../groups/group/name";
                    }
                    max-elements 8;
                    ordered-by user;
                    description "Apply a configuration group at this level";
                }

                leaf-list apply-groups-exclude {
                    type leafref {
                        path "../../../../groups/group/name";
                    }
                    max-elements 8;
                    ordered-by user;
                    description "Exclude a configuration group at this level";
                }

                container match {
                    description "Enter the match context";

                    leaf protocol {
                        type types-sros:match-ip-protocol;
                        description "IP protocol to match.";
                    }

                    choice port-selector {
                        case src-dst-port {

                            container src-port {
                                description "Enter the src-port context";

                                choice port {
                                    case eq {

                                        leaf eq {
                                            type uint16 {
                                                range "0..65535";
                                            }
                                            description "Exact match criterion";
                                        }

                                    }
                                    case lt {

                                        leaf lt {
                                            type uint16 {
                                                range "1..65535";
                                            }
                                            description "Condition on being less than the specified value.";
                                        }

                                    }
                                    case gt {

                                        leaf gt {
                                            type uint16 {
                                                range "0..65534";
                                            }
                                            description "Condition on being greater than the specified value.";
                                        }

                                    }
                                    case range {

                                        container range {
                                            presence "Enable the range context";
                                            description "Enter the range context";

                                            leaf start {
                                                type uint16 {
                                                    range "0..65534";
                                                }
                                                mandatory true;
                                                description "Lower bound of the port range to match";
                                            }

                                            leaf end {
                                                type uint16 {
                                                    range "1..65535";
                                                }
                                                mandatory true;
                                                description "Upper bound of the port range to match";
                                            }

                                        } // container range

                                    }
                                }
                            } // container src-port

                            container dst-port {
                                description "Enter the dst-port context";

                                choice port {
                                    case eq {

                                        leaf eq {
                                            type uint16 {
                                                range "0..65535";
                                            }
                                            description "Exact match criterion";
                                        }

                                    }
                                    case lt {

                                        leaf lt {
                                            type uint16 {
                                                range "1..65535";
                                            }
                                            description "Condition on being less than the specified value.";
                                        }

                                    }
                                    case gt {

                                        leaf gt {
                                            type uint16 {
                                                range "0..65534";
                                            }
                                            description "Condition on being greater than the specified value.";
                                        }

                                    }
                                    case range {

                                        container range {
                                            presence "Enable the range context";
                                            description "Enter the range context";

                                            leaf start {
                                                type uint16 {
                                                    range "0..65534";
                                                }
                                                mandatory true;
                                                description "Lower bound of the port range to match";
                                            }

                                            leaf end {
                                                type uint16 {
                                                    range "1..65535";
                                                }
                                                mandatory true;
                                                description "Upper bound of the port range to match";
                                            }

                                        } // container range

                                    }
                                }
                            } // container dst-port

                        }
                    }
                    container src-ip {
                        description "Enter the src-ip context";

                        choice match-address-choice {
                            case address-and-prefix-or-mask {

                                leaf address {
                                    type union {
                                        type types-sros:ipv4-prefix-with-host-bits;
                                        type types-sros:ipv4-address;
                                    }
                                    description "IP address to match";
                                }

                                leaf mask {
                                    type types-sros:ipv4-address;
                                    description "Mask applied as an AND to the IP address";
                                }

                            }
                        }
                    } // container src-ip

                    container dst-ip {
                        description "Enter the dst-ip context";

                        choice match-address-choice {
                            case address-and-prefix-or-mask {

                                leaf address {
                                    type union {
                                        type types-sros:ipv4-prefix-with-host-bits;
                                        type types-sros:ipv4-address;
                                    }
                                    description "IP address to match";
                                }

                                leaf mask {
                                    type types-sros:ipv4-address;
                                    description "Mask applied as an AND to the IP address";
                                }

                            }
                        }
                    } // container dst-ip

                    container icmp {
                        description "Enter the icmp context";

                        choice icmp-code {
                            case code {

                                leaf code {
                                    type types-filter:ipv4-match-icmp-codes;
                                    description "ICMP code value to match";
                                }

                            }
                        }
                        choice icmp-type {
                            case type {

                                leaf type {
                                    type types-filter:ipv4-match-icmp-types;
                                    description "ICMP type value to match";
                                }

                            }
                        }
                    } // container icmp

                } // container match

            } // list entry

        } // list ip-exception

    } // grouping conf-filter-ip-exception

    grouping conf-filter-ip-exception-ipv6-exception {
        list ipv6-exception {
            key "filter-name";
            description "Enter the ipv6-exception list instance";

            leaf filter-name {
                type types-filter:filter-name;
                description "Filter name";
            }

            leaf description {
                type types-sros:description;
                description "Text description";
            }

            leaf filter-id {
                type types-filter:filter-id;
                sros-ext:immutable;
                description "Filter ID";
            }

            leaf-list apply-groups {
                type leafref {
                    path "../../../groups/group/name";
                }
                max-elements 8;
                ordered-by user;
                description "Apply a configuration group at this level";
            }

            leaf-list apply-groups-exclude {
                type leafref {
                    path "../../../groups/group/name";
                }
                max-elements 8;
                ordered-by user;
                description "Exclude a configuration group at this level";
            }

            list entry {
                key "entry-id";
                description "Enter the entry list instance";

                leaf entry-id {
                    type types-filter:entry-id;
                    description "ID for a match criteria and the corresponding action";
                }

                leaf description {
                    type types-sros:description;
                    description "Text description";
                }

                leaf-list apply-groups {
                    type leafref {
                        path "../../../../groups/group/name";
                    }
                    max-elements 8;
                    ordered-by user;
                    description "Apply a configuration group at this level";
                }

                leaf-list apply-groups-exclude {
                    type leafref {
                        path "../../../../groups/group/name";
                    }
                    max-elements 8;
                    ordered-by user;
                    description "Exclude a configuration group at this level";
                }

                container match {
                    description "Enter the match context";

                    leaf next-header {
                        type types-sros:match-ip-protocol;
                        description "IP protocol to match";
                    }

                    choice port-selector {
                        case src-dst-port {

                            container src-port {
                                description "Enter the src-port context";

                                choice port {
                                    case eq {

                                        leaf eq {
                                            type uint16 {
                                                range "0..65535";
                                            }
                                            description "Exact match criterion for the port number";
                                        }

                                    }
                                    case lt {

                                        leaf lt {
                                            type uint16 {
                                                range "1..65535";
                                            }
                                            description "Less than match criterion for the port number";
                                        }

                                    }
                                    case gt {

                                        leaf gt {
                                            type uint16 {
                                                range "0..65534";
                                            }
                                            description "Greater than match criterion for the port number";
                                        }

                                    }
                                    case range {

                                        container range {
                                            presence "Enable the range context";
                                            description "Enter the range context";

                                            leaf start {
                                                type uint16 {
                                                    range "0..65534";
                                                }
                                                mandatory true;
                                                description "Lower bound of the port range as port match criterion";
                                            }

                                            leaf end {
                                                type uint16 {
                                                    range "1..65535";
                                                }
                                                mandatory true;
                                                description "Upper bound of the port range as port match criterion";
                                            }

                                        } // container range

                                    }
                                    case port-list {

                                        leaf port-list {
                                            type leafref {
                                                path "../../../../../match-list/port-list/port-list-name";
                                            }
                                            description "Name of the port list as the match criterion";
                                        }

                                    }
                                }
                            } // container src-port

                            container dst-port {
                                description "Enter the dst-port context";

                                choice port {
                                    case eq {

                                        leaf eq {
                                            type uint16 {
                                                range "0..65535";
                                            }
                                            description "Exact match criterion for the port number";
                                        }

                                    }
                                    case lt {

                                        leaf lt {
                                            type uint16 {
                                                range "1..65535";
                                            }
                                            description "Less than match criterion for the port number";
                                        }

                                    }
                                    case gt {

                                        leaf gt {
                                            type uint16 {
                                                range "0..65534";
                                            }
                                            description "Greater than match criterion for the port number";
                                        }

                                    }
                                    case range {

                                        container range {
                                            presence "Enable the range context";
                                            description "Enter the range context";

                                            leaf start {
                                                type uint16 {
                                                    range "0..65534";
                                                }
                                                mandatory true;
                                                description "Lower bound of the port range as port match criterion";
                                            }

                                            leaf end {
                                                type uint16 {
                                                    range "1..65535";
                                                }
                                                mandatory true;
                                                description "Upper bound of the port range as port match criterion";
                                            }

                                        } // container range

                                    }
                                    case port-list {

                                        leaf port-list {
                                            type leafref {
                                                path "../../../../../match-list/port-list/port-list-name";
                                            }
                                            description "Name of the port list as the match criterion";
                                        }

                                    }
                                }
                            } // container dst-port

                        }
                        case port {

                            container port {
                                description "Enter the port context";

                                choice port {
                                    case eq {

                                        leaf eq {
                                            type uint16 {
                                                range "0..65535";
                                            }
                                            description "Exact match criterion for the port number";
                                        }

                                    }
                                    case lt {

                                        leaf lt {
                                            type uint16 {
                                                range "1..65535";
                                            }
                                            description "Less than match criterion for the port number";
                                        }

                                    }
                                    case gt {

                                        leaf gt {
                                            type uint16 {
                                                range "0..65534";
                                            }
                                            description "Greater than match criterion for the port number";
                                        }

                                    }
                                    case range {

                                        container range {
                                            presence "Enable the range context";
                                            description "Enter the range context";

                                            leaf start {
                                                type uint16 {
                                                    range "0..65534";
                                                }
                                                mandatory true;
                                                description "Lower bound of the port range as port match criterion";
                                            }

                                            leaf end {
                                                type uint16 {
                                                    range "1..65535";
                                                }
                                                mandatory true;
                                                description "Upper bound of the port range as port match criterion";
                                            }

                                        } // container range

                                    }
                                    case port-list {

                                        leaf port-list {
                                            type leafref {
                                                path "../../../../../match-list/port-list/port-list-name";
                                            }
                                            description "Name of the port list as the match criterion";
                                        }

                                    }
                                }
                            } // container port

                        }
                    }
                    container src-ip {
                        description "Enter the src-ip context";

                        choice match-address-choice {
                            case address-and-prefix-or-mask {

                                leaf address {
                                    type union {
                                        type types-sros:ipv6-prefix-with-host-bits;
                                        type types-sros:ipv6-address;
                                    }
                                    description "IPv6 address used as the match criterion";
                                }

                                leaf mask {
                                    type types-sros:ipv6-address;
                                    description "IPv6 address mask used as the match criterion";
                                }

                            }
                            case ipv6-prefix-list {

                                leaf ipv6-prefix-list {
                                    type leafref {
                                        path "../../../../../match-list/ipv6-prefix-list/prefix-list-name";
                                    }
                                    description "IPv6 address prefix list used as match criterion";
                                }

                            }
                        }
                    } // container src-ip

                    container dst-ip {
                        description "Enter the dst-ip context";

                        choice match-address-choice {
                            case address-and-prefix-or-mask {

                                leaf address {
                                    type union {
                                        type types-sros:ipv6-prefix-with-host-bits;
                                        type types-sros:ipv6-address;
                                    }
                                    description "IPv6 address used as the match criterion";
                                }

                                leaf mask {
                                    type types-sros:ipv6-address;
                                    description "IPv6 address mask used as the match criterion";
                                }

                            }
                            case ipv6-prefix-list {

                                leaf ipv6-prefix-list {
                                    type leafref {
                                        path "../../../../../match-list/ipv6-prefix-list/prefix-list-name";
                                    }
                                    description "IPv6 address prefix list used as match criterion";
                                }

                            }
                        }
                    } // container dst-ip

                    container icmp {
                        description "Enter the icmp context";

                        choice icmp-code {
                            case code {

                                leaf code {
                                    type types-filter:ipv6-match-icmp-codes;
                                    description "ICMPv6 code value to match";
                                }

                            }
                        }
                        choice icmp-type {
                            case type {

                                leaf type {
                                    type types-filter:ipv6-match-icmp-types;
                                    description "ICMPv6 type value to match";
                                }

                            }
                        }
                    } // container icmp

                } // container match

            } // list entry

        } // list ipv6-exception

    } // grouping conf-filter-ip-exception-ipv6-exception

}
