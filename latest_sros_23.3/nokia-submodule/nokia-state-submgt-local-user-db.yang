submodule nokia-state-submgt-local-user-db {

    yang-version "1.1";

    belongs-to nokia-state { prefix "state"; }

    import nokia-sros-yang-extensions     { prefix "sros-ext"; }
    import nokia-types-sros               { prefix "types-sros"; }


    sros-ext:sros-major-release "rel23";

    organization "Nokia";

    contact
        "Nokia SR OS Support
         Web: <http://www.nokia.com>";

    description
        "Nokia YANG Data model with operational state for subscriber management local user database on SR OS based routers.

         Copyright 2016 Nokia. All rights reserved. Reproduction of this document
         is authorized on the condition that the foregoing copyright notice is included.

         This nokia-state-submgt-local-user-db YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";

    revision "2023-01-30";

    grouping state-submgt-local-user-db {
        list local-user-db {
            key "name";
            description "Enter the local-user-db list instance";

            leaf name {
                type types-sros:named-item;
                description "Local user database name";
            }

            leaf host-count {
                type uint32;
                description "The number of hosts configured in this local user database.";
            }

            leaf creation-origin {
                type types-sros:creation-origin;
                description "The mechanism which created this local user database.";
            }

            container ipoe {
                description "Enter the ipoe context";

                list host {
                    key "host-name";
                    description "Enter the host list instance";

                    leaf host-name {
                        type types-sros:named-item;
                        description "Host name";
                    }

                    container unmatched {
                        description "Enter the unmatched context";

                        leaf duplicate-host {
                            type types-sros:display-string {
                                length "1..32";
                            }
                            description
                                "The name of the host that is already matched and that has the
                                 same values, configured for the objects that correspond with
                                 the match types, as this unmatched host.";
                        }

                        leaf reason {
                            type enumeration {
                                enum "no-match-types"               { value 1; }
                                enum "duplicate"                    { value 2; }
                                enum "general-error"                { value 3; }
                                enum "overlap"                      { value 4; }
                                enum "limit-exceeded"               { value 5; }
                            }
                            description "The reason why this host is not matched.";
                        }

                    } // container unmatched

                } // list host

            } // container ipoe

            container ppp {
                description "Enter the ppp context";

                list host {
                    key "host-name";
                    description "Enter the host list instance";

                    leaf host-name {
                        type types-sros:named-item;
                        description "Host name";
                    }

                    container unmatched {
                        description "Enter the unmatched context";

                        leaf duplicate-host {
                            type types-sros:display-string {
                                length "1..32";
                            }
                            description
                                "The name of the host that is already matched and that has the
                                 same values, configured for the objects that correspond with
                                 the match types, as this unmatched host.";
                        }

                        leaf reason {
                            type enumeration {
                                enum "no-match-types"               { value 1; }
                                enum "duplicate"                    { value 2; }
                                enum "general-error"                { value 3; }
                                enum "overlap"                      { value 4; }
                                enum "limit-exceeded"               { value 5; }
                            }
                            description "The reason why this host is not matched.";
                        }

                    } // container unmatched

                } // list host

            } // container ppp

        } // list local-user-db

    } // grouping state-submgt-local-user-db

}
