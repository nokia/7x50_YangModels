module nokia-sr-openconfig-network-instance-l3-deviations {

    namespace "urn:nokia.com:sros:ns:yang:sr:openconfig-network-instance-l3-deviations";

    prefix "nokia-oc-ni-l3-devs";

    import nokia-sros-yang-extensions     { prefix "sros-ext"; }
    import openconfig-extensions          { prefix "oc-ext"; }
    import openconfig-network-instance    { prefix "oc-netinst"; }
    import openconfig-network-instance-l3 { prefix "oc-ni-l3"; }
    import openconfig-types               { prefix "oc-types"; }

    sros-ext:sros-major-release "rel23";

    organization "Nokia";

    contact
        "Nokia SR OS Support
         Web: <http://www.nokia.com>";

    description
        "This module contains the list of deviations against the openconfig-network-instance-l3
          module for the Nokia SR OS based routers.

         Copyright 2016 Nokia. All rights reserved. Reproduction of this document
         is authorized on the condition that the foregoing copyright notice is included.

         This nokia-sr-openconfig-network-instance-l3-deviations YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";

    revision "2018-11-21";

    deviation /oc-netinst:network-instances/oc-netinst:network-instance/oc-netinst:route-limits/oc-netinst:route-limit/oc-netinst:config/oc-netinst:afi {
        description "Address family must be IPV4 or IPV6.";
        deviate add {
            must ". = 'IPV4' or . = 'IPV6'";
        }
    }

    deviation /oc-netinst:network-instances/oc-netinst:network-instance/oc-netinst:route-limits/oc-netinst:route-limit/oc-netinst:config/oc-netinst:maximum {
        deviate replace {
            type uint32 {
                range 1..2147483647;
            }
        }
    }

    deviation /oc-netinst:network-instances/oc-netinst:network-instance/oc-netinst:route-limits/oc-netinst:route-limit/oc-netinst:config/oc-netinst:alarm-threshold {
        deviate replace {
            type uint32 {
                range 1..2147483647;
            }
        }
    }

    deviation /oc-netinst:network-instances/oc-netinst:network-instance/oc-netinst:route-limits/oc-netinst:route-limit/oc-netinst:state/oc-netinst:afi {
        description "Address family must be IPV4 or IPV6.";
        deviate add {
            must ". = 'IPV4' or . = 'IPV6'";
        }
    }

    deviation /oc-netinst:network-instances/oc-netinst:network-instance/oc-netinst:route-limits/oc-netinst:route-limit/oc-netinst:state/oc-netinst:maximum {
        deviate replace {
            type uint32 {
                range 1..2147483647;
            }
        }
    }

    deviation /oc-netinst:network-instances/oc-netinst:network-instance/oc-netinst:route-limits/oc-netinst:route-limit/oc-netinst:state/oc-netinst:alarm-threshold {
        deviate replace {
            type uint32 {
                range 1..2147483647;
            }
        }
    }

}
