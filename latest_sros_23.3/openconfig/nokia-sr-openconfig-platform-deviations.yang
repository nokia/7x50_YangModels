module nokia-sr-openconfig-platform-deviations {

    namespace "urn:nokia.com:sros:ns:yang:sr:openconfig-platform-deviations";

    prefix "nokia-oc-platform-devs";

    import nokia-sros-yang-extensions     { prefix "sros-ext"; }
    import openconfig-alarm-types         { prefix "oc-alarm-types"; }
    import openconfig-extensions          { prefix "oc-ext"; }
    import openconfig-platform            { prefix "oc-platform"; }
    import openconfig-platform-types      { prefix "oc-platform-types"; }
    import openconfig-types               { prefix "oc-types"; }
    import openconfig-yang-types          { prefix "oc-yang"; }

    sros-ext:sros-major-release "rel23";

    organization "Nokia";

    contact
        "Nokia SR OS Support
         Web: <http://www.nokia.com>";

    description
        "This module contains the list of deviations against the openconfig-platform
          module for the Nokia SR OS based routers.

         Copyright 2016 Nokia. All rights reserved. Reproduction of this document
         is authorized on the condition that the foregoing copyright notice is included.

         This nokia-sr-openconfig-platform-deviations YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";

    revision "2022-02-02";

    deviation /oc-platform:components/oc-platform:component/oc-platform:state/oc-platform:parent {
        deviate replace {
            type leafref {
                path ../../../component/state/name;
            }
        }
    }

    deviation /oc-platform:components/oc-platform:component/oc-platform:state/oc-platform:redundant-role {
        deviate not-supported;
    }

    deviation /oc-platform:components/oc-platform:component/oc-platform:state/oc-platform:last-switchover-reason {
        deviate not-supported;
    }

    deviation /oc-platform:components/oc-platform:component/oc-platform:state/oc-platform:last-switchover-time {
        deviate not-supported;
    }

    deviation /oc-platform:components/oc-platform:component/oc-platform:state/oc-platform:last-reboot-reason {
        deviate not-supported;
    }

    deviation /oc-platform:components/oc-platform:component/oc-platform:state/oc-platform:last-reboot-time {
        deviate not-supported;
    }

    deviation /oc-platform:components/oc-platform:component/oc-platform:state/oc-platform:temperature/oc-platform:avg {
        deviate not-supported;
    }

    deviation /oc-platform:components/oc-platform:component/oc-platform:state/oc-platform:temperature/oc-platform:min {
        deviate not-supported;
    }

    deviation /oc-platform:components/oc-platform:component/oc-platform:state/oc-platform:temperature/oc-platform:max {
        deviate not-supported;
    }

    deviation /oc-platform:components/oc-platform:component/oc-platform:state/oc-platform:temperature/oc-platform:interval {
        deviate not-supported;
    }

    deviation /oc-platform:components/oc-platform:component/oc-platform:state/oc-platform:temperature/oc-platform:min-time {
        deviate not-supported;
    }

    deviation /oc-platform:components/oc-platform:component/oc-platform:state/oc-platform:temperature/oc-platform:max-time {
        deviate not-supported;
    }

    deviation /oc-platform:components/oc-platform:component/oc-platform:state/oc-platform:temperature/oc-platform:alarm-status {
        deviate not-supported;
    }

    deviation /oc-platform:components/oc-platform:component/oc-platform:state/oc-platform:memory/oc-platform:utilized {
        deviate not-supported;
    }

    deviation /oc-platform:components/oc-platform:component/oc-platform:state/oc-platform:allocated-power {
        deviate not-supported;
    }

    deviation /oc-platform:components/oc-platform:component/oc-platform:state/oc-platform:used-power {
        deviate not-supported;
    }

    deviation /oc-platform:components/oc-platform:component/oc-platform:state/oc-platform:pcie {
        deviate not-supported;
    }

    deviation /oc-platform:components/oc-platform:component/oc-platform:properties/oc-platform:property/oc-platform:name {
        deviate replace {
            type leafref {
                path ../state/name;
            }
        }
    }

    deviation /oc-platform:components/oc-platform:component/oc-platform:properties/oc-platform:property/oc-platform:config {
        deviate not-supported;
    }

    deviation /oc-platform:components/oc-platform:component/oc-platform:properties {
        deviate replace {
            config false;
        }
    }

    deviation /oc-platform:components/oc-platform:component/oc-platform:subcomponents/oc-platform:subcomponent/oc-platform:name {
        deviate replace {
            type leafref {
                path ../state/name;
            }
        }
    }

    deviation /oc-platform:components/oc-platform:component/oc-platform:subcomponents/oc-platform:subcomponent/oc-platform:config {
        deviate not-supported;
    }

    deviation /oc-platform:components/oc-platform:component/oc-platform:subcomponents/oc-platform:subcomponent/oc-platform:state/oc-platform:name {
        deviate replace {
            type leafref {
                path ../../../../../component/state/name;
            }
        }
    }

    deviation /oc-platform:components/oc-platform:component/oc-platform:subcomponents {
        deviate replace {
            config false;
        }
    }

}
