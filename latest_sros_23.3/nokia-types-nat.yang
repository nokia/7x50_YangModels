module nokia-types-nat {

    yang-version "1.1";

    namespace "urn:nokia.com:sros:ns:yang:sr:types-nat";

    prefix "types-nat";

    import nokia-sros-yang-extensions     { prefix "sros-ext"; }

    sros-ext:sros-major-release "rel23";

    organization "Nokia";

    contact
        "Nokia SR OS Support
         Web: <http://www.nokia.com>";

    description
        "Common nat types data types used in the SR OS management system.

         Copyright 2016 Nokia. All rights reserved. Reproduction of this document
         is authorized on the condition that the foregoing copyright notice is included.

         This nokia-types-nat YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";

    revision "2018-12-04";

    typedef bb-group-member {
        type uint32;
        description
            "A logical entity that is actively participating in the ISA/ESA group.

             For active/active resiliency models this maps to a logical partition of an physical ISA/ESA
             For all other resiliency models this maps directly to a non-standby physical ISA/ESA.";
    }

    typedef deterministic-script-save-result {
        type enumeration {
            enum "none"                         { value 1; }
            enum "in-progress"                  { value 2; }
            enum "success"                      { value 3; }
            enum "failed"                       { value 4; }
        }
        description "Result of the last save action";
    }

    typedef syslog-facility {
        type enumeration {
            enum "kernel"                       { value 0; }
            enum "user"                         { value 1; }
            enum "mail"                         { value 2; }
            enum "systemd"                      { value 3; }
            enum "auth"                         { value 4; }
            enum "syslogd"                      { value 5; }
            enum "printer"                      { value 6; }
            enum "netnews"                      { value 7; }
            enum "uucp"                         { value 8; }
            enum "cron"                         { value 9; }
            enum "authpriv"                     { value 10; }
            enum "ftp"                          { value 11; }
            enum "ntp"                          { value 12; }
            enum "logaudit"                     { value 13; }
            enum "logalert"                     { value 14; }
            enum "cron2"                        { value 15; }
            enum "local0"                       { value 16; }
            enum "local1"                       { value 17; }
            enum "local2"                       { value 18; }
            enum "local3"                       { value 19; }
            enum "local4"                       { value 20; }
            enum "local5"                       { value 21; }
            enum "local6"                       { value 22; }
            enum "local7"                       { value 23; }
        }
        description "The 'Facility' number in the PRI part of the NAT syslog messages";
    }

    typedef syslog-severity-level {
        type enumeration {
            enum "emergency"                    { value 0; }
            enum "alert"                        { value 1; }
            enum "critical"                     { value 2; }
            enum "error"                        { value 3; }
            enum "warning"                      { value 4; }
            enum "notice"                       { value 5; }
            enum "info"                         { value 6; }
            enum "debug"                        { value 7; }
        }
        description "The severity level in the PRI part of the syslog messages";
    }

    typedef mac-format {
        type enumeration {
            enum "alu"                          { value 1; }
            enum "ieee"                         { value 2; }
        }
        default "alu";
        description
            "Specifies how to format a MAC address.

             The value 'alu' specifies the Nokia SROS style, xx:xx:xx:xx:xx:xx.
             The value 'ieee' specifies IEEE canonical style, xx-xx-xx-xx-xx-xx.";
    }

    typedef lsn-max-subscriber-limit {
        type uint32 {
            range "1 | 2 | 4 | 8 | 16 | 32 | 64 | 128 | 256 | 512 | 1024 | 2048 | 4096 | 8192 | 16384 | 32768";
        }
        description
            "Determines the length of the prefix on the inside that will
             be used for load balancing purposes between the MS-ISAs. The
             length of the prefix that will be used for load balancing
             purposes is (32-n), where 2^n = lsn-max-subscriber-limit.

             In deterministic NAT, is the largest value of all subscriber-limits
             configured in each deterministic pool that is used from inside routing
             context. In dNAT-only, this value can be set to any value from the specified
             range independent of the subscriber-limits.";
    }

    typedef classifier-default-action {
        type enumeration {
            enum "dnat"                         { value 0; }
            enum "forward"                      { value 1; }
        }
        default "dnat";
        description "Action to take";
    }

    typedef ip-protocol-tcp-or-udp {
        type enumeration {
            enum "tcp"                          { value 6; }
            enum "udp"                          { value 17; }
        }
        default "udp";
        description "IP protocol number";
    }

    typedef filtering {
        type enumeration {
            enum "endpoint-independent"         { value 0; }
            enum "address-and-port-dependent"   { value 2; }
        }
        default "endpoint-independent";
        description "The NAT filtering.";
    }

    typedef ip-fragmentation {
        type enumeration {
            enum "fragment-ipv6"                { value 1; }
            enum "fragment-ipv6-unless-ipv4-df-set" { value 2; }
        }
    }

    typedef sub-type {
        type enumeration {
            enum "undefined"                    { value 0; }
            enum "l2aware"                      { value 1; }
            enum "classic"                      { value 2; }
            enum "dslite"                       { value 3; }
            enum "nat64"                        { value 4; }
        }
        default "undefined";
    }

    typedef prefix-list-application {
        type enumeration {
            enum "l2-aware-dest-to-policy"      { value 1; }
            enum "dnat-only-subscribers"        { value 2; }
        }
        default "l2-aware-dest-to-policy";
        description
            "Specifies how the NAT prefix list is to be applied.

             The value 'l2-aware-dest-to-policy' specifies that the NAT prefix list will
             be applied to match destination IP addresses and find a NAT policy for Layer-2-Aware NAT.

             The value 'dnat-only-subscribers' specifies that the NAT prefix list will
             be applied to match source IP addresses of subscribers subjected
             to only Destination NAT (without Source Network Address and Port Translation);.";
    }

    typedef ipv6-subscriber-prefix-length {
        type uint8 {
            range "32..64|128";
        }
        default "128";
    }

    typedef nat-subscriber-identification-attr-vendor-id {
        type enumeration {
            enum "standard"                     { value 0; }
            enum "nokia"                        { value 6527; }
            enum "3gpp"                         { value 10415; }
        }
    }

    typedef nat-subscriber-identification-attr-type {
        type enumeration {
            enum "alc-sub-string"               { value 0; }
            enum "user-name"                    { value 1; }
            enum "class"                        { value 2; }
            enum "station-id"                   { value 3; }
            enum "imsi"                         { value 4; }
            enum "imei"                         { value 5; }
        }
    }

    typedef pool-type {
        type enumeration {
            enum "large-scale"                  { value 0; }
            enum "l2-aware"                     { value 1; }
            enum "wlan-gw-anchor"               { value 2; }
        }
    }

    typedef pool-mode {
        type enumeration {
            enum "auto"                         { value 0; }
            enum "napt"                         { value 1; }
            enum "one-to-one"                   { value 2; }
        }
    }

    typedef port-number {
        type uint32 {
            range "1..65536";
        }
    }

}
