module nokia-attributes {

    yang-version "1.1";

    namespace "urn:nokia.com:sros:ns:yang:sr:attributes";

    prefix "attr";

    import ietf-yang-metadata             { prefix "md"; }
    import nokia-sros-yang-extensions     { prefix "sros-ext"; }

    sros-ext:sros-major-release "rel23";

    organization "Nokia";

    contact
        "Nokia SR OS Support
         Web: <http://www.nokia.com>";


    revision "2021-02-18" {
        description "Initial revision.";
    }

    md:annotation comment {
        type string {
            length 1..2048;
        }
        description "Annotate a configuration element with a comment";
    }

}
