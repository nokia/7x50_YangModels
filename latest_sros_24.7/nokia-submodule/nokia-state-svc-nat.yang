submodule nokia-state-svc-nat {

    yang-version "1.1";

    belongs-to nokia-state { prefix "state"; }

    import ietf-yang-types                { prefix "yang"; }
    import nokia-sros-yang-extensions     { prefix "sros-ext"; }
    import nokia-types-isa                { prefix "types-isa"; }
    import nokia-types-nat                { prefix "types-nat"; }
    import nokia-types-services           { prefix "types-services"; }
    import nokia-types-sros               { prefix "types-sros"; }

    include nokia-state-esa;

    sros-ext:sros-major-release "rel24";
    organization "Nokia";
    contact
        "Nokia SR OS Support
         Web: <http://www.nokia.com>";
    description
        "Nokia YANG Data model with operational state for NAT configuration common to all router instances on SR OS based routers.

         Copyright 2016 Nokia. All rights reserved. Reproduction of this document
         is authorized on the condition that the foregoing copyright notice is included.

         This nokia-state-svc-nat YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";
    revision "2024-02-01";

    grouping state-svc-nat {
        container nat {
            description "Enter the nat context";

            list nat-policy {
                key "name";
                description "Enter the nat-policy list instance";

                leaf name {
                    type types-sros:external-named-item;
                    description "NAT policy name";
                }

                container statistics {
                    description "Enter the statistics context";

                    list mda {
                        key "mda-id";
                        description "Enter the mda list instance";

                        leaf mda-id {
                            type types-isa:slot-mda;
                            description "An ISA NAT group MDA";
                        }

                        container hosts {
                            description "Enter the hosts context";

                            leaf active {
                                type uint32;
                                description "Number of active hosts";
                            }

                            leaf peak {
                                type uint32;
                                description "Maximum number of hosts that were active together up to this point in time";
                            }

                        } // container hosts

                        container sessions {
                            description "Enter the sessions context";

                            container tcp {
                                description "Enter the tcp context";

                                leaf created {
                                    type uint32;
                                    description "Created TCP sessions";
                                }

                                leaf destroyed {
                                    type uint32;
                                    description "Destroyed TCP sessions";
                                }

                            } // container tcp

                            container udp {
                                description "Enter the udp context";

                                leaf created {
                                    type uint32;
                                    description "Created UDP sessions";
                                }

                                leaf destroyed {
                                    type uint32;
                                    description "Destroyed UDP sessions";
                                }

                            } // container udp

                            container icmp-query {
                                description "Enter the icmp-query context";

                                leaf created {
                                    type uint32;
                                    description "Created ICPM query sessions";
                                }

                                leaf destroyed {
                                    type uint32;
                                    description "Destroyed ICPM query sessions";
                                }

                            } // container icmp-query

                            container gre-query {
                                description "Enter the gre-query context";

                                leaf created {
                                    type uint32;
                                    description "Created GRE query sessions";
                                }

                                leaf destroyed {
                                    type uint32;
                                    description "Destroyed GRE query sessions";
                                }

                            } // container gre-query

                        } // container sessions

                    } // list mda

                    list esa {
                        key "esa-id vm";
                        description "Enter the esa list instance";

                        leaf esa-id {
                            type leafref {
                                path "../../../../../../esa/esa-id";
                            }
                            description "ESA used by the ISA NAT group";
                        }

                        leaf vm {
                            type leafref {
                                path "../../../../../../esa[esa-id=current()/../esa-id]/vm/vm-id";
                            }
                            description "ESA-VM used by the ISA NAT group";
                        }

                        container hosts {
                            description "Enter the hosts context";

                            leaf active {
                                type uint32;
                                description "Number of active hosts";
                            }

                            leaf peak {
                                type uint32;
                                description "Maximum number of hosts that were active together up to this point in time";
                            }

                        } // container hosts

                        container sessions {
                            description "Enter the sessions context";

                            container tcp {
                                description "Enter the tcp context";

                                leaf created {
                                    type uint32;
                                    description "Created TCP sessions";
                                }

                                leaf destroyed {
                                    type uint32;
                                    description "Destroyed TCP sessions";
                                }

                            } // container tcp

                            container udp {
                                description "Enter the udp context";

                                leaf created {
                                    type uint32;
                                    description "Created UDP sessions";
                                }

                                leaf destroyed {
                                    type uint32;
                                    description "Destroyed UDP sessions";
                                }

                            } // container udp

                            container icmp-query {
                                description "Enter the icmp-query context";

                                leaf created {
                                    type uint32;
                                    description "Created ICPM query sessions";
                                }

                                leaf destroyed {
                                    type uint32;
                                    description "Destroyed ICPM query sessions";
                                }

                            } // container icmp-query

                            container gre-query {
                                description "Enter the gre-query context";

                                leaf created {
                                    type uint32;
                                    description "Created GRE query sessions";
                                }

                                leaf destroyed {
                                    type uint32;
                                    description "Destroyed GRE query sessions";
                                }

                            } // container gre-query

                        } // container sessions

                    } // list esa

                } // container statistics

            } // list nat-policy

            container deterministic-script {
                description "Enter the deterministic-script context";

                leaf saved {
                    type boolean;
                    description
                        "Informs the operator whether the deterministic script for logging
                         purposes has been saved when deterministic NAT is configured

                         To preserve logging information, the script generated by deterministic NAT
                         that contains information about the deterministic mappings should be saved
                         locally on SR or on a remote server. The script is NOT saved automatically
                         and instead it should be explicitly saved by the operator.";
                }

                leaf last-save-result {
                    type types-nat:deterministic-script-save-result;
                    description "Result of the last save action";
                }

                leaf last-save-time {
                    type types-sros:date-time;
                    description "When the Deterministic script was last successfully saved";
                }

            } // container deterministic-script

            container map-t {
                description "Enter the map-t context";

                list domain {
                    key "name";
                    description "Enter the domain list instance";

                    leaf name {
                        type types-sros:named-item;
                        description "MAP domain name";
                    }

                    leaf service-name {
                        type types-services:service-name;
                        description "Routing context in which the domain is instantiated and active";
                    }

                    container statistics {
                        description "Enter the statistics context";

                        container upstream {
                            description "Enter the upstream context";

                            leaf fragments-rx {
                                type yang:counter64;
                                description "Number of fragmented packets received in the upstream direction";
                            }

                            leaf icmpv6-node-info-rx {
                                type yang:counter64;
                                description "Number of icmpv6 node information packets received in the upstream direction";
                            }

                            leaf cpe-icmpv6-error-reports-rx {
                                type yang:counter64;
                                description "Number of cpe generated icmpv6 error report packets received in the upstream direction";
                            }

                            leaf intermediate-icmpv6-error-rx {
                                type yang:counter64;
                                description "Number of intermediate node generated icmpv6 error report packets received in the upstream direction";
                            }

                            container dropped {
                                description "Enter the dropped context";

                                leaf total-packets {
                                    type yang:counter64;
                                    description "Number of packets dropped in the upstream direction";
                                }

                                leaf total-octets {
                                    type yang:counter64;
                                    description "Number of octets dropped in the upstream direction";
                                }

                                leaf unknown-protocol {
                                    type yang:counter64;
                                    description "Number of packets dropped in the upstream direction due to unknown protocol(not TCP/UDP/ICMP)";
                                }

                                leaf anti-spoof {
                                    type yang:counter64;
                                    description "Number of packets dropped in the upstream direction due to anti-spoof lookup failures";
                                }

                                leaf icmpv6 {
                                    type yang:counter64;
                                    description "Number of icmpv6 dropped packets in the upstream direction";
                                }

                                leaf other {
                                    type yang:counter64;
                                    description "Number of packets dropped in the upstream direction due to other reasons";
                                }

                            } // container dropped

                            container forwarded {
                                description "Enter the forwarded context";

                                leaf total-packets {
                                    type yang:counter64;
                                    description "Number of packets forwarded in the upstream direction";
                                }

                                leaf total-octets {
                                    type yang:counter64;
                                    description "Number of octets forwarded in the upstream direction";
                                }

                            } // container forwarded

                        } // container upstream

                        container downstream {
                            description "Enter the downstream context";

                            leaf fragments-rx {
                                type yang:counter64;
                                description "Number of fragmented packets received in the downstream direction";
                            }

                            leaf fragmentation-required {
                                type yang:counter64;
                                description "Number of packets with need-fragmentation received in the downstream direction";
                            }

                            leaf icmpv4-error-reports-rx {
                                type yang:counter64;
                                description "Number of icmpv4 error reports packets received in the downstream direction";
                            }

                            leaf icmpv4-echo-rx {
                                type yang:counter64;
                                description "Number of icmpv4 echo packets received in the downstream direction";
                            }

                            container dropped {
                                description "Enter the dropped context";

                                leaf total-packets {
                                    type yang:counter64;
                                    description "Number of packets dropped in the downstream direction";
                                }

                                leaf total-octets {
                                    type yang:counter64;
                                    description "Number of octets dropped in the downstream direction";
                                }

                                leaf unknown-protocol {
                                    type yang:counter64;
                                    description "Number of packets dropped in the downstream direction due to unknown protocol(not TCP/UDP/ICMP)";
                                }

                                leaf fragmentation-required {
                                    type yang:counter64;
                                    description "Number of packets dropped in the downstream direction due to fragmentation";
                                }

                                leaf icmpv4 {
                                    type yang:counter64;
                                    description "Number of icmpv4 packets dropped in the downstream direction";
                                }

                            } // container dropped

                            container forwarded {
                                description "Enter the forwarded context";

                                leaf total-packets {
                                    type yang:counter64;
                                    description "Number of packets forwarded in the downstream direction";
                                }

                                leaf total-octets {
                                    type yang:counter64;
                                    description "Number of octets forwarded in the downstream direction";
                                }

                            } // container forwarded

                        } // container downstream

                    } // container statistics

                    list mapping-rule {
                        key "rule-name";
                        description "Enter the mapping-rule list instance";

                        leaf rule-name {
                            type types-sros:named-item;
                            description "The name that identifies this mapping rule";
                        }

                        leaf address-sharing-ratio {
                            type yang:gauge32;
                            description
                                "Number of MAP Customer Edge (CE) sharing the same IP address.
                                 The value zero indicates that each CE is assigned its own IPv4 prefix.";
                        }

                        leaf excluded-ports {
                            type yang:gauge32;
                            description "Number of ports excluded from mapping with this rule";
                        }

                        leaf ports-per-user {
                            type yang:gauge32;
                            description "Number of ports available per MAP Customer Edge (CE)";
                        }

                        container statistics {
                            description "Enter the statistics context";

                            container upstream {
                                description "Enter the upstream context";

                                leaf fragments-rx {
                                    type yang:counter64;
                                    description "Number of fragmented packets received in the upstream direction";
                                }

                                leaf icmpv6-node-info-rx {
                                    type yang:counter64;
                                    description "Number of icmpv6 node information packets received in the upstream direction";
                                }

                                leaf cpe-icmpv6-error-reports-rx {
                                    type yang:counter64;
                                    description "Number of cpe generated icmpv6 error report packets received in the upstream direction";
                                }

                                leaf intermediate-icmpv6-error-rx {
                                    type yang:counter64;
                                    description "Number of intermediate node generated icmpv6 error report packets received in the upstream direction";
                                }

                                container dropped {
                                    description "Enter the dropped context";

                                    leaf total-packets {
                                        type yang:counter64;
                                        description "Number of packets dropped in the upstream direction";
                                    }

                                    leaf total-octets {
                                        type yang:counter64;
                                        description "Number of octets dropped in the upstream direction";
                                    }

                                    leaf unknown-protocol {
                                        type yang:counter64;
                                        description "Number of packets dropped in the upstream direction due to unknown protocol(not TCP/UDP/ICMP)";
                                    }

                                    leaf anti-spoof {
                                        type yang:counter64;
                                        description "Number of packets dropped in the upstream direction due to anti-spoof lookup failures";
                                    }

                                    leaf icmpv6 {
                                        type yang:counter64;
                                        description "Number of icmpv6 dropped packets in the upstream direction";
                                    }

                                    leaf other {
                                        type yang:counter64;
                                        description "Number of packets dropped in the upstream direction due to other reasons";
                                    }

                                } // container dropped

                                container forwarded {
                                    description "Enter the forwarded context";

                                    leaf total-packets {
                                        type yang:counter64;
                                        description "Number of packets forwarded in the upstream direction";
                                    }

                                    leaf total-octets {
                                        type yang:counter64;
                                        description "Number of octets forwarded in the upstream direction";
                                    }

                                } // container forwarded

                            } // container upstream

                            container downstream {
                                description "Enter the downstream context";

                                leaf fragments-rx {
                                    type yang:counter64;
                                    description "Number of fragmented packets received in the downstream direction";
                                }

                                leaf fragmentation-required {
                                    type yang:counter64;
                                    description "Number of packets with need-fragmentation received in the downstream direction";
                                }

                                leaf icmpv4-error-reports-rx {
                                    type yang:counter64;
                                    description "Number of icmpv4 error reports packets received in the downstream direction";
                                }

                                leaf icmpv4-echo-rx {
                                    type yang:counter64;
                                    description "Number of icmpv4 echo packets received in the downstream direction";
                                }

                                container dropped {
                                    description "Enter the dropped context";

                                    leaf total-packets {
                                        type yang:counter64;
                                        description "Number of packets dropped in the downstream direction";
                                    }

                                    leaf total-octets {
                                        type yang:counter64;
                                        description "Number of octets dropped in the downstream direction";
                                    }

                                    leaf unknown-protocol {
                                        type yang:counter64;
                                        description "Number of packets dropped in the downstream direction due to unknown protocol(not TCP/UDP/ICMP)";
                                    }

                                    leaf fragmentation-required {
                                        type yang:counter64;
                                        description "Number of packets dropped in the downstream direction due to fragmentation";
                                    }

                                    leaf icmpv4 {
                                        type yang:counter64;
                                        description "Number of icmpv4 packets dropped in the downstream direction";
                                    }

                                } // container dropped

                                container forwarded {
                                    description "Enter the forwarded context";

                                    leaf total-packets {
                                        type yang:counter64;
                                        description "Number of packets forwarded in the downstream direction";
                                    }

                                    leaf total-octets {
                                        type yang:counter64;
                                        description "Number of octets forwarded in the downstream direction";
                                    }

                                } // container forwarded

                            } // container downstream

                        } // container statistics

                    } // list mapping-rule

                } // list domain

                container statistics {
                    description "Enter the statistics context";

                    container fragmentation {
                        description "Enter the fragmentation context";

                        leaf rx-resolved {
                            type yang:counter64;
                            description "Fragments that are resolved without buffering";
                        }

                        leaf rx-unresolved {
                            type yang:counter64;
                            description
                                "Number of fragments that were queued in the system
                                 since the last clearing of the stats";
                        }

                        leaf tx-frags {
                            type yang:counter64;
                            description
                                "Number of fragments that were resolved and
                                 forwarded out of the fragmentation logic";
                        }

                        leaf dropped {
                            type yang:counter64;
                            description "Number of dropped fragments";
                        }

                        leaf created-flows {
                            type yang:counter64;
                            description
                                "Number of flow records created since the last
                                 clearing of the statistics. Flow record creation
                                 is triggered by the first fragment of a packet.";
                        }

                        leaf flow-collisions {
                            type yang:counter64;
                            description
                                "Number of flow collisions (overlapping first
                                 fragments) since the last clearing of the statistics";
                        }

                        leaf exceeded-max-flows {
                            type yang:counter64;
                            description "Number of times the maximum number of flows is exceeded";
                        }

                        leaf exceeded-max-timeouts {
                            type yang:counter64;
                            description
                                "Number of fragments that have timed out since the
                                 last clearing of the statistics";
                        }

                        leaf exceeded-max-buffers {
                            type yang:counter64;
                            description "Number of times the maximum number of buffers is exceeded";
                        }

                        leaf exceeded-max-buffers-per-flow {
                            type yang:counter64;
                            description
                                "Number of times a fragment count per flow has
                                 exceeded the maximum value";
                        }

                        leaf in-use-flows {
                            type types-sros:percent;
                            description "Percentage of currently processed flows (flow records)";
                        }

                        leaf max-flows {
                            type types-sros:percent;
                            description
                                "Maximum number of flows (flow records) reached
                                 since the last clearing of the statistics";
                        }

                        leaf in-use-buffers {
                            type types-sros:percent;
                            description "Percentage of in-use buffers";
                        }

                        leaf max-buffers {
                            type types-sros:percent;
                            description
                                "Maximum number of buffers allocated in the system
                                 since the last clearing of the statistics";
                        }

                    } // container fragmentation

                } // container statistics

            } // container map-t

            container statistics {
                description "Enter the statistics context";

                container dropped {
                    description "Enter the dropped context";

                    leaf radius-interim-updates {
                        type yang:counter64;
                        description
                            "The number of dropped RADIUS accounting interim update
                             messages generated by NAT";
                    }

                } // container dropped

            } // container statistics

        } // container nat

    } // grouping state-svc-nat

}
