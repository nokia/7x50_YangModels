submodule nokia-state-testoam-service-activation-testhead {

    yang-version "1.1";

    belongs-to nokia-state { prefix "state"; }

    import ietf-yang-types                { prefix "yang"; }
    import nokia-sros-yang-extensions     { prefix "sros-ext"; }
    import nokia-types-eth-cfm            { prefix "types-eth-cfm"; }
    import nokia-types-log                { prefix "types-log"; }
    import nokia-types-oam                { prefix "types-oam"; }
    import nokia-types-sros               { prefix "types-sros"; }

    include nokia-state-eth-cfm;

    sros-ext:sros-major-release "rel24";
    organization "Nokia";
    contact
        "Nokia SR OS Support
         Web: <http://www.nokia.com>";
    description
        "Nokia YANG Data model with operational state for OAM Service Activation Tests (Y.1564) on SR OS based routers.

         Copyright 2016 Nokia. All rights reserved. Reproduction of this document
         is authorized on the condition that the foregoing copyright notice is included.

         This nokia-state-testoam-service-activation-testhead YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";
    revision "2024-08-02";

    grouping state-testoam-service-activation-testhead {
        container service-activation-testhead {
            description "Enter the service-activation-testhead context";

            list service-test {
                key "test-name";
                description "Enter the service-test list instance";

                leaf test-name {
                    type types-sros:named-item-64;
                    description "Service activation test name";
                }

            } // list service-test

            container statistics {
                description "Enter the statistics context";

                list service-test {
                    key "test-name test-run";
                    description "Enter the service-test list instance";

                    leaf test-name {
                        type types-sros:named-item-64;
                        description "The name of the Service Activation Test";
                    }

                    leaf test-run {
                        type uint32 {
                            range "1..4294967295";
                        }
                        description "The run number of the OAM Service Activation service-test run to be read";
                    }

                    leaf description {
                        type types-sros:description;
                        description "Configure the description of the service test";
                    }

                    leaf accounting-policy {
                        type types-log:log-policy-id;
                        description "Configure the accounting policy, used to record results for the service test";
                    }

                    leaf oper-state {
                        type types-oam:sath-statistics-test-run-oper-state;
                        description "Indicates the operational state of the service-test run";
                    }

                    leaf accounting-oper-state {
                        type enumeration {
                            enum none                           { value 1; }
                            enum ready-to-send                  { value 2; }
                            enum sent                           { value 3; }
                            enum unable-to-send                 { value 4; }
                        }
                        description
                            "Indicates the operational status of the transfer of the service-test run's results
                             to the accounting log";
                    }

                    leaf time-start {
                        type types-oam:sath-test-time-start;
                        description "Indicates the start time of the specified service-test run";
                    }

                    leaf time-end {
                        type types-oam:sath-test-time-end;
                        description "Indicates the end time of the specified service-test run";
                    }

                    leaf service-test-completion-notification {
                        type boolean;
                        description "Enable SNMP trap generation upon test completion";
                    }

                    leaf stream-run-type {
                        type enumeration {
                            enum sequential                     { value 1; }
                            enum parallel                       { value 2; }
                        }
                        description "Service stream run order";
                    }

                    container test-duration {
                        description "Enter the test-duration context";

                        container cir {
                            description "Enter the cir context";

                            leaf minutes-seconds {
                                type types-oam:sath-mm-ss-string;
                                description "Duration of the service test CIR tests";
                            }

                        } // container cir

                        container cir-pir {
                            description "Enter the cir-pir context";

                            leaf minutes-seconds {
                                type types-oam:sath-mm-ss-string;
                                description "Duration of the service test CIR-PIR tests";
                            }

                        } // container cir-pir

                        container policing {
                            description "Enter the policing context";

                            leaf minutes-seconds {
                                type types-oam:sath-mm-ss-string;
                                description "Duration of policing tests belonging to the test";
                            }

                        } // container policing

                        container performance {
                            description "Enter the performance context";

                            leaf hours-minutes-seconds {
                                type types-oam:sath-hh-mm-ss-string;
                                description "Duration of performance tests belonging to the test";
                            }

                        } // container performance

                    } // container test-duration

                    list service-stream {
                        key "stream-id";
                        description "Enter the service-stream list instance";

                        leaf stream-id {
                            type uint32 {
                                range "1..8";
                            }
                            description "The number of the service stream to be configured or read";
                        }

                        leaf description {
                            type types-sros:description;
                            description "Configure the description of the service test";
                        }

                        leaf oper-state {
                            type types-oam:sath-statistics-test-run-oper-state;
                            description "Indicates the operational state of the service stream run";
                        }

                        leaf sap {
                            type string {
                                length "0..32";
                            }
                            description
                                "Indicates the Service Access Point (SAP) which hosts the Eth-CFM MEP, Domain, and
                                 Association configured for the service stream";
                        }

                        leaf router-instance {
                            type types-sros:named-item-or-empty;
                            description
                                "Indicates the router which hosts the Eth-CFM MEP, Domain, and
                                 Association configured for the service stream";
                        }

                        leaf router-interface {
                            type types-sros:named-item-or-empty;
                            description
                                "Indicates the router interface which hosts the Eth-CFM MEP, Domain, and
                                 Association configured for the service stream";
                        }

                        leaf source-port {
                            type types-sros:named-item-or-empty;
                            description
                                "Indicates the port which hosts the Eth-CFM MEP, Domain, and
                                 Association configured for the service stream";
                        }

                        leaf src-mac {
                            type yang:mac-address;
                            description
                                "Indicates the source MAC address for the service stream

                                 00:00:00:00:00:00 is returned if a source MAC address is not available";
                        }

                        leaf acceptance-criteria-template {
                            type types-sros:named-item-64;
                            description "Configure the acceptance criteria template for the service stream";
                        }

                        leaf rate-cir {
                            type uint32 {
                                range "0..400000000";
                            }
                            units "kilobps";
                            description "CIR packet transmit rate for the service stream";
                        }

                        leaf rate-pir {
                            type uint32 {
                                range "0..400000000";
                            }
                            units "kilobps";
                            description "PIR packet transmit rate for the service stream";
                        }

                        leaf service-stream-completion-notification {
                            type boolean;
                            description "Enable SNMP trap generation upon test completion";
                        }

                        leaf size-a {
                            type uint32 {
                                range "64..9212";
                            }
                            units "bytes";
                            description "Size-a";
                        }

                        leaf size-b {
                            type uint32 {
                                range "64..9212";
                            }
                            units "bytes";
                            description "Size-b";
                        }

                        leaf size-c {
                            type uint32 {
                                range "64..9212";
                            }
                            units "bytes";
                            description "Size-c";
                        }

                        leaf size-d {
                            type uint32 {
                                range "64..9212";
                            }
                            units "bytes";
                            description "Size-d";
                        }

                        leaf size-e {
                            type uint32 {
                                range "64..9212";
                            }
                            units "bytes";
                            description "Size-e";
                        }

                        leaf size-f {
                            type uint32 {
                                range "64..9212";
                            }
                            units "bytes";
                            description "Size-f";
                        }

                        leaf size-g {
                            type uint32 {
                                range "64..9212";
                            }
                            units "bytes";
                            description "Size-g";
                        }

                        leaf size-h {
                            type uint32 {
                                range "64..9212";
                            }
                            units "bytes";
                            description "Size-h";
                        }

                        leaf size-u {
                            type uint32 {
                                range "64..9212";
                            }
                            units "bytes";
                            description "Size-u";
                        }

                        leaf cir-threshold {
                            type uint32 {
                                range "0..400000000";
                            }
                            units "kilobps";
                            description
                                "Indicates the value of
                                 /test-oam/service-activation-testhead/acceptance-criteria-template/cir-threshold
                                 when the test run started";
                        }

                        leaf pir-threshold {
                            type uint32 {
                                range "0..400000000";
                            }
                            units "kilobps";
                            description
                                "Indicates the value of
                                 /test-oam/service-activation-testhead/acceptance-criteria-template/pir-threshold
                                 when the test run started";
                        }

                        leaf loss-threshold {
                            type types-oam:sath-loss-percent-union;
                            description
                                "Indicates the value of
                                 /test-oam/service-activation-testhead/acceptance-criteria-template/loss-threshold
                                 when the test run started";
                        }

                        leaf loss-threshold-policing {
                            type types-oam:sath-loss-percent-union;
                            description
                                "Indicates the value of
                                 /test-oam/service-activation-testhead/acceptance-criteria-template/loss-threshold-policing
                                 when the test run started";
                        }

                        leaf delay-threshold {
                            type uint32 {
                                range "0..100000000";
                            }
                            units "microseconds";
                            description
                                "Indicates the value of
                                 /test-oam/service-activation-testhead/acceptance-criteria-template/delay-threshold
                                 when the test run started";
                        }

                        leaf delay-var-threshold {
                            type uint32 {
                                range "0..100000000";
                            }
                            units "microseconds";
                            description
                                "Indicates the value of
                                 /test-oam/service-activation-testhead/acceptance-criteria-template/delay-var-threshold
                                 when the test run started";
                        }

                        leaf m-factor {
                            type uint32 {
                                range "0..400000000";
                            }
                            units "kilobps";
                            description
                                "Indicates the value of
                                 /test-oam/service-activation-testhead/acceptance-criteria-template/m-factor
                                 when the test run started";
                        }

                        container frame-mix {
                            description "Enter the frame-mix context";

                            leaf frame-size-template {
                                type types-sros:named-item-64;
                                description "Configure the frame size template for the service stream";
                            }

                            leaf sequence {
                                type string {
                                    length "1..16";
                                }
                                description "Configure the sequence of frame sizes for the service stream";
                            }

                        } // container frame-mix

                        container test-types {
                            description "Enter the test-types context";

                            leaf cir {
                                type boolean;
                                description "CIR test for the service stream";
                            }

                            leaf cir-pir {
                                type boolean;
                                description "CIR-PIR test for the service stream";
                            }

                            leaf policing {
                                type boolean;
                                description "Policing test for the service stream";
                            }

                            leaf performance {
                                type boolean;
                                description "Performance test for the service stream";
                            }

                        } // container test-types

                        container frame-payload {
                            description "Enter the frame-payload context";

                            container data-pattern {
                                description "Enter the data-pattern context";

                                leaf repeat {
                                    type types-sros:hex-string-or-uint;
                                    description "Repeated 4-byte pattern to pad each packet sent";
                                }

                            } // container data-pattern

                            container ethernet {
                                description "Enter the ethernet context";

                                leaf dst-mac {
                                    type types-sros:mac-unicast-address-no-zero;
                                    description "Destination MAC address of Ethernet frames";
                                }

                                container eth-cfm {
                                    description "Enter the eth-cfm context";

                                    container source {
                                        description "Enter the source context";

                                        leaf mep-id {
                                            type types-eth-cfm:mep-id-type;
                                            description "Source Ethernet maintenance association end point";
                                        }

                                        leaf md-admin-name {
                                            type leafref {
                                                path "../../../../../../../../../../eth-cfm/domain/md-admin-name";
                                            }
                                            description "Source Ethernet maintenance domain name";
                                        }

                                        leaf ma-admin-name {
                                            type leafref {
                                                path "../../../../../../../../../../eth-cfm/domain[md-admin-name=current()/../md-admin-name]/association/ma-admin-name";
                                            }
                                            description "Source Ethernet maintenance association name";
                                        }

                                    } // container source

                                } // container eth-cfm

                                container s-tag {
                                    description "Enter the s-tag context";

                                    leaf dot1p {
                                        type uint32 {
                                            range "0..7";
                                        }
                                        description "PCP of Ethernet frames for service stream";
                                    }

                                    leaf discard-eligible {
                                        type boolean;
                                        description "Enable marking of the DEI bit in the VLAN header";
                                    }

                                } // container s-tag

                                container c-tag {
                                    description "Enter the c-tag context";

                                    leaf dot1p {
                                        type uint32 {
                                            range "0..7";
                                        }
                                        description "PCP of Ethernet frames for service stream";
                                    }

                                    leaf discard-eligible {
                                        type boolean;
                                        description "Enable marking of the DEI bit in the VLAN header";
                                    }

                                } // container c-tag

                            } // container ethernet

                        } // container frame-payload

                        list test-results {
                            key "test-type";
                            description "Enter the test-results list instance";

                            leaf test-type {
                                type enumeration {
                                    enum cir                            { value 1; }
                                    enum cir-pir                        { value 2; }
                                    enum policing                       { value 3; }
                                    enum performance                    { value 4; }
                                }
                                description "The test type to be read";
                            }

                            leaf oper-state {
                                type types-oam:sath-statistics-test-run-oper-state;
                                description "Indicates the operational state of the test run";
                            }

                            leaf time-start {
                                type types-oam:sath-test-time-start;
                                description "Indicates the start time of the test run";
                            }

                            leaf time-end {
                                type types-oam:sath-test-time-end;
                                description "Indicates the end time of the test run";
                            }

                            leaf time-left {
                                type uint32;
                                units "seconds";
                                description "Indicates the execution time remaining for the test run";
                            }

                            leaf oper-status-throughput {
                                type types-oam:sath-statistics-test-oper-state;
                                description
                                    "Indicates the test run's operational status, with respect to the throughput
                                     acceptance criteria";
                            }

                            leaf oper-status-frame-loss-ratio {
                                type types-oam:sath-statistics-test-oper-state;
                                description
                                    "Indicates the test run's operational status, with respect to the FLR acceptance
                                     criteria";
                            }

                            leaf oper-status-delay {
                                type types-oam:sath-statistics-test-oper-state;
                                description
                                    "Indicates the test run's operational status, with respect to the delay acceptance
                                     criteria";
                            }

                            leaf oper-status-delay-var {
                                type types-oam:sath-statistics-test-oper-state;
                                description
                                    "Indicates the test run's operational status, with respect to the delay variation
                                     acceptance criteria";
                            }

                            leaf measured-delay-min {
                                type int32;
                                units "microseconds";
                                description "Indicates the minimum delay measured for the test run";
                            }

                            leaf measured-delay-max {
                                type int32;
                                units "microseconds";
                                description "Indicates the maximum delay measured for the test run";
                            }

                            leaf measured-delay-avg {
                                type int32;
                                units "microseconds";
                                description "Indicates the average delay measured for the test run";
                            }

                            leaf measured-delay-var-min {
                                type int32;
                                units "microseconds";
                                description "Indicates the minimum delay variation measured for the test run";
                            }

                            leaf measured-delay-var-max {
                                type int32;
                                units "microseconds";
                                description "Indicates the maximum delay variation measured for the test run";
                            }

                            leaf measured-delay-var-avg {
                                type int32;
                                units "microseconds";
                                description "Indicates the average delay variation measured for the test run";
                            }

                            leaf measured-throughput {
                                type uint32;
                                units "kilobps";
                                description "Indicates the measured throughput for the test run";
                            }

                            leaf measured-frame-loss-ratio {
                                type types-oam:sath-loss-percent-decimal64;
                                units "percent";
                                description "Indicates the measured FLR for the test run";
                            }

                            leaf measured-frame-tx {
                                type yang:counter64;
                                units "frames";
                                description "Indicates the number of frames transmitted during the test run";
                            }

                            leaf measured-frame-rx {
                                type yang:counter64;
                                units "frames";
                                description "Indicates the number of frames received during the test run";
                            }

                        } // list test-results

                    } // list service-stream

                } // list service-test

            } // container statistics

        } // container service-activation-testhead

    } // grouping state-testoam-service-activation-testhead

}
