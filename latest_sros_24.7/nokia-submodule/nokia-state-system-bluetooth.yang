submodule nokia-state-system-bluetooth {

    yang-version "1.1";

    belongs-to nokia-state { prefix "state"; }

    import ietf-yang-types                { prefix "yang"; }
    import nokia-sros-yang-extensions     { prefix "sros-ext"; }
    import nokia-types-card               { prefix "types-card"; }
    import nokia-types-sros               { prefix "types-sros"; }

    sros-ext:sros-major-release "rel24";
    organization "Nokia";
    contact
        "Nokia SR OS Support
         Web: <http://www.nokia.com>";
    description
        "Nokia YANG Data model with operational state for system bluetooth on SR OS based routers.

         Copyright 2016 Nokia. All rights reserved. Reproduction of this document
         is authorized on the condition that the foregoing copyright notice is included.

         This nokia-state-system-bluetooth YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";
    revision "2020-09-16";

    grouping state-system-bluetooth {
        container bluetooth {
            description "Enter the bluetooth context";

            list module {
                key "cpm-slot";
                description "Enter the module list instance";

                leaf cpm-slot {
                    type types-card:cpm-card-slot;
                    description "CPM slot on which the module resides";
                }

                leaf identifier {
                    type types-sros:display-string {
                        length "1..32";
                    }
                    description "The identifier to be used for broadcasting the module.";
                }

                leaf remote-device-connection {
                    type boolean;
                    description
                        "Whether a remote client Bluetooth device is currently connected with
                         this Bluetooth module.";
                }

                leaf remote-device-mac-address {
                    type yang:mac-address;
                    description "The remote client Bluetooth device MAC address, if connection exists.";
                }

            } // list module

        } // container bluetooth

    } // grouping state-system-bluetooth

}
