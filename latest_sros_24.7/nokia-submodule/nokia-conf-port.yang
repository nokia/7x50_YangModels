submodule nokia-conf-port {

    yang-version "1.1";

    belongs-to nokia-conf { prefix "conf"; }

    import nokia-sros-yang-extensions     { prefix "sros-ext"; }
    import nokia-types-qos                { prefix "types-qos"; }
    import nokia-types-services           { prefix "types-services"; }
    import nokia-types-sros               { prefix "types-sros"; }

    include nokia-conf-groups;
    include nokia-conf-port-access;
    include nokia-conf-port-connector;
    include nokia-conf-port-dwdm;
    include nokia-conf-port-ethernet;
    include nokia-conf-port-gnss;
    include nokia-conf-port-network;
    include nokia-conf-port-otu;
    include nokia-conf-port-sonet;
    include nokia-conf-port-tdm;
    include nokia-conf-qos;
    include nokia-conf-service;
    include nokia-conf-system;
    include nokia-conf-system-security;

    sros-ext:sros-major-release "rel24";
    organization "Nokia";
    contact
        "Nokia SR OS Support
         Web: <http://www.nokia.com>";
    description
        "Nokia YANG Data model to configure physical ports on SR OS based routers.

         Copyright 2016 Nokia. All rights reserved. Reproduction of this document
         is authorized on the condition that the foregoing copyright notice is included.

         This nokia-conf-port YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";
    revision "2024-08-21";

    grouping conf-port {
        list port {
            key "port-id";
            description "Enter the port list instance";

            leaf port-id {
                type types-sros:port;
                description "Port ID";
            }

            leaf admin-state {
                type types-sros:admin-state;
                description "Administrative state of the port";
            }

            leaf description {
                type types-sros:very-long-description;
                description "Text description";
            }

            leaf ddm-events {
                type boolean;
                default "true";
                description "Enable Digital Diagnostic Monitoring (DDM) events";
            }

            leaf monitor-agg-egress-queue-stats {
                type boolean;
                default "false";
                description "Monitor aggregate queue statistics";
            }

            leaf oper-group {
                type leafref {
                    path "../../service/oper-group/name";
                }
                description "Operational group ID";
            }

            leaf monitor-oper-group {
                type leafref {
                    path "../../service/oper-group/name";
                }
                description "Operational group to monitor";
            }

            leaf-list apply-groups {
                type leafref {
                    path "../../groups/group/name";
                }
                max-elements 8;
                ordered-by user;
                description "Apply a configuration group at this level";
            }

            leaf-list apply-groups-exclude {
                type leafref {
                    path "../../groups/group/name";
                }
                max-elements 8;
                ordered-by user;
                description "Exclude a configuration group at this level";
            }

            container dist-cpu-protection {
                description "Enter the dist-cpu-protection context";

                leaf policy {
                    type leafref {
                        path "../../../system/security/dist-cpu-protection/policy/policy-name";
                    }
                    description "Distributed CPU protection policy name";
                }

            } // container dist-cpu-protection

            container hybrid-buffer-allocation {
                description "Enter the hybrid-buffer-allocation context";

                container egress-weight {
                    description "Enter the egress-weight context";

                    leaf access {
                        type uint32 {
                            range "0..100";
                        }
                        default "50";
                        description "Access weight for the hybrid port";
                    }

                    leaf network {
                        type uint32 {
                            range "0..100";
                        }
                        default "50";
                        description "Access weight for the hybrid port";
                    }

                } // container egress-weight

                container ingress-weight {
                    description "Enter the ingress-weight context";

                    leaf access {
                        type uint32 {
                            range "0..100";
                        }
                        default "50";
                        description "Access weight for the hybrid port";
                    }

                    leaf network {
                        type uint32 {
                            range "0..100";
                        }
                        default "50";
                        description "Access weight for the hybrid port";
                    }

                } // container ingress-weight

            } // container hybrid-buffer-allocation

            container modify-buffer-allocation {
                description "Enter the modify-buffer-allocation context";

                container percentage-of-rate {
                    description "Enter the percentage-of-rate context";

                    leaf egress {
                        type uint32 {
                            range "1..1000";
                        }
                        description "Egress rate percentage";
                    }

                    leaf ingress {
                        type uint32 {
                            range "1..1000";
                        }
                        default "100";
                        description "Ingress rate percentage";
                    }

                } // container percentage-of-rate

            } // container modify-buffer-allocation

            container transceiver {
                description "Enter the transceiver context";

                leaf digital-coherent-optics {
                    type boolean;
                    default "false";
                    description "Enable digital coherent optics module for transceiver";
                }

                leaf-list apply-groups {
                    type leafref {
                        path "../../../groups/group/name";
                    }
                    max-elements 8;
                    ordered-by user;
                    description "Apply a configuration group at this level";
                }

                leaf-list apply-groups-exclude {
                    type leafref {
                        path "../../../groups/group/name";
                    }
                    max-elements 8;
                    ordered-by user;
                    description "Exclude a configuration group at this level";
                }

                container optical-line-system {
                    presence "Enable the optical-line-system context";
                    description "Enable the optical-line-system context";

                    leaf egress-amplifier-gain {
                        type decimal64 {
                            range "0.00..25.00";
                            fraction-digits 2;
                        }
                        units "decibels";
                        default "25.00";
                        description "Gain for the egress amplifier";
                    }

                } // container optical-line-system

            } // container transceiver

            container scheduler {
                description "Enter the scheduler context";

                leaf mode {
                    type enumeration {
                        enum vlan-qos                       { value 1; }
                    }
                    description "Port scheduler mode";
                }

                leaf low-latency {
                    type boolean;
                    default "false";
                    description "Enable low-latency mode on the port";
                }

                leaf-list apply-groups {
                    type leafref {
                        path "../../../groups/group/name";
                    }
                    max-elements 8;
                    ordered-by user;
                    description "Apply a configuration group at this level";
                }

                leaf-list apply-groups-exclude {
                    type leafref {
                        path "../../../groups/group/name";
                    }
                    max-elements 8;
                    ordered-by user;
                    description "Exclude a configuration group at this level";
                }

                list vlan-qos-policy {
                    when "../mode = 'vlan-qos'" {
                        description "only allowed in vlan-qos mode";
                    }
                    key "policy-name";
                    description "Enter the vlan-qos-policy list instance";

                    leaf policy-name {
                        type leafref {
                            path "../../../../qos/vlan-qos-policy/vlan-qos-policy-name";
                        }
                        description "VLAN QoS policy name";
                    }

                    leaf burst-limit {
                        type types-qos:vlan-qos-burst-limit;
                        description "Maximum traffic burst size for the port VLAN QoS policy";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                    choice egress-queue-agg-rate {
                        default "agg-rate";
                        case agg-rate {

                            container agg-rate {
                                description "Enter the agg-rate context";

                                leaf rate {
                                    type types-services:agg-rate-rate;
                                    units "kilobps";
                                    description "Maximum total rate of all egress queues";
                                }

                                leaf cir {
                                    type union {
                                        type int32 {
                                            range "0..400000000";
                                        }
                                        type enumeration {
                                            enum max                            { value -1; }
                                        }
                                    }
                                    units "kilobps";
                                    default "0";
                                    description "Administrative CIR";
                                }

                            } // container agg-rate

                        }
                        case percent-agg-rate {

                            container percent-agg-rate {
                                description "Enter the percent-agg-rate context";

                                leaf pir {
                                    type decimal64 {
                                        range "0.01..100.00";
                                        fraction-digits 2;
                                    }
                                    description "PIR percent rate";
                                }

                                leaf cir {
                                    type decimal64 {
                                        range "0.00..100.00";
                                        fraction-digits 2;
                                    }
                                    description "CIR percent rate";
                                }

                            } // container percent-agg-rate

                        }
                    }
                } // list vlan-qos-policy

            } // container scheduler

            uses conf-port-access;
            uses conf-port-connector;
            uses conf-port-dwdm;
            uses conf-port-ethernet;
            uses conf-port-gnss;
            uses conf-port-network;
            uses conf-port-otu;
            uses conf-port-sonet-sonet-sdh;
            uses conf-port-tdm;
        } // list port

    } // grouping conf-port

}
