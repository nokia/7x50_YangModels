submodule nokia-conf-system {

    yang-version "1.1";

    belongs-to nokia-conf { prefix "conf"; }

    import ietf-yang-types                { prefix "yang"; }
    import nokia-sros-yang-extensions     { prefix "sros-ext"; }
    import nokia-types-eth-cfm            { prefix "types-eth-cfm"; }
    import nokia-types-l2tp               { prefix "types-l2tp"; }
    import nokia-types-operation          { prefix "types-operation"; }
    import nokia-types-qos                { prefix "types-qos"; }
    import nokia-types-sros               { prefix "types-sros"; }
    import nokia-types-system             { prefix "types-system"; }

    include nokia-conf-groups;
    include nokia-conf-python;
    include nokia-conf-system-bluetooth;
    include nokia-conf-system-central-frequency-clock;
    include nokia-conf-system-cron;
    include nokia-conf-system-login-control;
    include nokia-conf-system-ned;
    include nokia-conf-system-persistence;
    include nokia-conf-system-ptp;
    include nokia-conf-system-script-control;
    include nokia-conf-system-security;
    include nokia-conf-system-security-tls;
    include nokia-conf-system-telemetry;
    include nokia-conf-system-time;

    sros-ext:sros-major-release "rel24";
    organization "Nokia";
    contact
        "Nokia SR OS Support
         Web: <http://www.nokia.com>";
    description
        "Nokia YANG Data model to configure system parameters on SR OS based routers.

         Copyright 2016 Nokia. All rights reserved. Reproduction of this document
         is authorized on the condition that the foregoing copyright notice is included.

         This nokia-conf-system YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";
    revision "2024-08-23";

    grouping conf-system {
        container system {
            description "Enter the system context";

            leaf contact {
                type types-sros:description;
                description "Contact information for the managed node";
            }

            leaf name {
                type types-sros:named-item-64;
                description "Administrative name assigned to the system";
            }

            leaf location {
                type types-sros:description;
                description "Site location of the system";
            }

            leaf alarm-contact-in-power {
                type boolean;
                default "false";
                description "Power the output pin on the CPM alarm interface port";
            }

            leaf icmp-vse {
                type boolean;
                default "false";
                description "Enable vendor-specific extensions to ICMP";
            }

            leaf selective-fib {
                type boolean;
                default "false";
                description "FIB assigned to the system";
            }

            leaf coordinates {
                type types-sros:description;
                description "GPS coordinates for the system location";
            }

            leaf clli-code {
                type types-sros:clli-description;
                description "CLLI code value for the system";
            }

            leaf congestion-management {
                type boolean;
                default "false";
                description "Enable Virtual Service Router congestion management";
            }

            leaf ospf-dynamic-hostnames {
                type boolean;
                default "false";
                description "Process received OSPF dynamic hostname information";
            }

            leaf boot-good-exec {
                type types-sros:url;
                description "CLI script file to execute following successful boot-up";
            }

            leaf boot-bad-exec {
                type types-sros:url;
                description "CLI script file to execute following a failed boot-up";
            }

            leaf allow-boot-license-violations {
                type boolean;
                default "true";
                description "Allow boot license violations in boot-up configuration";
            }

            leaf-list apply-groups {
                type leafref {
                    path "../../groups/group/name";
                }
                max-elements 8;
                ordered-by user;
                description "Apply a configuration group at this level";
            }

            leaf-list apply-groups-exclude {
                type leafref {
                    path "../../groups/group/name";
                }
                max-elements 8;
                ordered-by user;
                description "Exclude a configuration group at this level";
            }

            container alarms {
                description "Enter the alarms context";

                leaf admin-state {
                    type types-sros:admin-state;
                    default "enable";
                    description "Administrative state of the system alarm";
                }

                leaf max-cleared {
                    type uint32 {
                        range "0..500";
                    }
                    default "500";
                    description "Maximum number of cleared alarms";
                }

                leaf-list apply-groups {
                    type leafref {
                        path "../../../groups/group/name";
                    }
                    max-elements 8;
                    ordered-by user;
                    description "Apply a configuration group at this level";
                }

                leaf-list apply-groups-exclude {
                    type leafref {
                        path "../../../groups/group/name";
                    }
                    max-elements 8;
                    ordered-by user;
                    description "Exclude a configuration group at this level";
                }

            } // container alarms

            container cpm-http-redirect {
                description "Enter the cpm-http-redirect context";

                leaf optimized-mode {
                    type boolean;
                    default "true";
                    description "Enable optimized mode for CPM HTTP redirect messages";
                }

                leaf-list apply-groups {
                    type leafref {
                        path "../../../groups/group/name";
                    }
                    max-elements 8;
                    ordered-by user;
                    description "Apply a configuration group at this level";
                }

                leaf-list apply-groups-exclude {
                    type leafref {
                        path "../../../groups/group/name";
                    }
                    max-elements 8;
                    ordered-by user;
                    description "Exclude a configuration group at this level";
                }

            } // container cpm-http-redirect

            container load-balancing {
                description "Enter the load-balancing context";

                leaf l2tp-load-balancing {
                    type boolean;
                    default "false";
                    description "Include L2TP header information for load balancing";
                }

                leaf l4-load-balancing {
                    type boolean;
                    description "Use load balancing based on Layer 4 fields";
                }

                leaf lsr-load-balancing {
                    type enumeration {
                        enum lbl-only                       { value 1; }
                        enum lbl-ip                         { value 2; }
                        enum ip-only                        { value 3; }
                        enum eth-encap-ip                   { value 4; }
                        enum lbl-ip-l4-teid                 { value 5; }
                        enum lbl-eth-ip-l4-teid             { value 6; }
                        enum lbl-ip-or-teid                 { value 7; }
                    }
                    description "Algorithm for system-wide LSR load balancing";
                }

                leaf mc-enh-load-balancing {
                    type boolean;
                    default "false";
                    description "Enable enhanced egress multicast load balancing";
                }

                leaf service-id-lag-hashing {
                    type boolean;
                    default "false";
                    description "Enable enhanced VLL LAG service ID hashing";
                }

                leaf system-ip-load-balancing {
                    type boolean;
                    description "Use system IP address for ECMP and LAG load balancing";
                }

                leaf eler-enh-load-balancing {
                    type boolean;
                    default "false";
                    description "Use eLER load balancing based on outer MPLS label stack";
                }

                leaf-list apply-groups {
                    type leafref {
                        path "../../../groups/group/name";
                    }
                    max-elements 8;
                    ordered-by user;
                    description "Apply a configuration group at this level";
                }

                leaf-list apply-groups-exclude {
                    type leafref {
                        path "../../../groups/group/name";
                    }
                    max-elements 8;
                    ordered-by user;
                    description "Exclude a configuration group at this level";
                }

                container hash-polynomial {
                    description "Enter the hash-polynomial context";

                    leaf ecmp {
                        type types-system:hash-polynomial-ecmp-type;
                        default "poly1";
                        description "Hashing polynomial for (IP) ECMP";
                    }

                    leaf lag {
                        type types-system:hash-polynomial-lag-type;
                        default "poly2";
                        description "Hashing polynomial for LAG";
                    }

                } // container hash-polynomial

                container exclude {
                    description "Enter the exclude context";

                    leaf src-dst-ipv6 {
                        type boolean;
                        default "false";
                        description "Enable the exclusion of IPv6 addresses";
                    }

                } // container exclude

            } // container load-balancing

            list alarm-contact-input {
                key "input-pin-number";
                description "Enter the alarm-contact-input list instance";

                leaf input-pin-number {
                    type int32 {
                        range "1..4";
                    }
                    description "Alarm contact input pin";
                }

                leaf admin-state {
                    type types-sros:admin-state;
                    default "disable";
                    description "Administrative state of the alarm contact input";
                }

                leaf description {
                    type types-sros:long-description;
                    description "Text description";
                }

                leaf normal-state {
                    type enumeration {
                        enum open                           { value 1; }
                        enum closed                         { value 2; }
                    }
                    default "open";
                    description "Normal state associated with the alarm contact input";
                }

                leaf trigger-message {
                    type types-sros:description;
                    default "Alarm Input Triggered";
                    description "Text message sent in the log event when input changes";
                }

                leaf clear-message {
                    type types-sros:description;
                    default "Alarm Input Cleared";
                    description "Text message sent in the log event when an alarm clears";
                }

                leaf-list apply-groups {
                    type leafref {
                        path "../../../groups/group/name";
                    }
                    max-elements 8;
                    ordered-by user;
                    description "Apply a configuration group at this level";
                }

                leaf-list apply-groups-exclude {
                    type leafref {
                        path "../../../groups/group/name";
                    }
                    max-elements 8;
                    ordered-by user;
                    description "Exclude a configuration group at this level";
                }

            } // list alarm-contact-input


            container dns {
                description "Enter the dns context";

                leaf address-pref {
                    type enumeration {
                        enum ipv4-only                      { value 1; }
                        enum ipv6-first                     { value 2; }
                    }
                    description "Preference in DNS address resolving order";
                }

                leaf-list apply-groups {
                    type leafref {
                        path "../../../groups/group/name";
                    }
                    max-elements 8;
                    ordered-by user;
                    description "Apply a configuration group at this level";
                }

                leaf-list apply-groups-exclude {
                    type leafref {
                        path "../../../groups/group/name";
                    }
                    max-elements 8;
                    ordered-by user;
                    description "Exclude a configuration group at this level";
                }

                container dnssec {
                    description "Enter the dnssec context";

                    leaf ad-validation {
                        type enumeration {
                            enum fall-through {
                                value 1;
                                description "Allow non-DNSSEC responses to fall-through to permit resolution in case of validation failure";
                            }
                            enum drop {
                                value 2;
                                description "Drop non-DNSSEC responses in case of validation failure";
                            }
                        }
                        description "Validation of AD-bit presence in DNS server responses";
                    }

                } // container dnssec

            } // container dns

            container efm-oam {
                description "Enter the efm-oam context";

                leaf dying-gasp-tx-on-reset {
                    type boolean;
                    default "false";
                    description "Generate Information OAM PDU on soft reset notification";
                }

                leaf grace-tx {
                    type boolean;
                    default "false";
                    description "Send Grace TLVs for soft reset graceful recovery events";
                }

                leaf-list apply-groups {
                    type leafref {
                        path "../../../groups/group/name";
                    }
                    max-elements 8;
                    ordered-by user;
                    description "Apply a configuration group at this level";
                }

                leaf-list apply-groups-exclude {
                    type leafref {
                        path "../../../groups/group/name";
                    }
                    max-elements 8;
                    ordered-by user;
                    description "Exclude a configuration group at this level";
                }

            } // container efm-oam

            container eth-cfm {
                description "Enter the eth-cfm context";

                leaf grace {
                    type boolean;
                    default "true";
                    description "Allow system level capability of grace messaging";
                }

                leaf named-display {
                    type boolean;
                    default "false";
                    description "Enable administrative name display in CLI show outputs";
                }

                leaf-list apply-groups {
                    type leafref {
                        path "../../../groups/group/name";
                    }
                    max-elements 8;
                    ordered-by user;
                    description "Apply a configuration group at this level";
                }

                leaf-list apply-groups-exclude {
                    type leafref {
                        path "../../../groups/group/name";
                    }
                    max-elements 8;
                    ordered-by user;
                    description "Exclude a configuration group at this level";
                }

                container sender-id {
                    description "Enter the sender-id context";

                    leaf type {
                        type types-eth-cfm:chassis-id-subtype;
                        description "ETH-CFM sender ID to be used in CFM PDUs";
                    }

                    leaf local-name {
                        type string {
                            length "1..45";
                        }
                        description "Local name used in CFM PDUs";
                    }

                } // container sender-id

                container redundancy {
                    description "Enter the redundancy context";

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                    container mc-lag {
                        description "Enter the mc-lag context";

                        leaf propagate-hold-time {
                            type union {
                                type int32 {
                                    range "1..60";
                                }
                                type enumeration {
                                    enum none                           { value 0; }
                                }
                            }
                            units "seconds";
                            default "1";
                            description "Delay timer value for the fault propagation";
                        }

                        leaf standby-mep {
                            type boolean;
                            default "false";
                            description "Allow standby MC-LAG MEPs to act administratively down";
                        }

                    } // container mc-lag

                } // container redundancy

                container slm {
                    description "Enter the slm context";

                    leaf inactivity-timer {
                        type uint32 {
                            range "10..100";
                        }
                        units "seconds";
                        default "100";
                        description "SLR inactivity timer to maintain the stale test data";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                } // container slm

                container md-auto-id {
                    description "Enter the md-auto-id context";

                    container md-index-range {
                        presence "Enable the md-index-range context";
                        description "Enable the md-index-range context";

                        leaf start {
                            type uint32 {
                                range "1..max";
                            }
                            sros-ext:immutable;
                            mandatory true;
                            description "Lower bound of the range";
                        }

                        leaf end {
                            type uint32 {
                                range "1..max";
                            }
                            sros-ext:immutable;
                            mandatory true;
                            description "Upper bound of the range";
                        }

                        leaf-list apply-groups {
                            type leafref {
                                path "../../../../../groups/group/name";
                            }
                            max-elements 8;
                            ordered-by user;
                            description "Apply a configuration group at this level";
                        }

                        leaf-list apply-groups-exclude {
                            type leafref {
                                path "../../../../../groups/group/name";
                            }
                            max-elements 8;
                            ordered-by user;
                            description "Exclude a configuration group at this level";
                        }

                    } // container md-index-range

                    container ma-index-range {
                        presence "Enable the ma-index-range context";
                        description "Enable the ma-index-range context";

                        leaf start {
                            type uint32 {
                                range "1..max";
                            }
                            sros-ext:immutable;
                            mandatory true;
                            description "Lower bound of the range";
                        }

                        leaf end {
                            type uint32 {
                                range "1..max";
                            }
                            sros-ext:immutable;
                            mandatory true;
                            description "Upper bound of the range";
                        }

                        leaf-list apply-groups {
                            type leafref {
                                path "../../../../../groups/group/name";
                            }
                            max-elements 8;
                            ordered-by user;
                            description "Apply a configuration group at this level";
                        }

                        leaf-list apply-groups-exclude {
                            type leafref {
                                path "../../../../../groups/group/name";
                            }
                            max-elements 8;
                            ordered-by user;
                            description "Exclude a configuration group at this level";
                        }

                    } // container ma-index-range

                } // container md-auto-id

            } // container eth-cfm

            container fp {
                description "Enter the fp context";

                leaf-list apply-groups {
                    type leafref {
                        path "../../../groups/group/name";
                    }
                    max-elements 8;
                    ordered-by user;
                    description "Apply a configuration group at this level";
                }

                leaf-list apply-groups-exclude {
                    type leafref {
                        path "../../../groups/group/name";
                    }
                    max-elements 8;
                    ordered-by user;
                    description "Exclude a configuration group at this level";
                }

                container options {
                    description "Enter the options context";

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                    container qos {
                        description "Enter the qos context";

                        container dscp-transparency {
                            description "Enter the dscp-transparency context";

                            leaf admin-state {
                                type types-sros:admin-state;
                                default "enable";
                                description "Administrative state of the DSCP transparency option";
                            }

                        } // container dscp-transparency

                        container fc-4-profile {
                            description "Enter the fc-4-profile context";

                            leaf admin-state {
                                type types-sros:admin-state;
                                default "disable";
                                description "Administrative state of the fc-4-profile option";
                            }

                        } // container fc-4-profile

                        container mac-classification-criteria {
                            description "Enter the mac-classification-criteria context";

                            leaf admin-state {
                                type types-sros:admin-state;
                                default "disable";
                                description "Administrative state of QoS mac-classification-criteria";
                            }

                        } // container mac-classification-criteria

                        container ipv6-classification-criteria {
                            description "Enter the ipv6-classification-criteria context";

                            leaf admin-state {
                                type types-sros:admin-state;
                                default "disable";
                                description "Administrative state of QoS ipv6-classification-criteria";
                            }

                        } // container ipv6-classification-criteria

                        container bum-policers {
                            description "Enter the bum-policers context";

                            leaf admin-state {
                                type types-sros:admin-state;
                                default "disable";
                                description "Administrative state of the QoS BUM policers";
                            }

                        } // container bum-policers

                        container shared-policer {
                            description "Enter the shared-policer context";

                            leaf admin-state {
                                type types-sros:admin-state;
                                default "disable";
                                description "Administrative state of the QoS shared policer option";
                            }

                        } // container shared-policer

                    } // container qos

                    container mpls {
                        description "Enter the mpls context";

                        container entropy-label {
                            description "Enter the entropy-label context";

                            leaf admin-state {
                                type types-sros:admin-state;
                                default "disable";
                                description "Administrative state of the entropy-label option";
                            }

                        } // container entropy-label

                        container fast-switchover {
                            status obsolete;
                            description "Enter the fast-switchover context";

                            leaf admin-state {
                                status obsolete;
                                type types-sros:admin-state;
                                default "enable";
                                description "Administrative state of the MPLS fast-switchover option";
                            }

                        } // container fast-switchover

                    } // container mpls

                    container service {
                        description "Enter the service context";

                        container ces {
                            description "Enter the ces context";

                            leaf admin-state {
                                type types-sros:admin-state;
                                default "enable";
                                description "Administrative state of the CES option";
                            }

                        } // container ces

                        container ring-aps {
                            description "Enter the ring-aps context";

                            leaf admin-state {
                                type types-sros:admin-state;
                                default "disable";
                                description "Administrative state of the ring-aps option";
                            }

                        } // container ring-aps

                        container vpls-evpn-mpls {
                            description "Enter the vpls-evpn-mpls context";

                            leaf admin-state {
                                type types-sros:admin-state;
                                default "enable";
                                description "Administrative state of the VPLS EVPN MPLS option";
                            }

                        } // container vpls-evpn-mpls

                    } // container service

                    container mac-filter {
                        status obsolete;
                        description "Enter the mac-filter context";

                        container outer-vlan-priority {
                            status obsolete;
                            description "Enter the outer-vlan-priority context";

                            leaf admin-state {
                                status obsolete;
                                type types-sros:admin-state;
                                default "disable";
                                description "Administrative state of MAC filter outer VLAN priority";
                            }

                        } // container outer-vlan-priority

                    } // container mac-filter

                    container router {
                        description "Enter the router context";

                        container ecmp {
                            status obsolete;
                            description "Enter the ecmp context";

                            leaf admin-state {
                                status obsolete;
                                type types-sros:admin-state;
                                default "enable";
                                description "Administrative state of the router ECMP option";
                            }

                        } // container ecmp

                    } // container router

                    container ethernet {
                        description "Enter the ethernet context";

                        container dot1x-host-authentication {
                            description "Enter the dot1x-host-authentication context";

                            leaf admin-state {
                                type types-sros:admin-state;
                                default "disable";
                                description "Administrative state of dot1x-host-authentication";
                            }

                        } // container dot1x-host-authentication

                    } // container ethernet

                    container ip-filter {
                        description "Enter the ip-filter context";

                        container pbr-redirect {
                            description "Enter the pbr-redirect context";

                            leaf admin-state {
                                type types-sros:admin-state;
                                default "disable";
                                description "Administrative state of the pbr-redirect option";
                            }

                        } // container pbr-redirect

                        container stats-collection {
                            description "Enter the stats-collection context";

                            leaf admin-state {
                                type types-sros:admin-state;
                                default "enable";
                                description "Administrative state of the stats-collection option";
                            }

                        } // container stats-collection

                    } // container ip-filter

                    container ipv6-filter {
                        description "Enter the ipv6-filter context";

                        container egress {
                            description "Enter the egress context";

                            leaf admin-state {
                                type types-sros:admin-state;
                                default "enable";
                                description "Administrative state of the egress ipv6-filter option";
                            }

                        } // container egress

                        container dst-ip-lsb {
                            description "Enter the dst-ip-lsb context";

                            leaf admin-state {
                                type types-sros:admin-state;
                                default "disable";
                                description "Administrative state of the dst-ip-lsb option";
                            }

                        } // container dst-ip-lsb

                        container dst-port {
                            description "Enter the dst-port context";

                            leaf admin-state {
                                type types-sros:admin-state;
                                default "enable";
                                description "Administrative state of the dst-port option";
                            }

                        } // container dst-port

                        container flow-label {
                            description "Enter the flow-label context";

                            leaf admin-state {
                                type types-sros:admin-state;
                                default "disable";
                                description "Administrative state of the flow label match";
                            }

                        } // container flow-label

                        container next-header {
                            description "Enter the next-header context";

                            leaf admin-state {
                                type types-sros:admin-state;
                                default "enable";
                                description "Administrative state of the next-header option";
                            }

                        } // container next-header

                        container pbr-redirect {
                            description "Enter the pbr-redirect context";

                            leaf admin-state {
                                type types-sros:admin-state;
                                default "disable";
                                description "Administrative state of the pbr-redirect option";
                            }

                        } // container pbr-redirect

                        container src-port {
                            description "Enter the src-port context";

                            leaf admin-state {
                                type types-sros:admin-state;
                                default "enable";
                                description "Administrative state of the src-port option";
                            }

                        } // container src-port

                        container stats-collection {
                            description "Enter the stats-collection context";

                            leaf admin-state {
                                type types-sros:admin-state;
                                default "enable";
                                description "Administrative state of the stats-collection option";
                            }

                        } // container stats-collection

                        container tcp-flags {
                            description "Enter the tcp-flags context";

                            leaf admin-state {
                                type types-sros:admin-state;
                                default "enable";
                                description "Administrative state of the tcp-flags option";
                            }

                        } // container tcp-flags

                    } // container ipv6-filter


                    container lpm-allocation {
                        status obsolete;
                        description "Enter the lpm-allocation context";

                        container scale-option-1 {
                            status obsolete;
                            description "Enter the scale-option-1 context";

                            leaf admin-state {
                                status obsolete;
                                type types-sros:admin-state;
                                default "enable";
                                description "Administrative state of scale-option-1";
                            }

                        } // container scale-option-1

                        container scale-option-2 {
                            status obsolete;
                            description "Enter the scale-option-2 context";

                            leaf admin-state {
                                status obsolete;
                                type types-sros:admin-state;
                                default "disable";
                                description "Administrate state of scale-option-2";
                            }

                        } // container scale-option-2

                        container scale-option-3 {
                            status obsolete;
                            description "Enter the scale-option-3 context";

                            leaf admin-state {
                                status obsolete;
                                type types-sros:admin-state;
                                default "disable";
                                description "Administrative state of the scale-option-3 option";
                            }

                        } // container scale-option-3

                    } // container lpm-allocation

                } // container options

                container cam-allocation {
                    description "Enter the cam-allocation context";

                    leaf v6-multicast {
                        type uint32 {
                            range "0|512|1024|2048|4096|6144|8192|10240";
                        }
                        default "0";
                        description "CAM bank allocation for v6 multicast configurations";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                } // container cam-allocation

                container resource-allocation {
                    description "Enter the resource-allocation context";

                    leaf g8032-sap {
                        status obsolete;
                        type uint32 {
                            range "0..4096";
                        }
                        description "Maximum number of resources allocated to G.8032 SAPs";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                    container egress-encap {
                        description "Enter the egress-encap context";

                        leaf port-vlan-translation {
                            type enumeration {
                                enum 2k                             { value 1; }
                                enum 4k                             { value 2; }
                                enum 8k                             { value 3; }
                                enum 16k                            { value 4; }
                            }
                            description "Number of port-vlan-translation egress-encap entries";
                        }

                        leaf routed {
                            type enumeration {
                                enum 4k                             { value 1; }
                                enum 8k                             { value 2; }
                                enum 12k                            { value 3; }
                            }
                            default "12k";
                            description "Number of routed egress-encap entries";
                        }

                    } // container egress-encap

                    container filter {
                        description "Enter the filter context";

                        leaf ipv6-number {
                            type uint32 {
                                range "0|2|4|6|8|10";
                            }
                            description "Number of IPv6 filter resources (banks) allocated for egress IPv6 filters";
                        }

                        container ingress {
                            description "Enter the ingress context";

                            leaf-list apply-groups {
                                type leafref {
                                    path "../../../../../../groups/group/name";
                                }
                                max-elements 8;
                                ordered-by user;
                                description "Apply a configuration group at this level";
                            }

                            leaf-list apply-groups-exclude {
                                type leafref {
                                    path "../../../../../../groups/group/name";
                                }
                                max-elements 8;
                                ordered-by user;
                                description "Exclude a configuration group at this level";
                            }

                            container ip-filter {
                                description "Enter the ip-filter context";

                                leaf-list apply-groups {
                                    type leafref {
                                        path "../../../../../../../groups/group/name";
                                    }
                                    max-elements 8;
                                    ordered-by user;
                                    description "Apply a configuration group at this level";
                                }

                                leaf-list apply-groups-exclude {
                                    type leafref {
                                        path "../../../../../../../groups/group/name";
                                    }
                                    max-elements 8;
                                    ordered-by user;
                                    description "Exclude a configuration group at this level";
                                }

                                container actions {
                                    description "Enter the actions context";

                                    leaf-list apply-groups {
                                        type leafref {
                                            path "../../../../../../../../groups/group/name";
                                        }
                                        max-elements 8;
                                        ordered-by user;
                                        description "Apply a configuration group at this level";
                                    }

                                    leaf-list apply-groups-exclude {
                                        type leafref {
                                            path "../../../../../../../../groups/group/name";
                                        }
                                        max-elements 8;
                                        ordered-by user;
                                        description "Exclude a configuration group at this level";
                                    }

                                    container drop {
                                        description "Enter the drop context";

                                        leaf admin-state {
                                            type types-sros:admin-state;
                                            default "enable";
                                            description "Administrative state of the drop action";
                                        }

                                    } // container drop

                                    container fc {
                                        description "Enter the fc context";

                                        leaf admin-state {
                                            type types-sros:admin-state;
                                            default "enable";
                                            description "Administrative state of the FC action";
                                        }

                                    } // container fc

                                    container log {
                                        description "Enter the log context";

                                        leaf admin-state {
                                            type types-sros:admin-state;
                                            default "enable";
                                            description "Administrative state of the log action";
                                        }

                                    } // container log

                                    container mirror {
                                        description "Enter the mirror context";

                                        leaf admin-state {
                                            type types-sros:admin-state;
                                            default "enable";
                                            description "Administrative state of the mirror action";
                                        }

                                    } // container mirror

                                    container redirect {
                                        description "Enter the redirect context";

                                        leaf admin-state {
                                            type types-sros:admin-state;
                                            default "enable";
                                            description "Administrative state of the redirect action";
                                        }

                                    } // container redirect

                                    container stats-collection {
                                        description "Enter the stats-collection context";

                                        leaf admin-state {
                                            type types-sros:admin-state;
                                            default "enable";
                                            description "Administrative state of filter statistics collection";
                                        }

                                    } // container stats-collection

                                } // container actions

                                container match-criteria {
                                    description "Enter the match-criteria context";

                                    leaf-list apply-groups {
                                        type leafref {
                                            path "../../../../../../../../groups/group/name";
                                        }
                                        max-elements 8;
                                        ordered-by user;
                                        description "Apply a configuration group at this level";
                                    }

                                    leaf-list apply-groups-exclude {
                                        type leafref {
                                            path "../../../../../../../../groups/group/name";
                                        }
                                        max-elements 8;
                                        ordered-by user;
                                        description "Exclude a configuration group at this level";
                                    }

                                    container dscp {
                                        description "Enter the dscp context";

                                        leaf admin-state {
                                            type types-sros:admin-state;
                                            default "enable";
                                            description "Administrative state of DSCP match";
                                        }

                                    } // container dscp

                                    container dst-ip {
                                        description "Enter the dst-ip context";

                                        leaf admin-state {
                                            type types-sros:admin-state;
                                            default "enable";
                                            description "Administrative state of destination IP match";
                                        }

                                    } // container dst-ip

                                    container dst-port {
                                        description "Enter the dst-port context";

                                        leaf admin-state {
                                            type types-sros:admin-state;
                                            default "enable";
                                            description "Administrative state of the destination port match";
                                        }

                                    } // container dst-port

                                    container icmp-code {
                                        description "Enter the icmp-code context";

                                        leaf admin-state {
                                            type types-sros:admin-state;
                                            default "disable";
                                            description "Administrative state of the ICMP code matching";
                                        }

                                    } // container icmp-code

                                    container icmp-type {
                                        description "Enter the icmp-type context";

                                        leaf admin-state {
                                            type types-sros:admin-state;
                                            default "disable";
                                            description "Administrative state of the ICMP type matching";
                                        }

                                    } // container icmp-type

                                    container protocol {
                                        description "Enter the protocol context";

                                        leaf admin-state {
                                            type types-sros:admin-state;
                                            default "enable";
                                            description "Administrative state of protocol match";
                                        }

                                    } // container protocol

                                    container src-ip {
                                        description "Enter the src-ip context";

                                        leaf admin-state {
                                            type types-sros:admin-state;
                                            default "enable";
                                            description "Administrative state of source IP address match";
                                        }

                                    } // container src-ip

                                    container src-port {
                                        description "Enter the src-port context";

                                        leaf admin-state {
                                            type types-sros:admin-state;
                                            default "enable";
                                            description "Administrative state of source port match";
                                        }

                                    } // container src-port

                                    container tcp-flags {
                                        description "Enter the tcp-flags context";

                                        leaf admin-state {
                                            type types-sros:admin-state;
                                            default "enable";
                                            description "Administrative state of TCP flag match";
                                        }

                                    } // container tcp-flags

                                    container tcp-flags-ext {
                                        description "Enter the tcp-flags-ext context";

                                        leaf admin-state {
                                            type types-sros:admin-state;
                                            default "disable";
                                            description "Administrative state of the extended TCP flags";
                                        }

                                    } // container tcp-flags-ext

                                } // container match-criteria

                            } // container ip-filter

                            container ipv6-filter {
                                description "Enter the ipv6-filter context";

                                leaf-list apply-groups {
                                    type leafref {
                                        path "../../../../../../../groups/group/name";
                                    }
                                    max-elements 8;
                                    ordered-by user;
                                    description "Apply a configuration group at this level";
                                }

                                leaf-list apply-groups-exclude {
                                    type leafref {
                                        path "../../../../../../../groups/group/name";
                                    }
                                    max-elements 8;
                                    ordered-by user;
                                    description "Exclude a configuration group at this level";
                                }

                                container actions {
                                    description "Enter the actions context";

                                    leaf-list apply-groups {
                                        type leafref {
                                            path "../../../../../../../../groups/group/name";
                                        }
                                        max-elements 8;
                                        ordered-by user;
                                        description "Apply a configuration group at this level";
                                    }

                                    leaf-list apply-groups-exclude {
                                        type leafref {
                                            path "../../../../../../../../groups/group/name";
                                        }
                                        max-elements 8;
                                        ordered-by user;
                                        description "Exclude a configuration group at this level";
                                    }

                                    container drop {
                                        description "Enter the drop context";

                                        leaf admin-state {
                                            type types-sros:admin-state;
                                            default "enable";
                                            description "Administrative state of the drop action";
                                        }

                                    } // container drop

                                    container fc {
                                        description "Enter the fc context";

                                        leaf admin-state {
                                            type types-sros:admin-state;
                                            default "enable";
                                            description "Administrative state of the FC action";
                                        }

                                    } // container fc

                                    container log {
                                        description "Enter the log context";

                                        leaf admin-state {
                                            type types-sros:admin-state;
                                            default "enable";
                                            description "Administrative state of the log action";
                                        }

                                    } // container log

                                    container mirror {
                                        description "Enter the mirror context";

                                        leaf admin-state {
                                            type types-sros:admin-state;
                                            default "enable";
                                            description "Administrative state of the mirror action";
                                        }

                                    } // container mirror

                                    container redirect {
                                        description "Enter the redirect context";

                                        leaf admin-state {
                                            type types-sros:admin-state;
                                            default "enable";
                                            description "Administrative state of the redirect action";
                                        }

                                    } // container redirect

                                    container stats-collection {
                                        description "Enter the stats-collection context";

                                        leaf admin-state {
                                            type types-sros:admin-state;
                                            default "enable";
                                            description "Administrative state of filter statistics collection";
                                        }

                                    } // container stats-collection

                                } // container actions

                                container match-criteria {
                                    description "Enter the match-criteria context";

                                    leaf-list apply-groups {
                                        type leafref {
                                            path "../../../../../../../../groups/group/name";
                                        }
                                        max-elements 8;
                                        ordered-by user;
                                        description "Apply a configuration group at this level";
                                    }

                                    leaf-list apply-groups-exclude {
                                        type leafref {
                                            path "../../../../../../../../groups/group/name";
                                        }
                                        max-elements 8;
                                        ordered-by user;
                                        description "Exclude a configuration group at this level";
                                    }

                                    container dscp {
                                        description "Enter the dscp context";

                                        leaf admin-state {
                                            type types-sros:admin-state;
                                            default "enable";
                                            description "Administrative state of DSCP match";
                                        }

                                    } // container dscp

                                    container dst-ip-lsb {
                                        description "Enter the dst-ip-lsb context";

                                        leaf admin-state {
                                            type types-sros:admin-state;
                                            default "disable";
                                            description "Administrative state of the destination IP LSB match";
                                        }

                                    } // container dst-ip-lsb

                                    container dst-ip-msb {
                                        description "Enter the dst-ip-msb context";

                                        leaf admin-state {
                                            type types-sros:admin-state;
                                            default "enable";
                                            description "Administrative state of the destination IP MSB match";
                                        }

                                    } // container dst-ip-msb

                                    container dst-port {
                                        description "Enter the dst-port context";

                                        leaf admin-state {
                                            type types-sros:admin-state;
                                            default "enable";
                                            description "Administrative state of destination port match";
                                        }

                                    } // container dst-port

                                    container flow-label {
                                        description "Enter the flow-label context";

                                        leaf admin-state {
                                            type types-sros:admin-state;
                                            default "disable";
                                            description "Administrative state of the flow label match";
                                        }

                                    } // container flow-label

                                    container icmp-code {
                                        description "Enter the icmp-code context";

                                        leaf admin-state {
                                            type types-sros:admin-state;
                                            default "disable";
                                            description "Administrative state of the ICMP code matching";
                                        }

                                    } // container icmp-code

                                    container icmp-type {
                                        description "Enter the icmp-type context";

                                        leaf admin-state {
                                            type types-sros:admin-state;
                                            default "disable";
                                            description "Administrative state of the ICMP type matching";
                                        }

                                    } // container icmp-type

                                    container next-header {
                                        description "Enter the next-header context";

                                        leaf admin-state {
                                            type types-sros:admin-state;
                                            default "enable";
                                            description "Administrative state of next-header match";
                                        }

                                    } // container next-header

                                    container src-ip-lsb {
                                        description "Enter the src-ip-lsb context";

                                        leaf admin-state {
                                            type types-sros:admin-state;
                                            default "enable";
                                            description "Administrative state of source IP LSB match";
                                        }

                                    } // container src-ip-lsb

                                    container src-ip-msb {
                                        description "Enter the src-ip-msb context";

                                        leaf admin-state {
                                            type types-sros:admin-state;
                                            default "enable";
                                            description "Administrative state of source IP MSB match";
                                        }

                                    } // container src-ip-msb

                                    container src-port {
                                        description "Enter the src-port context";

                                        leaf admin-state {
                                            type types-sros:admin-state;
                                            default "enable";
                                            description "Administrative state of source port match";
                                        }

                                    } // container src-port

                                    container tcp-flags {
                                        description "Enter the tcp-flags context";

                                        leaf admin-state {
                                            type types-sros:admin-state;
                                            default "enable";
                                            description "Administrative state of TCP flags match";
                                        }

                                    } // container tcp-flags

                                    container tcp-flags-ext {
                                        description "Enter the tcp-flags-ext context";

                                        leaf admin-state {
                                            type types-sros:admin-state;
                                            default "disable";
                                            description "Administrative state of the extended TCP flags";
                                        }

                                    } // container tcp-flags-ext

                                } // container match-criteria

                            } // container ipv6-filter

                        } // container ingress

                        container egress {
                            description "Enter the egress context";

                            leaf-list apply-groups {
                                type leafref {
                                    path "../../../../../../groups/group/name";
                                }
                                max-elements 8;
                                ordered-by user;
                                description "Apply a configuration group at this level";
                            }

                            leaf-list apply-groups-exclude {
                                type leafref {
                                    path "../../../../../../groups/group/name";
                                }
                                max-elements 8;
                                ordered-by user;
                                description "Exclude a configuration group at this level";
                            }

                            container ip-filter {
                                description "Enter the ip-filter context";

                                leaf-list apply-groups {
                                    type leafref {
                                        path "../../../../../../../groups/group/name";
                                    }
                                    max-elements 8;
                                    ordered-by user;
                                    description "Apply a configuration group at this level";
                                }

                                leaf-list apply-groups-exclude {
                                    type leafref {
                                        path "../../../../../../../groups/group/name";
                                    }
                                    max-elements 8;
                                    ordered-by user;
                                    description "Exclude a configuration group at this level";
                                }

                                container actions {
                                    description "Enter the actions context";

                                    leaf-list apply-groups {
                                        type leafref {
                                            path "../../../../../../../../groups/group/name";
                                        }
                                        max-elements 8;
                                        ordered-by user;
                                        description "Apply a configuration group at this level";
                                    }

                                    leaf-list apply-groups-exclude {
                                        type leafref {
                                            path "../../../../../../../../groups/group/name";
                                        }
                                        max-elements 8;
                                        ordered-by user;
                                        description "Exclude a configuration group at this level";
                                    }

                                    container drop {
                                        description "Enter the drop context";

                                        leaf admin-state {
                                            type types-sros:admin-state;
                                            default "enable";
                                            description "Administrative state of the drop action";
                                        }

                                    } // container drop

                                    container stats-collection {
                                        description "Enter the stats-collection context";

                                        leaf admin-state {
                                            type types-sros:admin-state;
                                            default "enable";
                                            description "Administrative state of filter statistics collection";
                                        }

                                    } // container stats-collection

                                } // container actions

                                container match-criteria {
                                    description "Enter the match-criteria context";

                                    leaf-list apply-groups {
                                        type leafref {
                                            path "../../../../../../../../groups/group/name";
                                        }
                                        max-elements 8;
                                        ordered-by user;
                                        description "Apply a configuration group at this level";
                                    }

                                    leaf-list apply-groups-exclude {
                                        type leafref {
                                            path "../../../../../../../../groups/group/name";
                                        }
                                        max-elements 8;
                                        ordered-by user;
                                        description "Exclude a configuration group at this level";
                                    }

                                    container dscp {
                                        description "Enter the dscp context";

                                        leaf admin-state {
                                            type types-sros:admin-state;
                                            default "enable";
                                            description "Administrative state of DSCP match";
                                        }

                                    } // container dscp

                                    container dst-ip {
                                        description "Enter the dst-ip context";

                                        leaf admin-state {
                                            type types-sros:admin-state;
                                            default "enable";
                                            description "Administrative state of destination IP match";
                                        }

                                    } // container dst-ip

                                    container dst-port {
                                        description "Enter the dst-port context";

                                        leaf admin-state {
                                            type types-sros:admin-state;
                                            default "enable";
                                            description "Administrative state of the destination port match";
                                        }

                                    } // container dst-port

                                    container icmp-code {
                                        description "Enter the icmp-code context";

                                        leaf admin-state {
                                            type types-sros:admin-state;
                                            default "disable";
                                            description "Administrative state of the ICMP code matching";
                                        }

                                    } // container icmp-code

                                    container icmp-type {
                                        description "Enter the icmp-type context";

                                        leaf admin-state {
                                            type types-sros:admin-state;
                                            default "disable";
                                            description "Administrative state of the ICMP type matching";
                                        }

                                    } // container icmp-type

                                    container protocol {
                                        description "Enter the protocol context";

                                        leaf admin-state {
                                            type types-sros:admin-state;
                                            default "enable";
                                            description "Administrative state of protocol match";
                                        }

                                    } // container protocol

                                    container src-ip {
                                        description "Enter the src-ip context";

                                        leaf admin-state {
                                            type types-sros:admin-state;
                                            default "enable";
                                            description "Administrative state of source IP address match";
                                        }

                                    } // container src-ip

                                    container src-port {
                                        description "Enter the src-port context";

                                        leaf admin-state {
                                            type types-sros:admin-state;
                                            default "enable";
                                            description "Administrative state of source port match";
                                        }

                                    } // container src-port

                                    container tcp-flags {
                                        description "Enter the tcp-flags context";

                                        leaf admin-state {
                                            type types-sros:admin-state;
                                            default "enable";
                                            description "Administrative state of TCP flag match";
                                        }

                                    } // container tcp-flags

                                    container tcp-flags-ext {
                                        description "Enter the tcp-flags-ext context";

                                        leaf admin-state {
                                            type types-sros:admin-state;
                                            default "disable";
                                            description "Administrative state of the extended TCP flags";
                                        }

                                    } // container tcp-flags-ext

                                } // container match-criteria

                            } // container ip-filter

                            container ipv6-filter {
                                description "Enter the ipv6-filter context";

                                leaf-list apply-groups {
                                    type leafref {
                                        path "../../../../../../../groups/group/name";
                                    }
                                    max-elements 8;
                                    ordered-by user;
                                    description "Apply a configuration group at this level";
                                }

                                leaf-list apply-groups-exclude {
                                    type leafref {
                                        path "../../../../../../../groups/group/name";
                                    }
                                    max-elements 8;
                                    ordered-by user;
                                    description "Exclude a configuration group at this level";
                                }

                                container actions {
                                    description "Enter the actions context";

                                    leaf-list apply-groups {
                                        type leafref {
                                            path "../../../../../../../../groups/group/name";
                                        }
                                        max-elements 8;
                                        ordered-by user;
                                        description "Apply a configuration group at this level";
                                    }

                                    leaf-list apply-groups-exclude {
                                        type leafref {
                                            path "../../../../../../../../groups/group/name";
                                        }
                                        max-elements 8;
                                        ordered-by user;
                                        description "Exclude a configuration group at this level";
                                    }

                                    container drop {
                                        description "Enter the drop context";

                                        leaf admin-state {
                                            type types-sros:admin-state;
                                            default "enable";
                                            description "Administrative state of the drop action";
                                        }

                                    } // container drop

                                    container stats-collection {
                                        description "Enter the stats-collection context";

                                        leaf admin-state {
                                            type types-sros:admin-state;
                                            default "enable";
                                            description "Administrative state of filter statistics collection";
                                        }

                                    } // container stats-collection

                                } // container actions

                                container match-criteria {
                                    description "Enter the match-criteria context";

                                    leaf-list apply-groups {
                                        type leafref {
                                            path "../../../../../../../../groups/group/name";
                                        }
                                        max-elements 8;
                                        ordered-by user;
                                        description "Apply a configuration group at this level";
                                    }

                                    leaf-list apply-groups-exclude {
                                        type leafref {
                                            path "../../../../../../../../groups/group/name";
                                        }
                                        max-elements 8;
                                        ordered-by user;
                                        description "Exclude a configuration group at this level";
                                    }

                                    container dscp {
                                        description "Enter the dscp context";

                                        leaf admin-state {
                                            type types-sros:admin-state;
                                            default "enable";
                                            description "Administrative state of the DSCP match";
                                        }

                                    } // container dscp

                                    container dst-ip-lsb {
                                        description "Enter the dst-ip-lsb context";

                                        leaf admin-state {
                                            type types-sros:admin-state;
                                            default "disable";
                                            description "Administrative state of the destination IP LSB match";
                                        }

                                    } // container dst-ip-lsb

                                    container dst-ip-msb {
                                        description "Enter the dst-ip-msb context";

                                        leaf admin-state {
                                            type types-sros:admin-state;
                                            default "enable";
                                            description "Administrative state of the destination IP MSB match";
                                        }

                                    } // container dst-ip-msb

                                    container dst-port {
                                        description "Enter the dst-port context";

                                        leaf admin-state {
                                            type types-sros:admin-state;
                                            default "enable";
                                            description "Administrative state of the destination port match";
                                        }

                                    } // container dst-port

                                    container flow-label {
                                        description "Enter the flow-label context";

                                        leaf admin-state {
                                            type types-sros:admin-state;
                                            default "enable";
                                            description "Administrative state of the flow label match";
                                        }

                                    } // container flow-label

                                    container icmp-code {
                                        description "Enter the icmp-code context";

                                        leaf admin-state {
                                            type types-sros:admin-state;
                                            default "disable";
                                            description "Administrative state of the ICMP code matching";
                                        }

                                    } // container icmp-code

                                    container icmp-type {
                                        description "Enter the icmp-type context";

                                        leaf admin-state {
                                            type types-sros:admin-state;
                                            default "disable";
                                            description "Administrative state of the ICMP type matching";
                                        }

                                    } // container icmp-type

                                    container next-header {
                                        description "Enter the next-header context";

                                        leaf admin-state {
                                            type types-sros:admin-state;
                                            default "enable";
                                            description "Administrative state of next-header match";
                                        }

                                    } // container next-header

                                    container src-ip-lsb {
                                        description "Enter the src-ip-lsb context";

                                        leaf admin-state {
                                            type types-sros:admin-state;
                                            default "enable";
                                            description "Administrative state of source IP LSB match";
                                        }

                                    } // container src-ip-lsb

                                    container src-ip-msb {
                                        description "Enter the src-ip-msb context";

                                        leaf admin-state {
                                            type types-sros:admin-state;
                                            default "enable";
                                            description "Administrative state of the source IP MSB match";
                                        }

                                    } // container src-ip-msb

                                    container src-port {
                                        description "Enter the src-port context";

                                        leaf admin-state {
                                            type types-sros:admin-state;
                                            default "enable";
                                            description "Administrative state of the source port match";
                                        }

                                    } // container src-port

                                    container tcp-flags {
                                        description "Enter the tcp-flags context";

                                        leaf admin-state {
                                            type types-sros:admin-state;
                                            default "enable";
                                            description "Administrative state of the TCP flags match";
                                        }

                                    } // container tcp-flags

                                    container tcp-flags-ext {
                                        description "Enter the tcp-flags-ext context";

                                        leaf admin-state {
                                            type types-sros:admin-state;
                                            default "disable";
                                            description "Administrative state of the extended TCP flags";
                                        }

                                    } // container tcp-flags-ext

                                } // container match-criteria

                            } // container ipv6-filter

                        } // container egress

                    } // container filter

                    container statistics {
                        description "Enter the statistics context";

                        container policer {
                            description "Enter the policer context";

                            leaf banks {
                                type uint32 {
                                    range "0|1|2|4";
                                }
                                description "Number of policer banks";
                            }

                            leaf dedicated-fc-policers {
                                type uint32 {
                                    range "0..10816";
                                }
                                description "Number of resources allocated to FC policer statistics";
                            }

                        } // container policer

                        container filter {
                            description "Enter the filter context";

                            leaf ingress-banks {
                                type uint32 {
                                    range "0..4";
                                }
                                default "0";
                                description "Number of ingress banks";
                            }

                            leaf egress-banks {
                                type uint32 {
                                    range "0..4";
                                }
                                default "0";
                                description "Number of egress banks";
                            }

                        } // container filter

                    } // container statistics

                    list pool {
                        key "pool-id";
                        description "Enter the pool list instance";

                        leaf pool-id {
                            type uint32 {
                                range "1..2";
                            }
                            description "Pool identifier";
                        }

                        leaf-list apply-groups {
                            type leafref {
                                path "../../../../../groups/group/name";
                            }
                            max-elements 8;
                            ordered-by user;
                            description "Apply a configuration group at this level";
                        }

                        leaf-list apply-groups-exclude {
                            type leafref {
                                path "../../../../../groups/group/name";
                            }
                            max-elements 8;
                            ordered-by user;
                            description "Exclude a configuration group at this level";
                        }

                        container lag-bundle {
                            description "Enter the lag-bundle context";

                            leaf reserved-member-count {
                                type uint32 {
                                    range "2|4|8|16|32|64";
                                }
                                default "64";
                                description "Member count reserved for LAG bundle";
                            }

                        } // container lag-bundle

                    } // list pool

                    container fec {
                        description "Enter the fec context";

                        container system-wide {
                            description "Enter the system-wide context";

                            leaf unpaired {
                                type uint32 {
                                    range "2..10240";
                                }
                                description "Number of system-wide unpaired FEC space";
                            }

                            leaf paired {
                                type uint32 {
                                    range "0..8192";
                                }
                                description "Number of paired FECs available";
                            }

                        } // container system-wide

                    } // container fec

                    container lpm {
                        description "Enter the lpm context";

                        list scale-option {
                            key "option";
                            description "Enter the scale-option list instance";

                            leaf option {
                                type uint32 {
                                    range "1..4";
                                }
                                description "Unique LPM (FIB) scale option";
                            }

                            leaf admin-state {
                                type types-sros:admin-state;
                                description "Administrative state of the LPM (FIB) scale option";
                            }

                            leaf-list apply-groups {
                                type leafref {
                                    path "../../../../../../groups/group/name";
                                }
                                max-elements 8;
                                ordered-by user;
                                description "Apply a configuration group at this level";
                            }

                            leaf-list apply-groups-exclude {
                                type leafref {
                                    path "../../../../../../groups/group/name";
                                }
                                max-elements 8;
                                ordered-by user;
                                description "Exclude a configuration group at this level";
                            }

                        } // list scale-option

                    } // container lpm

                    container policer-and-statistics-override {
                        description "Enter the policer-and-statistics-override context";

                        leaf admin-state {
                            type types-sros:admin-state;
                            default "disable";
                            description "Administrative state of policer and statistics override";
                        }

                        leaf-list apply-groups {
                            type leafref {
                                path "../../../../../groups/group/name";
                            }
                            max-elements 8;
                            ordered-by user;
                            description "Apply a configuration group at this level";
                        }

                        leaf-list apply-groups-exclude {
                            type leafref {
                                path "../../../../../groups/group/name";
                            }
                            max-elements 8;
                            ordered-by user;
                            description "Exclude a configuration group at this level";
                        }

                        list bank {
                            key "bank-name";
                            description "Enter the bank list instance";

                            leaf bank-name {
                                type enumeration {
                                    enum dual-mode-16k-bank-1           { value 1; }
                                    enum dual-mode-16k-bank-2           { value 2; }
                                    enum dual-mode-16k-bank-3           { value 3; }
                                    enum dual-mode-16k-bank-4           { value 4; }
                                    enum dual-mode-16k-bank-5           { value 5; }
                                    enum dual-mode-16k-bank-6           { value 6; }
                                }
                                description "Bank name";
                            }

                            leaf-list apply-groups {
                                type leafref {
                                    path "../../../../../../groups/group/name";
                                }
                                max-elements 8;
                                ordered-by user;
                                description "Apply a configuration group at this level";
                            }

                            leaf-list apply-groups-exclude {
                                type leafref {
                                    path "../../../../../../groups/group/name";
                                }
                                max-elements 8;
                                ordered-by user;
                                description "Exclude a configuration group at this level";
                            }

                            container application {
                                description "Enter the application context";

                                leaf group {
                                    type int32 {
                                        range "1..3";
                                    }
                                    description "Group associated to a bank";
                                }

                                leaf binding {
                                    type enumeration {
                                        enum policer                        { value 1; }
                                        enum statistics                     { value 2; }
                                    }
                                    description "Application to allocate bank resources";
                                }

                            } // container application

                        } // list bank

                        container application-group {
                            description "Enter the application-group context";

                            list group {
                                key "group-id";
                                description "Enter the group list instance";

                                leaf group-id {
                                    type uint32 {
                                        range "1..3";
                                    }
                                    description "Application group ID";
                                }

                                leaf-list apply-groups {
                                    type leafref {
                                        path "../../../../../../../groups/group/name";
                                    }
                                    max-elements 8;
                                    ordered-by user;
                                    description "Apply a configuration group at this level";
                                }

                                leaf-list apply-groups-exclude {
                                    type leafref {
                                        path "../../../../../../../groups/group/name";
                                    }
                                    max-elements 8;
                                    ordered-by user;
                                    description "Exclude a configuration group at this level";
                                }

                                container policers {
                                    description "Enter the policers context";

                                    list application {
                                        key "application-id";
                                        description "Enter the application list instance";

                                        leaf application-id {
                                            type enumeration {
                                                enum per-fc-unicast-broadcast-unknown-multicast { value 1; }
                                                enum per-fc-unicast-multipoint      { value 2; }
                                                enum per-fc                         { value 3; }
                                                enum per-2-fc-unicast-multipoint    { value 4; }
                                                enum per-4-fc-unicast-multipoint    { value 5; }
                                                enum per-2-fc                       { value 6; }
                                                enum per-4-fc                       { value 7; }
                                                enum aggregate-policers             { value 8; }
                                                enum shared-policers                { value 9; }
                                            }
                                            description "FC policer type";
                                        }

                                        leaf scale {
                                            type int32 {
                                                range "0..96";
                                            }
                                            description "Number of policers to allocate to the group";
                                        }

                                        leaf-list apply-groups {
                                            type leafref {
                                                path "../../../../../../../../../groups/group/name";
                                            }
                                            max-elements 8;
                                            ordered-by user;
                                            description "Apply a configuration group at this level";
                                        }

                                        leaf-list apply-groups-exclude {
                                            type leafref {
                                                path "../../../../../../../../../groups/group/name";
                                            }
                                            max-elements 8;
                                            ordered-by user;
                                            description "Exclude a configuration group at this level";
                                        }

                                    } // list application

                                } // container policers

                                container statistics {
                                    description "Enter the statistics context";

                                    list application {
                                        key "application-id";
                                        description "Enter the application list instance";

                                        leaf application-id {
                                            type enumeration {
                                                enum aggregate-policers             { value 8; }
                                                enum shared-policers                { value 9; }
                                                enum fc-policers                    { value 10; }
                                            }
                                            description "FC policer type";
                                        }

                                        leaf scale {
                                            type int32 {
                                                range "0..96";
                                            }
                                            description "Number of policer statistics to allocate to the group";
                                        }

                                        leaf-list apply-groups {
                                            type leafref {
                                                path "../../../../../../../../../groups/group/name";
                                            }
                                            max-elements 8;
                                            ordered-by user;
                                            description "Apply a configuration group at this level";
                                        }

                                        leaf-list apply-groups-exclude {
                                            type leafref {
                                                path "../../../../../../../../../groups/group/name";
                                            }
                                            max-elements 8;
                                            ordered-by user;
                                            description "Exclude a configuration group at this level";
                                        }

                                    } // list application

                                } // container statistics

                            } // list group

                        } // container application-group

                    } // container policer-and-statistics-override

                    container segment-routing-v6 {
                        description "Enter the segment-routing-v6 context";

                        container tunnel-termination {
                            description "Enter the tunnel-termination context";

                            leaf entries {
                                type uint32 {
                                    range "256|1024|2048";
                                }
                                default "256";
                                description "Maximum SRv6 tunnel termination TCAM entries";
                            }

                        } // container tunnel-termination

                    } // container segment-routing-v6


                } // container resource-allocation

            } // container fp

            list transmission-profile {
                key "name";
                description "Enter the transmission-profile list instance";

                leaf name {
                    type types-sros:named-item;
                    description "File transmission profile name";
                }

                leaf ipv4-source-address {
                    type types-sros:ipv4-unicast-address;
                    description "IPv4 source address used for the transport protocol";
                }

                leaf ipv6-source-address {
                    type types-sros:ipv6-address;
                    description "IPv6 source address used for the transport protocol";
                }

                leaf redirection {
                    type uint32 {
                        range "1..8";
                    }
                    description "Maximum level of redirection";
                }

                leaf retry {
                    type uint32 {
                        range "1..256";
                    }
                    description "Number of attempts to reconnecting to the server";
                }

                leaf router-instance {
                    type types-sros:router-instance-base-management-vprn-loose;
                    default "Base";
                    description "Router instance used by the transport protocol";
                }

                leaf timeout {
                    type uint32 {
                        range "1..3600";
                    }
                    units "seconds";
                    default "60";
                    description "Timeout for a response from the server";
                }

                leaf http-version {
                    type types-system:http-version-type;
                    description "HTTP version";
                }

                leaf-list apply-groups {
                    type leafref {
                        path "../../../groups/group/name";
                    }
                    max-elements 8;
                    ordered-by user;
                    description "Apply a configuration group at this level";
                }

                leaf-list apply-groups-exclude {
                    type leafref {
                        path "../../../groups/group/name";
                    }
                    max-elements 8;
                    ordered-by user;
                    description "Exclude a configuration group at this level";
                }

            } // list transmission-profile

            container grpc {
                description "Enter the grpc context";

                leaf admin-state {
                    type types-sros:admin-state;
                    default "disable";
                    description "Administrative state of the gRPC server";
                }

                leaf listening-port {
                    type types-sros:tcp-udp-port-non-zero {
                        range "1024..49151|57400";
                    }
                    default "57400";
                    description "Listening port for the gRPC server";
                }

                leaf delay-on-boot {
                    type uint16 {
                        range "1..3600";
                    }
                    units "seconds";
                    description "Delay for gRPC connections after system boot";
                }

                leaf max-msg-size {
                    type uint32 {
                        range "1..1024";
                    }
                    units "megabytes";
                    default "512";
                    description "Maximum size of received message";
                }

                leaf-list apply-groups {
                    type leafref {
                        path "../../../groups/group/name";
                    }
                    max-elements 8;
                    ordered-by user;
                    description "Apply a configuration group at this level";
                }

                leaf-list apply-groups-exclude {
                    type leafref {
                        path "../../../groups/group/name";
                    }
                    max-elements 8;
                    ordered-by user;
                    description "Exclude a configuration group at this level";
                }

                choice transport {
                    case tls-server-profile {

                        leaf tls-server-profile {
                            type leafref {
                                path "../../security/tls/server-tls-profile/server-profile-name";
                            }
                            description "Preferred TLS server profile";
                        }

                    }
                    case allow-unsecure-connection {

                        leaf allow-unsecure-connection {
                            type empty;
                            description "Allow connection without secured transport protocol";
                        }

                    }
                }
                container tcp-keepalive {
                    description "Enter the tcp-keepalive context";

                    leaf admin-state {
                        type types-sros:admin-state;
                        default "disable";
                        description "Administrative state of the TCP keepalive algorithm";
                    }

                    leaf idle-time {
                        type types-sros:time-duration {
                            range "1..100000";
                        }
                        units "seconds";
                        default "600";
                        description "Time until the first TCP keepalive probe is sent";
                    }

                    leaf interval {
                        type types-sros:time-duration {
                            range "1..100000";
                        }
                        units "seconds";
                        default "15";
                        description "Time between TCP keep-alive probes";
                    }

                    leaf retries {
                        type uint32 {
                            range "3..100";
                        }
                        default "4";
                        description "Number of probe retries before closing the connection";
                    }

                } // container tcp-keepalive

                container gnmi {
                    description "Enter the gnmi context";

                    leaf admin-state {
                        type types-sros:admin-state;
                        default "enable";
                        description "Administrative state of the gNMI service";
                    }

                    leaf proto-version {
                        type enumeration {
                            enum latest {
                                value 0;
                                description "Latest supported version";
                            }
                            enum v070 {
                                value 1;
                                description "gNMI version 0.7.0";
                            }
                        }
                        default "latest";
                        description "gnmi.proto version";
                    }

                    leaf auto-config-save {
                        type boolean;
                        default "true";
                        description "Automatically save configuration as part of commit";
                    }

                } // container gnmi

                container gnoi {
                    description "Enter the gnoi context";

                    container cert-mgmt {
                        description "Enter the cert-mgmt context";

                        leaf admin-state {
                            type types-sros:admin-state;
                            default "disable";
                            description "Administrative state of gNOI CertificateManagement";
                        }

                    } // container cert-mgmt

                    container file {
                        description "Enter the file context";

                        leaf admin-state {
                            type types-sros:admin-state;
                            default "disable";
                            description "Administrative state of the gNOI File service";
                        }

                    } // container file

                    container system {
                        description "Enter the system context";

                        leaf admin-state {
                            type types-sros:admin-state;
                            default "disable";
                            description "Administrative state of the gNOI System service";
                        }

                    } // container system

                } // container gnoi

                container md-cli {
                    description "Enter the md-cli context";

                    leaf admin-state {
                        type types-sros:admin-state;
                        default "disable";
                        description "Administrative state of the MD-CLI service";
                    }

                } // container md-cli

                container rib-api {
                    description "Enter the rib-api context";

                    leaf admin-state {
                        type types-sros:admin-state;
                        default "disable";
                        description "Administrative state of the RIB API service";
                    }

                    leaf purge-timeout {
                        type types-sros:time-duration {
                            range "1..100000";
                        }
                        units "seconds";
                        description "Time until stale entries are purged";
                    }

                } // container rib-api

            } // container grpc

            container grpc-tunnel {
                description "Enter the grpc-tunnel context";

                leaf delay-on-boot {
                    type uint16 {
                        range "1..3600";
                    }
                    units "seconds";
                    description "Delay for gRPC tunnels after system boot";
                }

                leaf-list apply-groups {
                    type leafref {
                        path "../../../groups/group/name";
                    }
                    max-elements 8;
                    ordered-by user;
                    description "Apply a configuration group at this level";
                }

                leaf-list apply-groups-exclude {
                    type leafref {
                        path "../../../groups/group/name";
                    }
                    max-elements 8;
                    ordered-by user;
                    description "Exclude a configuration group at this level";
                }

                list destination-group {
                    key "name";
                    max-elements 4;
                    description "Enter the destination-group list instance";

                    leaf name {
                        type types-sros:named-item;
                        description "Destination group name";
                    }

                    leaf description {
                        type types-sros:description;
                        description "Text description";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                    choice transport {
                        case tls-client-profile {

                            leaf tls-client-profile {
                                type leafref {
                                    path "../../../security/tls/client-tls-profile/client-profile-name";
                                }
                                description "TLS client profile assigned to the destination group";
                            }

                        }
                        case allow-unsecure-connection {

                            leaf allow-unsecure-connection {
                                type empty;
                                description "Allow unsecured operation of gRPC connections";
                            }

                        }
                    }
                    container tcp-keepalive {
                        description "Enter the tcp-keepalive context";

                        leaf admin-state {
                            type types-sros:admin-state;
                            default "disable";
                            description "Administrative state of the TCP keepalive algorithm";
                        }

                        leaf idle-time {
                            type types-sros:time-duration {
                                range "1..100000";
                            }
                            units "seconds";
                            default "600";
                            description "Time until the first TCP keepalive probe is sent";
                        }

                        leaf interval {
                            type types-sros:time-duration {
                                range "1..100000";
                            }
                            units "seconds";
                            default "15";
                            description "Time between TCP keep-alive probes";
                        }

                        leaf retries {
                            type uint32 {
                                range "3..100";
                            }
                            default "4";
                            description "Number of probe retries before closing the connection";
                        }

                    } // container tcp-keepalive

                    list destination {
                        key "address port";
                        max-elements 4;
                        ordered-by user;
                        description "Enter the destination list instance";

                        leaf address {
                            type union {
                                type types-sros:ip-address;
                                type types-sros:fully-qualified-domain-name;
                            }
                            description "Address of the destination within the destination group";
                        }

                        leaf port {
                            type types-sros:tcp-udp-port-non-zero;
                            description "TCP port number for the destination";
                        }

                        leaf router-instance {
                            type string;
                            description "Router instance for the destination group";
                        }

                        leaf local-source-address {
                            type types-sros:ip-address;
                            description "Local IP address of packets sent from the source";
                        }

                        leaf originated-qos-marking {
                            type types-qos:dscp-name;
                            description "QoS marking used for gRPC tunnel packets";
                        }

                        leaf-list apply-groups {
                            type leafref {
                                path "../../../../../groups/group/name";
                            }
                            max-elements 8;
                            ordered-by user;
                            description "Apply a configuration group at this level";
                        }

                        leaf-list apply-groups-exclude {
                            type leafref {
                                path "../../../../../groups/group/name";
                            }
                            max-elements 8;
                            ordered-by user;
                            description "Exclude a configuration group at this level";
                        }

                    } // list destination

                } // list destination-group

                list tunnel {
                    key "name";
                    max-elements 4;
                    description "Enter the tunnel list instance";

                    leaf name {
                        type types-sros:named-item;
                        description "Tunnel name";
                    }

                    leaf admin-state {
                        type types-sros:admin-state;
                        default "disable";
                        description "Administrative state of the tunnel";
                    }

                    leaf description {
                        type types-sros:description;
                        description "Text description";
                    }

                    leaf destination-group {
                        type leafref {
                            path "../../destination-group/name";
                        }
                        description "Destination group used in the tunnel";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                    container target-name {
                        description "Enter the target-name context";

                        choice tunnel-identifier {
                            case custom-string {

                                leaf custom-string {
                                    type types-sros:named-item-64;
                                    description "Custom target name";
                                }

                            }
                            case user-agent {

                                leaf user-agent {
                                    type empty;
                                    description "Set the user agent as the target name";
                                }

                            }
                            case node-name {

                                leaf node-name {
                                    type empty;
                                    description "Set the node name as target name";
                                }

                            }
                        }
                    } // container target-name

                    list handler {
                        key "name";
                        max-elements 8;
                        description "Enter the handler list instance";

                        leaf name {
                            type types-sros:named-item;
                            description "Handler name";
                        }

                        leaf admin-state {
                            type types-sros:admin-state;
                            default "disable";
                            description "Administrative state of the handler";
                        }

                        leaf port {
                            type types-sros:tcp-udp-port-non-zero;
                            description "TCP port number the handler listens to internally";
                        }

                        leaf-list apply-groups {
                            type leafref {
                                path "../../../../../groups/group/name";
                            }
                            max-elements 8;
                            ordered-by user;
                            description "Apply a configuration group at this level";
                        }

                        leaf-list apply-groups-exclude {
                            type leafref {
                                path "../../../../../groups/group/name";
                            }
                            max-elements 8;
                            ordered-by user;
                            description "Exclude a configuration group at this level";
                        }

                        container target-type {
                            description "Enter the target-type context";

                            choice application {
                                case custom-type {

                                    leaf custom-type {
                                        type string {
                                            length "1..64";
                                            pattern "[_0-9A-Z]+" {
                                                error-message "must only contain uppercase letters, digits or underscores";
                                            }
                                        }
                                        description "Custom string for target type";
                                    }

                                }
                                case grpc-server {

                                    leaf grpc-server {
                                        type empty;
                                        description "Target type set to GNMI_GNOI";
                                    }

                                }
                                case ssh-server {

                                    leaf ssh-server {
                                        type empty;
                                        description "Target type is SSH";
                                    }

                                }
                            }
                        } // container target-type

                    } // list handler

                } // list tunnel

            } // container grpc-tunnel

            container management-interface {
                description "Enter the management-interface context";

                leaf configuration-mode {
                    type enumeration {
                        enum classic                        { value 1; }
                        enum model-driven                   { value 2; }
                        enum mixed                          { value 3; }
                    }
                    description "Management interfaces allowed to edit the configuration";
                }

                leaf schema-path {
                    type types-sros:url;
                    description "Schema path URL";
                }

                leaf commit-history {
                    type uint32 {
                        range "0..200";
                    }
                    default "50";
                    description "Number of commit history IDs to store";
                }

                leaf-list apply-groups {
                    type leafref {
                        path "../../../groups/group/name";
                    }
                    max-elements 8;
                    ordered-by user;
                    description "Apply a configuration group at this level";
                }

                leaf-list apply-groups-exclude {
                    type leafref {
                        path "../../../groups/group/name";
                    }
                    max-elements 8;
                    ordered-by user;
                    description "Exclude a configuration group at this level";
                }

                container cli {
                    description "Enter the cli context";

                    leaf-list cli-engine {
                        type types-system:cli-engine-type;
                        max-elements 2;
                        ordered-by user;
                        description "System-wide CLI engine access";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                    container classic-cli {
                        description "Enter the classic-cli context";

                        leaf allow-immediate {
                            type boolean;
                            default "true";
                            description "Allow writable access in classic CLI configure branch";
                        }

                        container rollback {
                            description "Enter the rollback context";

                            leaf location {
                                type types-sros:url;
                                description "Path and filename prefix for rollback checkpoint files";
                            }

                            leaf local-checkpoints {
                                type uint32 {
                                    range "1..50";
                                }
                                default "10";
                                description "Maximum number of rollback files on local storage";
                            }

                            leaf remote-checkpoints {
                                type uint32 {
                                    range "1..200";
                                }
                                default "10";
                                description "Maximum rollback files saved at a remote location";
                            }

                            leaf-list apply-groups {
                                type leafref {
                                    path "../../../../../../groups/group/name";
                                }
                                max-elements 8;
                                ordered-by user;
                                description "Apply a configuration group at this level";
                            }

                            leaf-list apply-groups-exclude {
                                type leafref {
                                    path "../../../../../../groups/group/name";
                                }
                                max-elements 8;
                                ordered-by user;
                                description "Exclude a configuration group at this level";
                            }

                            container rescue {
                                description "Enter the rescue context";

                                leaf location {
                                    type types-sros:url;
                                    description "Location of the rescue configuration file";
                                }

                            } // container rescue

                        } // container rollback

                    } // container classic-cli

                    container md-cli {
                        description "Enter the md-cli context";

                        leaf auto-config-save {
                            type boolean;
                            default "true";
                            description "Automatically save configuration as part of commit";
                        }

                        leaf command-accounting-during-load {
                            status obsolete;
                            type boolean;
                            default "true";
                            description "Perform remote command accounting during a load or rollback operation";
                        }

                        leaf-list apply-groups {
                            type leafref {
                                path "../../../../../groups/group/name";
                            }
                            max-elements 8;
                            ordered-by user;
                            description "Apply a configuration group at this level";
                        }

                        leaf-list apply-groups-exclude {
                            type leafref {
                                path "../../../../../groups/group/name";
                            }
                            max-elements 8;
                            ordered-by user;
                            description "Exclude a configuration group at this level";
                        }

                        container environment {
                            description "Enter the environment context";

                            leaf more {
                                type boolean;
                                default "true";
                                description "Activate the pager when output is longer than a screen";
                            }

                            leaf time-display {
                                type enumeration {
                                    enum local                          { value 1; }
                                    enum utc                            { value 2; }
                                }
                                default "local";
                                description "Time zone to display time";
                            }

                            leaf time-format {
                                type enumeration {
                                    enum iso-8601                       { value 1; }
                                    enum rfc-1123                       { value 2; }
                                    enum rfc-3339                       { value 3; }
                                }
                                default "rfc-3339";
                                description "Format to display the date and time";
                            }

                            container command-alias {
                                description "Enter the command-alias context";

                                list alias {
                                    key "alias-name";
                                    description "Enter the alias list instance";

                                    leaf alias-name {
                                        type string {
                                            length "1..64";
                                            pattern "[_a-zA-Z0-9][-_a-zA-Z0-9]*" {
                                                error-message "must only contain alpha-numeric characters, underscore or hyphen (not as the first character)";
                                            }
                                        }
                                        description "Alias name";
                                    }

                                    leaf admin-state {
                                        type types-sros:admin-state;
                                        default "disable";
                                        description "Administrative state of the alias";
                                    }

                                    leaf description {
                                        type types-sros:string-not-all-spaces {
                                            length "1..110";
                                        }
                                        description "Alias description";
                                    }

                                    leaf-list apply-groups {
                                        type leafref {
                                            path "../../../../../../../../groups/group/name";
                                        }
                                        max-elements 8;
                                        ordered-by user;
                                        description "Apply a configuration group at this level";
                                    }

                                    leaf-list apply-groups-exclude {
                                        type leafref {
                                            path "../../../../../../../../groups/group/name";
                                        }
                                        max-elements 8;
                                        ordered-by user;
                                        description "Exclude a configuration group at this level";
                                    }

                                    choice alias-expansion {
                                        mandatory true;
                                        case python {

                                            leaf python-script {
                                                type leafref {
                                                    path "../../../../../../../../python/python-script/name";
                                                }
                                                description "Python script to run when executing the alias";
                                            }

                                        }
                                        case cli {

                                            leaf cli-command {
                                                type string {
                                                    length "1..255";
                                                }
                                                description "CLI command to run when executing the alias";
                                            }

                                        }
                                    }
                                    list mount-point {
                                        key "path";
                                        min-elements 1;
                                        description "Add a list entry for mount-point";

                                        leaf path {
                                            type union {
                                                type enumeration {
                                                    enum global                         { value 0; }
                                                }
                                                type string {
                                                    length "1..255";
                                                    pattern "/.*" {
                                                        error-message "must start with forward slash";
                                                    }
                                                }
                                            }
                                            description "Mount point where the alias is available";
                                        }

                                    } // list mount-point

                                } // list alias

                            } // container command-alias

                            container command-completion {
                                description "Enter the command-completion context";

                                leaf enter {
                                    type boolean;
                                    default "true";
                                    description "Complete the command when the Enter key is pressed";
                                }

                                leaf space {
                                    type boolean;
                                    default "true";
                                    description "Complete the command when the Space key is pressed";
                                }

                                leaf tab {
                                    type boolean;
                                    default "true";
                                    description "Complete the command when the Tab key is pressed";
                                }

                            } // container command-completion


                            container console {
                                description "Enter the console context";

                                leaf length {
                                    type uint32 {
                                        range "24..512";
                                    }
                                    default "24";
                                    description "Number of lines displayed on the console";
                                }

                                leaf width {
                                    type uint32 {
                                        range "80..512";
                                    }
                                    default "80";
                                    description "Number of columns displayed on the console";
                                }

                            } // container console

                            container history {
                                description "Enter the history context";

                                leaf recall {
                                    type boolean;
                                    default "true";
                                    description "Allow command history recall and search execution";
                                }

                                leaf size {
                                    type uint16 {
                                        range "0..1000";
                                    }
                                    default "50";
                                    description "Command history size";
                                }

                            } // container history

                            container info-output {
                                description "Enter the info-output context";

                                container always-display {
                                    description "Enter the always-display context";

                                    leaf admin-state {
                                        type boolean;
                                        default "false";
                                        description "Always display admin-state elements";
                                    }

                                } // container always-display

                            } // container info-output

                            container message-severity-level {
                                description "Enter the message-severity-level context";

                                leaf cli {
                                    type enumeration {
                                        enum warning                        { value 6; }
                                        enum info                           { value 7; }
                                    }
                                    default "info";
                                    description "Message severity threshold for CLI messages";
                                }

                            } // container message-severity-level

                            container progress-indicator {
                                description "Enter the progress-indicator context";

                                leaf admin-state {
                                    type types-sros:admin-state;
                                    default "enable";
                                    description "Administrative state of the progress indicator";
                                }

                                leaf type {
                                    type enumeration {
                                        enum dots                           { value 1; }
                                    }
                                    default "dots";
                                    description "Progress indicator output style";
                                }

                                leaf delay {
                                    type uint32 {
                                        range "0..10000";
                                    }
                                    units "milliseconds";
                                    default "1000";
                                    description "Delay before the progress indicator is displayed";
                                }

                            } // container progress-indicator

                            container prompt {
                                description "Enter the prompt context";

                                leaf context {
                                    type boolean;
                                    default "true";
                                    description "Show the current command context in the prompt";
                                }

                                leaf newline {
                                    type boolean;
                                    default "true";
                                    description "Add a new line before every prompt line";
                                }

                                leaf timestamp {
                                    type boolean;
                                    default "false";
                                    description "Show the timestamp before the first prompt line";
                                }

                                leaf uncommitted-changes-indicator {
                                    type boolean;
                                    default "true";
                                    description "Show an asterisk (*) when uncommitted changes exist";
                                }

                            } // container prompt

                            container python {
                                description "Enter the python context";

                                leaf memory-reservation {
                                    type uint32 {
                                        range "1..500";
                                    }
                                    units "megabytes";
                                    description "Memory reserved per Python interpreter";
                                }

                                leaf minimum-available-memory {
                                    type uint32 {
                                        range "5..50";
                                    }
                                    units "percent";
                                    description "Minimum memory requirement to run a Python interpreter";
                                }

                                leaf timeout {
                                    type uint32 {
                                        range "30..86400";
                                    }
                                    units "seconds";
                                    default "3600";
                                    description "Maximum run time before a Python application is stopped";
                                }

                            } // container python

                        } // container environment

                    } // container md-cli

                } // container cli

                container configuration-save {
                    description "Enter the configuration-save context";

                    leaf configuration-backups {
                        type uint32 {
                            range "1..200";
                        }
                        default "50";
                        description "Maximum number of configuration versions maintained";
                    }

                    leaf incremental-saves {
                        type boolean;
                        default "true";
                        description "Use incremental saved configuration files";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                } // container configuration-save

                container netconf {
                    description "Enter the netconf context";

                    leaf admin-state {
                        status obsolete;
                        type types-sros:admin-state;
                        default "disable";
                        description "Administrative state of NETCONF";
                    }

                    leaf port {
                        status obsolete;
                        type uint32 {
                            range "22|830";
                        }
                        default "830";
                        description "Port on which NETCONF server listens for connections";
                    }

                    leaf delay-on-boot {
                        status obsolete;
                        type uint16 {
                            range "1..3600";
                        }
                        units "seconds";
                        description "Delay for NETCONF connections after system boot";
                    }

                    leaf auto-config-save {
                        type boolean;
                        default "true";
                        description "Automatically save configuration as part of commit";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                    container capabilities {
                        description "Enter the capabilities context";

                        leaf candidate {
                            type boolean;
                            default "true";
                            description "Allow the NETCONF server to access candidate datastore";
                        }

                        leaf writable-running {
                            status obsolete;
                            type boolean;
                            default "false";
                            description "Allow NETCONF server to access the running datastore";
                        }

                    } // container capabilities

                    container listen {
                        description "Enter the listen context";

                        leaf admin-state {
                            type types-sros:admin-state;
                            default "disable";
                            description "Administrative state of NETCONF server in listen mode";
                        }

                        leaf port {
                            type uint32 {
                                range "22|830";
                            }
                            default "830";
                            description "Port on which NETCONF server listens for connections";
                        }

                        leaf delay-on-boot {
                            type uint16 {
                                range "1..3600";
                            }
                            units "seconds";
                            description "Delay before NETCONF server is operational after boot";
                        }

                    } // container listen


                } // container netconf

                container operations {
                    description "Enter the operations context";

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                    container global-timeouts {
                        description "Enter the global-timeouts context";

                        leaf asynchronous-execution {
                            type types-operation:operation-timeout;
                            default "3600";
                            description "Timeout for asynchronous operation execution";
                        }

                        leaf asynchronous-retention {
                            type types-operation:operation-timeout;
                            default "86400";
                            description "Timeout for asynchronous operation data retention";
                        }

                        leaf synchronous-execution {
                            type types-operation:operation-timeout;
                            default "never";
                            description "Timeout for synchronous operation execution";
                        }

                    } // container global-timeouts

                } // container operations

                container remote-management {
                    description "Enter the remote-management context";

                    leaf admin-state {
                        type types-sros:admin-state;
                        default "disable";
                        description "Administrative state of remote management registration";
                    }

                    leaf delay-on-boot {
                        type uint16 {
                            range "1..3600";
                        }
                        units "seconds";
                        description "Delay for remote management after system boot";
                    }

                    leaf connection-timeout {
                        type uint32 {
                            range "1..3600";
                        }
                        units "seconds";
                        default "60";
                        description "Time without a response before manager declared down";
                    }

                    leaf hello-interval {
                        type types-sros:time-duration {
                            range "10..216000";
                        }
                        units "seconds";
                        default "600";
                        description "Time between hello messages from SR OS node to manager";
                    }

                    leaf router-instance {
                        type string;
                        default "management";
                        description "Router name or VPRN service name";
                    }

                    leaf device-label {
                        type types-sros:named-item-64;
                        description "Device label supplied to the remote manager";
                    }

                    leaf device-name {
                        type types-sros:named-item-64;
                        description "Device name supplied to the remote manager";
                    }

                    leaf source-address {
                        type types-sros:ip-address;
                        description "Source IP address for connection to the manager";
                    }

                    leaf source-port {
                        type types-system:remote-mgmt-registration-port;
                        default "grpc-default";
                        description "Source TCP port number to connection to the manager";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                    choice transport {
                        case client-tls-profile {

                            leaf client-tls-profile {
                                type leafref {
                                    path "../../../security/tls/client-tls-profile/client-profile-name";
                                }
                                description "TLS client profile name";
                            }

                        }
                        case allow-unsecure-connection {

                            leaf allow-unsecure-connection {
                                type empty;
                                description "Allow connection without secured transport protocol";
                            }

                        }
                    }
                    list manager {
                        key "manager-name";
                        max-elements 2;
                        description "Enter the manager list instance";

                        leaf manager-name {
                            type types-sros:named-item-64;
                            description "Remote management manager name";
                        }

                        leaf admin-state {
                            type types-sros:admin-state;
                            default "disable";
                            description "Administrative state of remote management registration";
                        }

                        leaf connection-timeout {
                            type uint32 {
                                range "1..3600";
                            }
                            units "seconds";
                            description "Time without response before manager is declared down";
                        }

                        leaf description {
                            type types-sros:description;
                            description "Text description";
                        }

                        leaf manager-address {
                            type union {
                                type types-sros:ip-address;
                                type types-sros:fully-qualified-domain-name;
                            }
                            description "Destination IP address of the manager";
                        }

                        leaf manager-port {
                            type types-sros:tcp-udp-port-non-zero;
                            default "57400";
                            description "Destination TCP port for gRPC connections to manager";
                        }

                        leaf router-instance {
                            type string;
                            description "Reference to a router or VPRN service name";
                        }

                        leaf device-label {
                            type types-sros:named-item-64;
                            description "Device label supplied to the remote manager";
                        }

                        leaf device-name {
                            type types-sros:named-item-64;
                            description "Device name supplied to the remote manager";
                        }

                        leaf source-address {
                            type types-sros:ip-address;
                            description "Source IP address for connection to the manager";
                        }

                        leaf source-port {
                            type types-system:remote-mgmt-registration-port;
                            description "Source TCP destination port number";
                        }

                        leaf-list apply-groups {
                            type leafref {
                                path "../../../../../groups/group/name";
                            }
                            max-elements 8;
                            ordered-by user;
                            description "Apply a configuration group at this level";
                        }

                        leaf-list apply-groups-exclude {
                            type leafref {
                                path "../../../../../groups/group/name";
                            }
                            max-elements 8;
                            ordered-by user;
                            description "Exclude a configuration group at this level";
                        }

                        choice transport {
                            case client-tls-profile {

                                leaf client-tls-profile {
                                    type leafref {
                                        path "../../../../security/tls/client-tls-profile/client-profile-name";
                                    }
                                    description "TLS client profile name assigned to the remote manager";
                                }

                            }
                            case allow-unsecure-connection {

                                leaf allow-unsecure-connection {
                                    type empty;
                                    description "Allow connection without secured transport protocol";
                                }

                            }
                        }
                    } // list manager

                } // container remote-management

                container yang-modules {
                    description "Enter the yang-modules context";

                    leaf base-r13-modules {
                        status obsolete;
                        type boolean;
                        default "false";
                        description "Support Base-R13 YANG models";
                    }

                    leaf nokia-modules {
                        status obsolete;
                        type boolean;
                        description "Support Nokia YANG models";
                    }

                    leaf nokia-submodules {
                        type boolean;
                        description "Support submodule-based packaging of Nokia YANG models";
                    }

                    leaf openconfig-modules {
                        type boolean;
                        default "false";
                        description "Support access to OpenConfig YANG models";
                    }

                    leaf nokia-combined-modules {
                        type boolean;
                        description "Support access to combined Nokia YANG models";
                    }

                    leaf shared-model-management {
                        when "../openconfig-modules = 'true'" {
                            description "openconfig-modules must be true";
                        }
                        type boolean;
                        default "true";
                        description "Allow multiple models to configure the same elements";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                    container nmda {
                        description "Enter the nmda context";

                        leaf nmda-support {
                            type boolean;
                            default "false";
                            description "Advertise NMDA support over NETCONF";
                        }

                    } // container nmda

                } // container yang-modules

                container snmp {
                    description "Enter the snmp context";

                    leaf engine-id {
                        type types-system:engine-id-as-string;
                        description "SNMP engine ID that identifies the SNMPv3 node";
                    }

                    leaf general-port {
                        type types-sros:tcp-udp-port;
                        default "161";
                        description "Port number used to send general SNMP messages";
                    }

                    leaf max-bulk-duration {
                        type uint32 {
                            range "100..5000";
                        }
                        units "milliseconds";
                        description "Maximum process duration before responses are returned";
                    }

                    leaf packet-size {
                        type int32 {
                            range "484..9216";
                        }
                        default "1500";
                        description "Maximum SNMP packet size generated by the node";
                    }

                    leaf admin-state {
                        type types-sros:admin-state;
                        default "enable";
                        description "Administrative state of the SNMP agent";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                    container streaming {
                        description "Enter the streaming context";

                        leaf admin-state {
                            type types-sros:admin-state;
                            default "disable";
                            description "Administrative state of SNMP streaming";
                        }

                        leaf-list apply-groups {
                            type leafref {
                                path "../../../../../groups/group/name";
                            }
                            max-elements 8;
                            ordered-by user;
                            description "Apply a configuration group at this level";
                        }

                        leaf-list apply-groups-exclude {
                            type leafref {
                                path "../../../../../groups/group/name";
                            }
                            max-elements 8;
                            ordered-by user;
                            description "Exclude a configuration group at this level";
                        }

                    } // container streaming

                } // container snmp

            } // container management-interface

            container thresholds {
                description "Enter the thresholds context";

                list cflash-cap-alarm-percent {
                    key "cflash-id";
                    description "Enter the cflash-cap-alarm-percent list instance";

                    leaf cflash-id {
                        type types-sros:thresholds-cflash-url;
                        description "cflash device name monitored for capacity";
                    }

                    leaf rising-threshold {
                        type int32 {
                            range "0..100";
                        }
                        units "percent";
                        mandatory true;
                        description "Rising threshold for the sampled statistic";
                    }

                    leaf falling-threshold {
                        type int32 {
                            range "0..100";
                        }
                        units "percent";
                        description "Falling threshold for the sampled statistic";
                    }

                    leaf interval {
                        type int32 {
                            range "1..2147483647";
                        }
                        mandatory true;
                        description "Polling period over which data is sampled and compared";
                    }

                    leaf rmon-event-type {
                        type types-system:threshold-event-type;
                        description "Notification type specifying action when event occurs";
                    }

                    leaf startup-alarm {
                        type types-system:threshold-startup-alarm;
                        description "Alarm type when the alarm is first created";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                } // list cflash-cap-alarm-percent

                list cflash-cap-warn-percent {
                    key "cflash-id";
                    description "Enter the cflash-cap-warn-percent list instance";

                    leaf cflash-id {
                        type types-sros:thresholds-cflash-url;
                        description "cflash device name monitored for capacity";
                    }

                    leaf rising-threshold {
                        type int32 {
                            range "0..100";
                        }
                        units "percent";
                        mandatory true;
                        description "Rising threshold for the sampled statistic";
                    }

                    leaf falling-threshold {
                        type int32 {
                            range "0..100";
                        }
                        units "percent";
                        description "Falling threshold for the sampled statistic";
                    }

                    leaf interval {
                        type int32 {
                            range "1..2147483647";
                        }
                        mandatory true;
                        description "Polling period over which data is sampled and compared";
                    }

                    leaf rmon-event-type {
                        type types-system:threshold-event-type;
                        description "Notification type specifying action when event occurs";
                    }

                    leaf startup-alarm {
                        type types-system:threshold-startup-alarm;
                        description "Alarm type when the alarm is first created";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                } // list cflash-cap-warn-percent

                container kb-memory-use-alarm {
                    presence "Enable the kb-memory-use-alarm context";
                    description "Enable the kb-memory-use-alarm context";

                    leaf rising-threshold {
                        type int64 {
                            range "-2147483648..2147483647";
                        }
                        mandatory true;
                        description "Rising threshold for the sampled statistic";
                    }

                    leaf falling-threshold {
                        type int64 {
                            range "-2147483648..2147483647";
                        }
                        description "Falling threshold for the sampled statistic";
                    }

                    leaf interval {
                        type int32 {
                            range "1..2147483647";
                        }
                        mandatory true;
                        description "Polling period over which data is sampled and compared";
                    }

                    leaf rmon-event-type {
                        type types-system:threshold-event-type;
                        description "Notification type specifying action when event occurs";
                    }

                    leaf startup-alarm {
                        type types-system:threshold-startup-alarm;
                        description "Alarm type when the alarm is first created";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                } // container kb-memory-use-alarm

                container kb-memory-use-warn {
                    presence "Enable the kb-memory-use-warn context";
                    description "Enable the kb-memory-use-warn context";

                    leaf rising-threshold {
                        type int64 {
                            range "-2147483648..2147483647";
                        }
                        mandatory true;
                        description "Rising threshold for the sampled statistic";
                    }

                    leaf falling-threshold {
                        type int64 {
                            range "-2147483648..2147483647";
                        }
                        description "Falling threshold for the sampled statistic";
                    }

                    leaf interval {
                        type int32 {
                            range "1..2147483647";
                        }
                        mandatory true;
                        description "Polling period over which data is sampled and compared";
                    }

                    leaf rmon-event-type {
                        type types-system:threshold-event-type;
                        description "Notification type specifying action when event occurs";
                    }

                    leaf startup-alarm {
                        type types-system:threshold-startup-alarm;
                        description "Alarm type when the alarm is first created";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                } // container kb-memory-use-warn

                container rmon {
                    description "Enter the rmon context";

                    list alarm {
                        key "rmon-alarm-id";
                        max-elements 1200;
                        description "Enter the alarm list instance";

                        leaf rmon-alarm-id {
                            type uint32 {
                                range "0..65400";
                            }
                            description "Index ID for an entry in the alarm table";
                        }

                        leaf variable-oid {
                            type string {
                                length "1..255";
                            }
                            mandatory true;
                            description "Object identifier to sample the specific variable";
                        }

                        leaf interval {
                            type int32 {
                                range "1..2147483647";
                            }
                            mandatory true;
                            description "Polling period over which data is sampled and compared";
                        }

                        leaf sample-type {
                            type types-system:threshold-sample;
                            description "Sampling type for value comparison with thresholds";
                        }

                        leaf startup-alarm {
                            type types-system:threshold-startup-alarm;
                            description "Alarm to send when this entry is first set to valid";
                        }

                        leaf rising-event {
                            type uint32 {
                                range "0..65400";
                            }
                            description "RMON event ID for rising threshold crossing event";
                        }

                        leaf falling-event {
                            type uint32 {
                                range "0..65400";
                            }
                            description "RMON event ID for falling threshold crossing event";
                        }

                        leaf rising-threshold {
                            type int64 {
                                range "-2147483648..2147483647";
                            }
                            description "Rising threshold for the sampled statistic";
                        }

                        leaf falling-threshold {
                            type int64 {
                                range "-2147483648..2147483647";
                            }
                            description "Falling threshold for the sampled statistic";
                        }

                        leaf owner {
                            type string {
                                length "1..80";
                            }
                            default "TiMOS CLI";
                            description "Owner that created this entry and uses the resources";
                        }

                        leaf-list apply-groups {
                            type leafref {
                                path "../../../../../groups/group/name";
                            }
                            max-elements 8;
                            ordered-by user;
                            description "Apply a configuration group at this level";
                        }

                        leaf-list apply-groups-exclude {
                            type leafref {
                                path "../../../../../groups/group/name";
                            }
                            max-elements 8;
                            ordered-by user;
                            description "Exclude a configuration group at this level";
                        }

                    } // list alarm

                    list event {
                        key "rmon-event-id";
                        max-elements 1200;
                        description "Enter the event list instance";

                        leaf rmon-event-id {
                            type uint32 {
                                range "1..65400";
                            }
                            description "Index ID for an entry in the event table";
                        }

                        leaf event-type {
                            type types-system:threshold-rmon-event-type;
                            description "Notification action to be taken when the event occurs";
                        }

                        leaf description {
                            type types-sros:description;
                            description "Text description";
                        }

                        leaf owner {
                            type string {
                                length "1..80";
                            }
                            default "TiMOS CLI";
                            description "Owner that created this entry and uses the resources";
                        }

                        leaf-list apply-groups {
                            type leafref {
                                path "../../../../../groups/group/name";
                            }
                            max-elements 8;
                            ordered-by user;
                            description "Apply a configuration group at this level";
                        }

                        leaf-list apply-groups-exclude {
                            type leafref {
                                path "../../../../../groups/group/name";
                            }
                            max-elements 8;
                            ordered-by user;
                            description "Exclude a configuration group at this level";
                        }

                    } // list event

                } // container rmon

            } // container thresholds

            container ip {
                description "Enter the ip context";

                leaf allow-qinq-network-interface {
                    type boolean;
                    default "false";
                    description "Allow QinQ encapsulation for network interfaces";
                }

                leaf enforce-unique-if-index {
                    type boolean;
                    default "false";
                    description "Force creation of globally unique IP interface indexes";
                }

                leaf mpls-tunnel-mode {
                    type types-sros:mpls-tunnel-mode;
                    default "uniform";
                    description "MPLS tunnel mode";
                }

                leaf forward-6in4 {
                    type boolean;
                    default "false";
                    description "Allow forwarding of IPv6 over IPv4 to system IP address";
                }

                leaf forward-ip-over-gre {
                    type boolean;
                    default "false";
                    description "Allow forwarding of IP over GRE to system IP address";
                }

                leaf ipv6-eh {
                    type enumeration {
                        enum max                            { value 1; }
                        enum limited                        { value 2; }
                    }
                    default "max";
                    description "Number of IPv6 extension headers parsed in line cards";
                }

                leaf allow-cpu-fragmentation {
                    type boolean;
                    default "false";
                    description "Enable IP fragmentation for packets exceeding IP MTU";
                }

                leaf allow-icmp-redirect {
                    type boolean;
                    default "false";
                    description "Enable generation of ICMP redirect messages";
                }

                leaf-list apply-groups {
                    type leafref {
                        path "../../../groups/group/name";
                    }
                    max-elements 8;
                    ordered-by user;
                    description "Apply a configuration group at this level";
                }

                leaf-list apply-groups-exclude {
                    type leafref {
                        path "../../../groups/group/name";
                    }
                    max-elements 8;
                    ordered-by user;
                    description "Exclude a configuration group at this level";
                }

                container mpls {
                    description "Enter the mpls context";

                    leaf label-stack-statistics-count {
                        type uint32 {
                            range "1..2";
                        }
                        default "1";
                        description "Collect traffic statistics on labels of the MPLS stack";
                    }

                } // container mpls

            } // container ip

            container lacp {
                description "Enter the lacp context";

                leaf system-priority {
                    type uint32 {
                        range "1..65535";
                    }
                    default "32768";
                    description "LACP system priority on aggregated Ethernet interfaces";
                }

                leaf-list apply-groups {
                    type leafref {
                        path "../../../groups/group/name";
                    }
                    max-elements 8;
                    ordered-by user;
                    description "Apply a configuration group at this level";
                }

                leaf-list apply-groups-exclude {
                    type leafref {
                        path "../../../groups/group/name";
                    }
                    max-elements 8;
                    ordered-by user;
                    description "Exclude a configuration group at this level";
                }

            } // container lacp

            container lldp {
                description "Enter the lldp context";

                leaf tx-credit-max {
                    type int32 {
                        range "1..100";
                    }
                    default "5";
                    description "Maximum consecutive LLDPDUs that can be transmitted";
                }

                leaf message-fast-tx {
                    type int32 {
                        range "1..3600";
                    }
                    units "seconds";
                    default "1";
                    description "Interval at which LLDP frames are transmitted";
                }

                leaf message-fast-tx-init {
                    type int32 {
                        range "1..8";
                    }
                    default "4";
                    description "PDUs to transmit during the fast transmission period";
                }

                leaf admin-state {
                    type types-sros:admin-state;
                    default "enable";
                    description "Administrative state of LLDP";
                }

                leaf tx-interval {
                    type int32 {
                        range "5..32768";
                    }
                    units "seconds";
                    default "30";
                    description "LLDP transmit interval";
                }

                leaf tx-hold-multiplier {
                    type int32 {
                        range "2..10";
                    }
                    default "4";
                    description "Transmit interval multiplier";
                }

                leaf reinit-delay {
                    type int32 {
                        range "1..10";
                    }
                    units "seconds";
                    default "2";
                    description "Time required before re-initializing LLDP on a port";
                }

                leaf notification-interval {
                    type int32 {
                        range "5..3600";
                    }
                    units "seconds";
                    default "5";
                    description "Minimum interval between change notifications";
                }

                leaf-list apply-groups {
                    type leafref {
                        path "../../../groups/group/name";
                    }
                    max-elements 8;
                    ordered-by user;
                    description "Apply a configuration group at this level";
                }

                leaf-list apply-groups-exclude {
                    type leafref {
                        path "../../../groups/group/name";
                    }
                    max-elements 8;
                    ordered-by user;
                    description "Exclude a configuration group at this level";
                }

            } // container lldp

            container l2tp {
                description "Enter the l2tp context";

                leaf-list apply-groups {
                    type leafref {
                        path "../../../groups/group/name";
                    }
                    max-elements 8;
                    ordered-by user;
                    description "Apply a configuration group at this level";
                }

                leaf-list apply-groups-exclude {
                    type leafref {
                        path "../../../groups/group/name";
                    }
                    max-elements 8;
                    ordered-by user;
                    description "Exclude a configuration group at this level";
                }

                container non-multi-chassis-tunnel-id-range {
                    description "Enter the non-multi-chassis-tunnel-id-range context";

                    leaf start {
                        type types-l2tp:loc-tunnel-id-or-zero;
                        default "1";
                        description "Lower bound of the range";
                    }

                    leaf end {
                        type types-l2tp:loc-tunnel-id-or-zero;
                        default "16383";
                        description "Upper bound of the range";
                    }

                } // container non-multi-chassis-tunnel-id-range

            } // container l2tp

            list power-management {
                key "power-zone";
                description "Enter the power-management list instance";

                leaf power-zone {
                    type uint32 {
                        range "1..2";
                    }
                    description "Power zone";
                }

                leaf mode {
                    type enumeration {
                        enum none                           { value 0; }
                        enum basic                          { value 1; }
                        enum advanced                       { value 2; }
                    }
                    default "basic";
                    description "Power capacity mode algorithm";
                }

                leaf power-safety-alert {
                    type uint32 {
                        range "0..120000";
                    }
                    units "watts";
                    default "0";
                    description "Power capacity to trigger a safety alert event";
                }

                leaf power-safety-level {
                    type yang:gauge32 {
                        range "0..100";
                    }
                    units "percent";
                    default "100";
                    description "Minimum threshold to power off devices";
                }

                leaf-list apply-groups {
                    type leafref {
                        path "../../../groups/group/name";
                    }
                    max-elements 8;
                    ordered-by user;
                    description "Apply a configuration group at this level";
                }

                leaf-list apply-groups-exclude {
                    type leafref {
                        path "../../../groups/group/name";
                    }
                    max-elements 8;
                    ordered-by user;
                    description "Exclude a configuration group at this level";
                }

            } // list power-management

            container dhcp6 {
                description "Enter the dhcp6 context";

                leaf-list adv-noaddrs-global {
                    type enumeration {
                        enum esm-relay                      { value 1; }
                        enum server                         { value 2; }
                    }
                    max-elements 2;
                    description "Applications to send NoAddrsAvail in Advertise messages";
                }

                leaf-list apply-groups {
                    type leafref {
                        path "../../../groups/group/name";
                    }
                    max-elements 8;
                    ordered-by user;
                    description "Apply a configuration group at this level";
                }

                leaf-list apply-groups-exclude {
                    type leafref {
                        path "../../../groups/group/name";
                    }
                    max-elements 8;
                    ordered-by user;
                    description "Exclude a configuration group at this level";
                }

            } // container dhcp6

            list software-repository {
                key "repository-name";
                description "Enter the software-repository list instance";

                leaf repository-name {
                    type types-sros:named-item;
                    description "Software repository name";
                }

                leaf description {
                    type types-sros:description;
                    description "Text description";
                }

                leaf primary-location {
                    type string {
                        length "1..180";
                    }
                    description "Primary location for files in the software repository";
                }

                leaf secondary-location {
                    type string {
                        length "1..180";
                    }
                    description "Secondary location for files in the software repository";
                }

                leaf tertiary-location {
                    type string {
                        length "1..180";
                    }
                    description "Tertiary location for files in the software repository";
                }

                leaf-list apply-groups {
                    type leafref {
                        path "../../../groups/group/name";
                    }
                    max-elements 8;
                    ordered-by user;
                    description "Apply a configuration group at this level";
                }

                leaf-list apply-groups-exclude {
                    type leafref {
                        path "../../../groups/group/name";
                    }
                    max-elements 8;
                    ordered-by user;
                    description "Exclude a configuration group at this level";
                }

            } // list software-repository

            container resource {
                status obsolete;
                description "Enter the resource context";

                list ecmp-profile {
                    status obsolete;
                    key "profile-id";
                    description "Enter the ecmp-profile list instance";

                    leaf profile-id {
                        status obsolete;
                        type uint32 {
                            range "1..2";
                        }
                        description "ECMP profile identifier";
                    }

                    leaf type {
                        status obsolete;
                        type enumeration {
                            enum mpls                           { value 1; }
                            enum ip                             { value 2; }
                        }
                        sros-ext:immutable;
                        mandatory true;
                        description "ECMP bundle type for the profile";
                    }

                    leaf links {
                        status obsolete;
                        type uint32 {
                            range "1..16";
                        }
                        mandatory true;
                        description "Maximum number of links per group for the ECMP bundle";
                    }

                    leaf groups {
                        status obsolete;
                        type uint32 {
                            range "1..2048";
                        }
                        mandatory true;
                        description "Maximum number of groups allowed by the profile";
                    }

                    leaf-list apply-groups {
                        status obsolete;
                        type leafref {
                            path "../../../../groups/group/name";
                        }
                        max-elements 8;
                        ordered-by user;
                        description "Apply a configuration group at this level";
                    }

                    leaf-list apply-groups-exclude {
                        status obsolete;
                        type leafref {
                            path "../../../../groups/group/name";
                        }
                        max-elements 8;
                        ordered-by user;
                        description "Exclude a configuration group at this level";
                    }

                } // list ecmp-profile

            } // container resource

            container switch-fabric {
                description "Enter the switch-fabric context";

                leaf sfm-loss-threshold {
                    type uint32 {
                        range "1..7";
                    }
                    description "Number of SFMs that can fail before SFM overload state";
                }

                leaf-list apply-groups {
                    type leafref {
                        path "../../../groups/group/name";
                    }
                    max-elements 8;
                    ordered-by user;
                    description "Apply a configuration group at this level";
                }

                leaf-list apply-groups-exclude {
                    type leafref {
                        path "../../../groups/group/name";
                    }
                    max-elements 8;
                    ordered-by user;
                    description "Exclude a configuration group at this level";
                }

                container failure-recovery {
                    description "Enter the failure-recovery context";

                    leaf admin-state {
                        type types-sros:admin-state;
                        default "disable";
                        description "Administrative state of the failure recovery process";
                    }

                } // container failure-recovery

            } // container switch-fabric

            list usb {
                key "usb-cflash";
                description "Enter the usb list instance";

                leaf usb-cflash {
                    type enumeration {
                        enum cf2                            { value 2; }
                    }
                    description "Specifies the compact flash ID";
                }

                leaf admin-state {
                    type types-sros:admin-state;
                    default "disable";
                    description "Administrative state of the USB port";
                }

                leaf-list apply-groups {
                    type leafref {
                        path "../../../groups/group/name";
                    }
                    max-elements 8;
                    ordered-by user;
                    description "Apply a configuration group at this level";
                }

                leaf-list apply-groups-exclude {
                    type leafref {
                        path "../../../groups/group/name";
                    }
                    max-elements 8;
                    ordered-by user;
                    description "Exclude a configuration group at this level";
                }

            } // list usb


            container fan-control {
                description "Enter the fan-control context";

                leaf increase-min-speed {
                    type boolean;
                    default "false";
                    description "Increase minimum speed of router fans";
                }

                leaf min-speed {
                    type enumeration {
                        enum 65                             { value 65; }
                        enum 90                             { value 90; }
                    }
                    description "Minimum fan speed for the system as a percentage";
                }

                leaf cooling-profile {
                    type enumeration {
                        enum default                        { value 1; }
                        enum aggressive                     { value 2; }
                    }
                    default "default";
                    description "Cooling profile used to determine fan speeds";
                }

                leaf-list apply-groups {
                    type leafref {
                        path "../../../groups/group/name";
                    }
                    max-elements 8;
                    ordered-by user;
                    description "Apply a configuration group at this level";
                }

                leaf-list apply-groups-exclude {
                    type leafref {
                        path "../../../groups/group/name";
                    }
                    max-elements 8;
                    ordered-by user;
                    description "Exclude a configuration group at this level";
                }

            } // container fan-control

            uses conf-system-bluetooth;
            uses conf-system-central-frequency-clock;
            uses conf-system-cron;
            uses conf-system-login-control;
            uses conf-system-ned-network-element-discovery;
            uses conf-system-persistence;
            uses conf-system-ptp;
            uses conf-system-script-control;
            uses conf-system-security;
            uses conf-system-telemetry;
            uses conf-system-time;
        } // container system

    } // grouping conf-system

}
