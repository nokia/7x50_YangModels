submodule nokia-state-port-eth-dot1x {

    yang-version "1.1";

    belongs-to nokia-state { prefix "state"; }

    import ietf-yang-types                { prefix "yang"; }
    import nokia-sros-yang-extensions     { prefix "sros-ext"; }
    import nokia-types-port               { prefix "types-port"; }
    import nokia-types-sros               { prefix "types-sros"; }

    sros-ext:sros-major-release "rel24";
    organization "Nokia";
    contact
        "Nokia SR OS Support
         Web: <http://www.nokia.com>";
    description
        "Nokia YANG Data model with operational state for ethernet ports 802.1x authentication capabilities on SR OS based routers.

         Copyright 2016 Nokia. All rights reserved. Reproduction of this document
         is authorized on the condition that the foregoing copyright notice is included.

         This nokia-state-port-eth-dot1x YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";
    revision "2024-05-22";

    grouping state-port-eth-dot1x {
        container dot1x {
            description "Enter the dot1x context";

            leaf authenticator-pae-state {
                type enumeration {
                    enum initialize                     { value 1; }
                    enum disconnected                   { value 2; }
                    enum connecting                     { value 3; }
                    enum authenticating                 { value 4; }
                    enum authenticated                  { value 5; }
                    enum aborting                       { value 6; }
                    enum held                           { value 7; }
                    enum force-authorized               { value 8; }
                    enum force-unauthorized             { value 9; }
                }
                description
                    "Indicates the current value of the Authenticator PAE state
                     machine.";
            }

            leaf backend-authentication-state {
                type enumeration {
                    enum request                        { value 1; }
                    enum response                       { value 2; }
                    enum success                        { value 3; }
                    enum fail                           { value 4; }
                    enum timeout                        { value 5; }
                    enum idle                           { value 6; }
                    enum initialize                     { value 7; }
                }
                description
                    "Indicates the current state of the Backend Authentication
                     state machine.";
            }

            leaf port-status {
                type types-port:pae-controlled-port-status;
                description
                    "Indicates the current value of the controlled Port
                     status parameter for the Port.";
            }

            list host {
                key "mac";
                description "Enter the host list instance";

                leaf mac {
                    type yang:mac-address;
                    description "Source MAC address of a host present on this port";
                }

                leaf allowed-by-configuration {
                    type boolean;
                    description "The host is allowed access by configuration";
                }

                leaf authenticator-pae-state {
                    type enumeration {
                        enum initialize                     { value 1; }
                        enum disconnected                   { value 2; }
                        enum connecting                     { value 3; }
                        enum authenticating                 { value 4; }
                        enum authenticated                  { value 5; }
                        enum aborting                       { value 6; }
                        enum held                           { value 7; }
                        enum force-authorized               { value 8; }
                        enum force-unauthorized             { value 9; }
                    }
                    description "The current value of the Authenticator PAE state machine";
                }

                leaf backend-authentication-state {
                    type enumeration {
                        enum request                        { value 1; }
                        enum response                       { value 2; }
                        enum success                        { value 3; }
                        enum fail                           { value 4; }
                        enum timeout                        { value 5; }
                        enum idle                           { value 6; }
                        enum initialize                     { value 7; }
                    }
                    description "The current state of the Backend Authentication state machine";
                }

                container statistics {
                    description "Enter the statistics context";

                    leaf octets-rx {
                        type yang:counter64;
                        description
                            "The number of octets received in user data frames on
                             this Port during the session";
                    }

                    leaf octets-tx {
                        type yang:counter64;
                        description
                            "The number of octets transmitted in user data frames on
                             this Port during the session";
                    }

                    leaf frames-rx {
                        type yang:counter32;
                        description
                            "The number of user data frames received on this Port
                             during the session";
                    }

                    leaf frames-tx {
                        type yang:counter32;
                        description
                            "The number of user data frames transmitted on this Port
                             during the session";
                    }

                    leaf session-identifier {
                        type string;
                        description
                            "A unique identifier for the session, in the form of a
                             printable ASCII string of at least three characters";
                    }

                    leaf authentication-method {
                        type enumeration {
                            enum remote-authentication-server   { value 1; }
                            enum local-authentication-server    { value 2; }
                        }
                        description "The authentication method used to establish the session";
                    }

                    leaf session-time {
                        type yang:timeticks;
                        description "The duration of the session in seconds";
                    }

                    leaf termination-cause {
                        type enumeration {
                            enum supplicant-logoff              { value 1; }
                            enum port-failure                   { value 2; }
                            enum supplicant-restart             { value 3; }
                            enum reauth-failed                  { value 4; }
                            enum auth-control-force-unauth      { value 5; }
                            enum port-re-init                   { value 6; }
                            enum port-admin-disabled            { value 7; }
                            enum not-terminated-yet             { value 999; }
                        }
                        description "The reason for the session termination";
                    }

                    leaf username {
                        type string;
                        description
                            "The User-Name representing the identity of the
                             Supplicant PAE";
                    }

                } // container statistics

                container diagnostics {
                    description "Enter the diagnostics context";

                    leaf enters-connecting {
                        type yang:counter32;
                        description
                            "Number of times that the state machine transitions to
                             the CONNECTING state from any other state";
                    }

                    leaf eap-logoffs-while-connecting {
                        type yang:counter32;
                        description
                            "Number of times that the state machine transitions from
                             CONNECTING to DISCONNECTED as a result of receiving an
                             EAPOL-Logoff message";
                    }

                    leaf enters-authenticating {
                        type yang:counter32;
                        description
                            "Number of times that the state machine transitions from
                             CONNECTING to AUTHENTICATING, as a result of an
                             EAP-Response/Identity message being received from the
                             Supplicant";
                    }

                    leaf success-while-authenticating {
                        type yang:counter32;
                        description
                            "Number of times that the state machine transitions from
                             AUTHENTICATING to AUTHENTICATED, as a result of the
                             Backend Authentication state machine indicating
                             successful authentication of the Supplicant
                             ('authSuccess' = true)";
                    }

                    leaf timeouts-while-authenticating {
                        type yang:counter32;
                        description
                            "Number of times that the state machine transitions from
                             AUTHENTICATING to ABORTING, as a result of the Backend
                             Authentication state machine indicating authentication
                             timeout ('authTimeout' = true)";
                    }

                    leaf fail-while-authenticating {
                        type yang:counter32;
                        description
                            "Number of times that the state machine transitions from
                             AUTHENTICATING to HELD, as a result of the Backend
                             Authentication state machine indicating authentication
                             failure ('authFail' = true)";
                    }

                    leaf reauthentication-while-authenticating {
                        type yang:counter32;
                        description
                            "Number of times that the state machine transitions from
                             AUTHENTICATING to ABORTING, as a result of a
                             reauthentication request ('reAuthenticate' = true)";
                    }

                    leaf eap-start-while-authenticating {
                        type yang:counter32;
                        description
                            "Number of times that the state machine transitions from
                             AUTHENTICATING to ABORTING, as a result of an
                             EAPOL-Start message being received from the Supplicant";
                    }

                    leaf eap-logoff-while-authenticating {
                        type yang:counter32;
                        description
                            "Number of times that the state machine transitions from
                             AUTHENTICATING to ABORTING, as a result of an
                             EAPOL-Logoff message being received from the Supplicant";
                    }

                    leaf reauthenticaton-while-authenticated {
                        type yang:counter32;
                        description
                            "Number of times that the state machine transitions from
                             AUTHENTICATED to CONNECTING, as a result of a
                             reauthentication request ('reAuthenticate' = true)";
                    }

                    leaf eap-start-while-authenticated {
                        type yang:counter32;
                        description
                            "Number of times that the state machine transitions from
                             AUTHENTICATED to CONNECTING, as a result of an
                             EAPOL-Start message being received from the Supplicant";
                    }

                    leaf eap-logoff-while-authenticated {
                        type yang:counter32;
                        description
                            "Number of times that the state machine transitions from
                             AUTHENTICATED to DISCONNECTED, as a result of an
                             EAPOL-Logoff message being received from the Supplicant";
                    }

                    leaf responses {
                        type yang:counter32;
                        description
                            "Number of times that the state machine sends an initial
                             Access-Request packet to the Authentication server
                             (i.e., executes 'sendRespToServer' on entry to the
                             RESPONSE state). Indicates that the Authenticator
                             attempted communication with the Authentication Server";
                    }

                    leaf access-challenges {
                        type yang:counter32;
                        description
                            "Number of times that the state machine receives an
                             initial Access-Challenge packet from the Authentication
                             server (i.e., 'aReq' becomes TRUE, causing exit from
                             the RESPONSE state). Indicates that the Authentication
                             Server has communication with the Authenticator.";
                    }

                    leaf other-requests-to-supplicant {
                        type yang:counter32;
                        description
                            "Number of times that the state machine sends an
                             EAP-Request packet (other than an Identity,
                             Notification, Failure or Success message) to the
                             Supplicant (i.e., executes 'txReq' on entry to the
                             REQUEST state). Indicates that the Authenticator chose
                             an EAP-method.";
                    }

                    leaf non-nak-responses-from-supplicant {
                        type yang:counter32;
                        description
                            "Number of times that the state machine receives a
                             response from the Supplicant to an initial EAP-Request,
                             and the response is something other than EAP-NAK (i.e.,
                             'rxResp' becomes TRUE, causing the state machine to
                             transition from REQUEST to RESPONSE, and the response
                             is not an EAP-NAK). Indicates that the Supplicant can
                             respond to the Authenticator's chosen EAP-method.";
                    }

                    leaf authentication-successes {
                        type yang:counter32;
                        description
                            "Number of times that the state machine receives an
                             EAP-Success message from the Authentication Server
                             (i.e., 'aSuccess' becomes TRUE, causing a transition
                             from RESPONSE to SUCCESS). Indicates that the
                             Supplicant has successfully authenticated to the
                             Authentication Server.";
                    }

                    leaf authentication-fails {
                        type yang:counter32;
                        description
                            "Number of times that the state machine receives an
                             EAP-Failure message from the Authentication Server
                             (i.e., 'aFail' becomes TRUE, causing a transition from
                             RESPONSE to FAIL). Indicates that the Supplicant has not
                             authenticated to the Authentication Server.";
                    }

                } // container diagnostics

            } // list host

            container macsec {
                description "Enter the macsec context";

                list sub-port {
                    key "sub-port-id";
                    description "Enter the sub-port list instance";

                    leaf sub-port-id {
                        type uint32 {
                            range "1..1023";
                        }
                        description "Sub-port ID";
                    }

                    container statistics {
                        description "Enter the statistics context";

                        list mka {
                            key "ckn";
                            description "Enter the mka list instance";

                            leaf ckn {
                                type binary {
                                    length "1..32";
                                }
                                description "Indicates CKN information for the MKA instance.";
                            }

                            leaf member-id {
                                type binary {
                                    length "12";
                                }
                                description "Indicates the Member Identifier (MI) for the MKA instance.";
                            }

                            leaf outbound-sci {
                                type binary {
                                    length "8";
                                }
                                description
                                    "Indicates the Secure Channel Identifier (SCI) information for transmitting
                                     MACsec frames.";
                            }

                            leaf message-count {
                                type uint32;
                                description "Indicates the current count of MKA messages that is attached to MKA PDUs.";
                            }

                            leaf key-number {
                                type uint32;
                                description
                                    "Indicates the number of the currently assigned CAK. When a new CAK is
                                     generated, this number is incremented.";
                            }

                            leaf key-server {
                                type boolean;
                                description
                                    "Indicates whether this server is the highest priority server in the peer
                                     group.";
                            }

                            leaf latest-sak-an {
                                type uint32;
                                description
                                    "Indicates the Association Number (AN) of the latest Secure Association Key
                                     (SAK). This number is concatenated with an SCI to identify a Secure
                                     Association (SA).";
                            }

                            leaf previous-sak-an {
                                type uint32;
                                description
                                    "Indicates the AN of the previous SAK. This number is concatenated with an SCI
                                     to identify an SA.";
                            }

                            leaf latest-sak-ki {
                                type binary {
                                    length "16";
                                }
                                description
                                    "Indicates the Key Identifier (KI) of the latest SAK. This number is derived
                                     from the MI of the key server and the key number.";
                            }

                            leaf previous-sak-ki {
                                type binary {
                                    length "16";
                                }
                                description
                                    "Indicates the KI of the previous SAK. This number is derived from the MI of
                                     the key server and the key number.";
                            }

                            leaf peers-removed {
                                type yang:counter64;
                                description
                                    "Indicates the number of peers removed from the live/potential peer list due to
                                     not receiving an MKPDU within the MKA Live Time (6.0 sec).";
                            }

                            leaf ckn-not-found {
                                type yang:counter64;
                                description
                                    "Indicates the number of MKPDUs received with a CKN that does not match the CA
                                     configured for the port.";
                            }

                            leaf new-live-peer {
                                type yang:counter64;
                                description
                                    "Indicates the number of validated peers that have been added to the live peer
                                     list.";
                            }

                            leaf sak-generated {
                                type yang:counter64;
                                description "Indicates the number of SAKs generated by this MKA instance.";
                            }

                            leaf sak-installed-transmitting {
                                type yang:counter64;
                                description "Indicates the number of SAKs installed for transmitting.";
                            }

                            leaf sak-installed-receiving {
                                type yang:counter64;
                                description "Indicates the number of SAKs installed for receiving.";
                            }

                            leaf pdu-too-small {
                                type yang:counter64;
                                description "Indicates the number of MKPDUs received that are less than 32 octets.";
                            }

                            leaf pdu-too-big {
                                type yang:counter64;
                                description
                                    "Indicates the number of MKPDUs received where the EAPOL header indicates a
                                     size larger than the received packet.";
                            }

                            leaf pdu-not-quad-size {
                                type yang:counter64;
                                description
                                    "Indicates the number of MKPDUs received with a size that is not a multiple of
                                     4 octets.";
                            }

                            leaf pdu-invalid-number {
                                type yang:counter64;
                                description
                                    "Indicates the number of MKPDUs received out of order as indicated by the
                                     Message Number.";
                            }

                            leaf parameter-size-invalid {
                                type yang:counter64;
                                description
                                    "Indicates the number of MKPDUs received which contain a parameter set body
                                     length that exceeds the remaining length of the MKPDU.";
                            }

                            leaf liveness-check-fail {
                                type yang:counter64;
                                description
                                    "Indicates the number of MKPDUs received which contain an MN that is not
                                     acceptably recent.";
                            }

                            leaf parameter-not-quad-size {
                                type yang:counter64;
                                description
                                    "Indicates the number of MKPDUs received which contain a parameter set that is
                                     not a multiple of 4 octets.";
                            }

                            leaf unsupported-algorithm-agility {
                                type yang:counter64;
                                description
                                    "Indicates the number of MKPDUs received which contain an unsupported Algorithm
                                     Agility value.";
                            }

                            leaf invalid-ckn-length {
                                type yang:counter64;
                                description
                                    "Indicates the number of MKPDUs received which contain a CAK name that exceeds
                                     the maximum CAK name length.";
                            }

                            leaf icv-check-failed {
                                type yang:counter64;
                                description
                                    "Indicates the number of MKPDUs received which contain an ICV value that does
                                     not authenticate.";
                            }

                            leaf peer-same-mi {
                                type yang:counter64;
                                description
                                    "Indicates the number of MKPDUs received which contain a peerlist with an MI
                                     entry which conflicts with the local MI.";
                            }

                            leaf sak-non-live-peer {
                                type yang:counter64;
                                description
                                    "Indicates the number of SAKs received from a peer that is not a member of the
                                     Live Peers List.";
                            }

                            leaf sak-no-key-server {
                                type yang:counter64;
                                description
                                    "Indicates the number of SAKs received from an MKA participant that has not
                                     been designated as the Key Server.";
                            }

                            leaf sak-decrypt-fail {
                                type yang:counter64;
                                description
                                    "Indicates the number of AES Key Wrap SAK decryption failures that have
                                     occurred.";
                            }

                            leaf sak-encrypt-fail {
                                type yang:counter64;
                                description
                                    "Indicates the number of AES Key Wrap SAK encryption failures that have
                                     occurred.";
                            }

                            leaf key-number-invalid {
                                type yang:counter64;
                                description "Indicates the number of SAKs received with an invalid Key Number.";
                            }

                            leaf sak-install-fail {
                                type yang:counter64;
                                description "Indicates the number of SecY SAK installation failures that have occurred.";
                            }

                            leaf cak-info-missing {
                                type yang:counter64;
                                description
                                    "Indicates the number of times internal CAK data is not available for the
                                     generation of the SAK.";
                            }

                            leaf max-peers-set-zero {
                                type yang:counter64;
                                description
                                    "Indicates the number of SecY SAK installations that have failed due to the max
                                     peer entry being set to 0.";
                            }

                            leaf oper-state {
                                type types-sros:oper-state;
                                description "Indicates the operational state of the MKA participant.";
                            }

                            leaf oper-offset {
                                type uint32 {
                                    range "0|30|50";
                                }
                                units "octets";
                                description
                                    "Indicates the operational encryption offset used for the datapath PDUs when
                                     all parties in the CA have the SAK. This value is specified by the key
                                     server.";
                            }

                            leaf oper-cipher {
                                type enumeration {
                                    enum gcm-aes-128                    { value 1; }
                                    enum gcm-aes-256                    { value 2; }
                                    enum gcm-aes-xpn-128                { value 3; }
                                    enum gcm-aes-xpn-256                { value 4; }
                                }
                                description
                                    "Indicates the operational encryption algorithm used for datapath PDUs when all
                                     parties in the CA have the SAK. This value is specified by the key server.";
                            }

                            leaf latest-sak-lpn {
                                type yang:counter64;
                                description "Indicates Lowest Acceptable Packet Number of the latest SAK.";
                            }

                            leaf previous-sak-lpn {
                                type yang:counter64;
                                description "Indicates Lowest Acceptable Packet Number of the previous SAK.";
                            }

                            leaf invalid-header {
                                type yang:counter64;
                                description "Indicates the number of MKPDUs received with an invalid MKA header.";
                            }

                            list mka-peer {
                                key "member-id";
                                description "Enter the mka-peer list instance";

                                leaf member-id {
                                    type binary {
                                        length "12";
                                    }
                                    description "Specifies the MI of the peer entry.";
                                }

                                leaf member-number {
                                    type yang:counter64;
                                    description "Indicates the latest Member Number of the peer entry.";
                                }

                                leaf type {
                                    type enumeration {
                                        enum live-peer-list                 { value 1; }
                                        enum potential-peer-list            { value 2; }
                                    }
                                    description
                                        "Indicates the type of the peer entry.

                                         live-peer-list(1):      the peer entry is in the Live Peer List.
                                         potential-peer-list(2): the peer entry is in the Potential Peer List.";
                                }

                                leaf sci {
                                    type binary {
                                        length "8";
                                    }
                                    description "Indicates the SCI information of this peer list entry.";
                                }

                                leaf key-server-priority {
                                    type yang:counter64;
                                    description "Indicates the priority of this MKA peer.";
                                }

                                leaf lowest-acceptable-packet-number {
                                    type yang:counter64;
                                    description "Indicates the lowest acceptable packet number of this MKA peer.";
                                }

                            } // list mka-peer

                        } // list mka

                        container secy {
                            description "Enter the secy context";

                            container received {
                                description "Enter the received context";

                                leaf bad-tag-packets {
                                    type yang:counter64;
                                    units "packets";
                                    description
                                        "Indicates the number of received packets discarded with an
                                         invalid SecTAG or a zero value Packet Number (PN) or an
                                         invalid Integrity Check Value (ICV).";
                                }

                                leaf unknown-sci-packets {
                                    type yang:counter64;
                                    units "packets";
                                    description
                                        "Indicates the number of received packets discarded with
                                         unknown SCI information when the C bit in the SecTAG is
                                         set.";
                                }

                                leaf packets-without-tag {
                                    type yang:counter64;
                                    units "packets";
                                    description
                                        "Indicates the number of received packets discarded without
                                         the MAC security tag (SecTAG).";
                                }

                                leaf overrun-packets {
                                    type yang:counter64;
                                    units "packets";
                                    description
                                        "Indicates the number of packets discarded because the number
                                         of received packets exceeded the cryptographic performance
                                         capabilities.";
                                }

                            } // container received

                            container transmitted {
                                description "Enter the transmitted context";

                                leaf too-long-packets {
                                    type yang:counter64;
                                    units "packets";
                                    description
                                        "Indicates the number of transmitted packets discarded because
                                         the packet length is greater than the Maximum Transmission Unit
                                         (MTU) of the Ethernet physical interface.";
                                }

                                leaf untagged-packets {
                                    type yang:counter64;
                                    units "packets";
                                    description
                                        "Indicates the number of transmitted packets without the MAC
                                         security tag (SecTAG) when the value of 
                                         macsec/connectivity-association/replay-protection
                                         for the configured CA is set to 'false'.";
                                }

                            } // container transmitted

                            container secure-channel {
                                description "Enter the secure-channel context";

                                container transmitting-sc {
                                    description "Enter the transmitting-sc context";

                                    leaf protected-packets {
                                        type yang:counter64;
                                        units "packets";
                                        description
                                            "Indicates the number of integrity protected but not encrypted packets for this
                                             transmitting SC.";
                                    }

                                    leaf encrypted-packets {
                                        type yang:counter64;
                                        units "packets";
                                        description
                                            "Indicates the number of integrity protected and encrypted packets for this
                                             transmitting SC.";
                                    }

                                    leaf octets-protected {
                                        type yang:counter64;
                                        units "octets";
                                        description
                                            "Indicates the number of plain text octets that are integrity protected but not
                                             encrypted on the transmitting SC.";
                                    }

                                    leaf octets-encrypted {
                                        type yang:counter64;
                                        units "octets";
                                        description
                                            "Indicates the number of plain text octets that are integrity protected and
                                             encrypted on the transmitting SC.";
                                    }

                                    list transmitting-sa {
                                        key "tx-sa-an";
                                        description "Enter the transmitting-sa list instance";

                                        leaf tx-sa-an {
                                            type uint32;
                                            description "Indicates the AN for identifying the transmitting SA.";
                                        }

                                        leaf protected-packets {
                                            type yang:counter32;
                                            units "packets";
                                            description
                                                "Indicates the number of packets that are integrity protected but not encrypted
                                                 for this transmitting SA.";
                                        }

                                        leaf encrypted-packets {
                                            type yang:counter32;
                                            units "packets";
                                            description
                                                "Indicates the number of packets that are integrity protected and encrypted for
                                                 this transmitting SA.";
                                        }

                                    } // list transmitting-sa

                                } // container transmitting-sc

                                list receiving-sc {
                                    key "rx-sci";
                                    description "Enter the receiving-sc list instance";

                                    leaf rx-sci {
                                        type binary {
                                            length "8";
                                        }
                                        description "Indicates the SCI for identifying the receiving SC.";
                                    }

                                    leaf not-using-sa-packets {
                                        type yang:counter64;
                                        units "packets";
                                        description
                                            "Indicates the summation of counter /macsec/rx-sa/not-using-sa-packets
                                                information for all the SAs which belong to this SC.";
                                    }

                                    leaf late-packets {
                                        type yang:counter64;
                                        units "packets";
                                        description
                                            "Indicates the number of received packets that have been discarded due to
                                             replay window protection on this SC.";
                                    }

                                    leaf not-valid-packets {
                                        type yang:counter64;
                                        units "packets";
                                        description
                                            "Indicates the summation of counter /macsec/rx-sa/not-valid-packets information
                                             for all the SAs which belong to this SC.";
                                    }

                                    leaf delayed-packets {
                                        type yang:counter64;
                                        units "packets";
                                        description
                                            "Indicates the number of received packets with the condition that the PN of the
                                             packets is lower than the lower bound of the replay protection PN.";
                                    }

                                    leaf unchecked-packets {
                                        type yang:counter64;
                                        units "packets";
                                        description
                                            "Indicates the number of packets that have failed the integrity check on this
                                             SC.";
                                    }

                                    leaf ok-packets {
                                        type yang:counter64;
                                        units "packets";
                                        description
                                            "Indicates the summation of counter /macsec/rx-sa/ok-packets information for all
                                             the SAs which belong to this SC.";
                                    }

                                    leaf octets-validated {
                                        type yang:counter64;
                                        units "octets";
                                        description
                                            "Indicates the number of octets of plain text recovered from received packets
                                             that were integrity protected but not encrypted.";
                                    }

                                    leaf octets-decrypted {
                                        type yang:counter64;
                                        units "octets";
                                        description
                                            "Indicates the number of octets of plain text recovered from received packets
                                             that were integrity protected and encrypted.";
                                    }

                                    list receiving-sa {
                                        key "rx-sa-an";
                                        description "Enter the receiving-sa list instance";

                                        leaf rx-sa-an {
                                            type uint32;
                                            description "Indicates the AN for identifying the receiving SA.";
                                        }

                                        leaf discarded-inactive {
                                            type yang:counter32;
                                            units "packets";
                                            description
                                                "Indicates the number of received packets that have been discarded on this SA which
                                                 is not currently in use.";
                                        }

                                        leaf discarded-active {
                                            type yang:counter32;
                                            units "packets";
                                            description
                                                "Indicates the number of not valid packets that have been discarded on this active
                                                 SA.";
                                        }

                                        leaf accepted-packets {
                                            type yang:counter32;
                                            units "packets";
                                            description "Indicates the number of validated packets on this SA.";
                                        }

                                    } // list receiving-sa

                                } // list receiving-sc

                            } // container secure-channel

                        } // container secy

                    } // container statistics

                } // list sub-port

            } // container macsec

            container statistics {
                description "Enter the statistics context";

                container received {
                    description "Enter the received context";

                    leaf bad-eap-length-frames {
                        type yang:counter32;
                        description
                            "Indicates the number of EAPOL frames that have been received
                             by this Authenticator in which the Packet Body
                             Length field is invalid.";
                    }

                    leaf last-source-mac-address {
                        type yang:mac-address;
                        description
                            "Indicates the source MAC address carried in the
                             most recently received EAPOL frame.";
                    }

                    leaf last-version {
                        type uint32;
                        description
                            "Indicates the protocol version number carried in the
                             most recently received EAPOL frame.";
                    }

                    leaf logoff-frames {
                        type yang:counter32;
                        description
                            "Indicates the number of EAPOL Logoff frames that have
                             been received by this Authenticator.";
                    }

                    leaf response-frames {
                        type yang:counter32;
                        description
                            "Indicates the number of valid EAP Response frames
                             (other than Resp/Id frames) that have been
                             received by this Authenticator.";
                    }

                    leaf response-id-frames {
                        type yang:counter32;
                        description
                            "Indicates the number of EAP Resp/Id frames that have
                             been received by this Authenticator.";
                    }

                    leaf start-frames {
                        type yang:counter32;
                        description
                            "Indicates the number of EAPOL Start frames that have
                             been received by this Authenticator.";
                    }

                    leaf valid-frames {
                        type yang:counter32;
                        description
                            "Indicates the number of valid EAPOL frames of any type
                             that have been received by this Authenticator.";
                    }

                    leaf unknown-frames {
                        type yang:counter32;
                        description
                            "Indicates the number of EAPOL frames that have been
                             received by this Authenticator in which the
                             frame type is not recognized.";
                    }

                } // container received

                container transmitted {
                    description "Enter the transmitted context";

                    leaf request-frames {
                        type yang:counter32;
                        description
                            "Indicates the number of EAP Request frames
                             (other than Rq/Id frames) that have been
                             transmitted by this Authenticator.";
                    }

                    leaf request-id-frames {
                        type yang:counter32;
                        description
                            "Indicates the number of EAP Req/Id frames that have been
                             transmitted by this Authenticator.";
                    }

                    leaf total-frames {
                        type yang:counter32;
                        description
                            "Indicates the number of EAPOL frames of any type
                             that have been transmitted by this Authenticator.";
                    }

                } // container transmitted

            } // container statistics

        } // container dot1x

    } // grouping state-port-eth-dot1x

}
