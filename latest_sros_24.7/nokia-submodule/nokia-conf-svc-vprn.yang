submodule nokia-conf-svc-vprn {

    yang-version "1.1";

    belongs-to nokia-conf { prefix "conf"; }

    import ietf-inet-types                { prefix "inet"; }
    import ietf-yang-types                { prefix "yang"; }
    import nokia-sros-yang-extensions     { prefix "sros-ext"; }
    import nokia-types-bgp                { prefix "types-bgp"; }
    import nokia-types-eth-cfm            { prefix "types-eth-cfm"; }
    import nokia-types-igmp               { prefix "types-igmp"; }
    import nokia-types-ipsec              { prefix "types-ipsec"; }
    import nokia-types-l2tp               { prefix "types-l2tp"; }
    import nokia-types-log                { prefix "types-log"; }
    import nokia-types-mcast-cac          { prefix "types-mcast-cac"; }
    import nokia-types-nat                { prefix "types-nat"; }
    import nokia-types-ppp                { prefix "types-ppp"; }
    import nokia-types-qos                { prefix "types-qos"; }
    import nokia-types-redundancy         { prefix "types-redundancy"; }
    import nokia-types-router             { prefix "types-router"; }
    import nokia-types-services           { prefix "types-services"; }
    import nokia-types-sros               { prefix "types-sros"; }
    import nokia-types-subscriber-mgmt    { prefix "types-submgt"; }

    include nokia-conf-aa-group;
    include nokia-conf-aaa;
    include nokia-conf-application-assurance;
    include nokia-conf-bfd;
    include nokia-conf-bmp;
    include nokia-conf-eth-cfm;
    include nokia-conf-filter;
    include nokia-conf-filter-ip-exception;
    include nokia-conf-groups;
    include nokia-conf-ipsec;
    include nokia-conf-isa;
    include nokia-conf-log;
    include nokia-conf-mcast-cac;
    include nokia-conf-mcast-mgmt;
    include nokia-conf-policy-options;
    include nokia-conf-port;
    include nokia-conf-port-eth-access;
    include nokia-conf-port-ethernet;
    include nokia-conf-pxc;
    include nokia-conf-python;
    include nokia-conf-qos;
    include nokia-conf-redundancy;
    include nokia-conf-router;
    include nokia-conf-router-mpls;
    include nokia-conf-router-p2mp-sr-tree;
    include nokia-conf-router-segment-routing;
    include nokia-conf-routing-options;
    include nokia-conf-service;
    include nokia-conf-submgt-gtp;
    include nokia-conf-submgt-local-user-db;
    include nokia-conf-subscriber-mgmt;
    include nokia-conf-svc-epipe;
    include nokia-conf-svc-nat;
    include nokia-conf-svc-vprn-dhcp-server;
    include nokia-conf-svc-vprn-isis;
    include nokia-conf-svc-vprn-msdp;
    include nokia-conf-svc-vprn-ospf;
    include nokia-conf-svc-vprn-ospf3;
    include nokia-conf-svc-vprn-radius;
    include nokia-conf-svc-vprn-rip;
    include nokia-conf-svc-vprn-ripng;
    include nokia-conf-svc-vprn-sub-if;
    include nokia-conf-svc-vprn-twamp-light;
    include nokia-conf-svc-vprn-vdo-if;
    include nokia-conf-system;
    include nokia-conf-system-security;
    include nokia-conf-system-security-aaa;
    include nokia-conf-system-security-snmp;
    include nokia-conf-system-security-tls;
    include nokia-conf-test-oam;
    include nokia-conf-vrrp;

    sros-ext:sros-major-release "rel24";
    organization "Nokia";
    contact
        "Nokia SR OS Support
         Web: <http://www.nokia.com>";
    description
        "Nokia YANG Data model to configure vprn services on SR OS based routers.

         Copyright 2016 Nokia. All rights reserved. Reproduction of this document
         is authorized on the condition that the foregoing copyright notice is included.

         This nokia-conf-svc-vprn YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";
    revision "2024-05-31";

    grouping conf-svc-vprn {
        list vprn {
            key "service-name";
            description "Enter the vprn list instance";

            leaf service-name {
                type types-services:service-name;
                description "Administrative service name";
            }

            leaf service-id {
                type types-services:external-service-id;
                sros-ext:immutable;
                description "Service ID";
            }

            leaf description {
                type types-sros:description;
                description "Text description";
            }

            leaf customer {
                type leafref {
                    path "../../customer/customer-name";
                }
                sros-ext:immutable;
                mandatory true;
                description "Service customer ID";
            }

            leaf admin-state {
                type types-sros:admin-state;
                default "disable";
                description "Administrative state of the service";
            }

            leaf hash-label {
                type boolean;
                default "false";
                description "Include hash label";
            }

            leaf autonomous-system {
                type uint32 {
                    range "1..max";
                }
                description "AS number advertised to peers for this router";
            }

            leaf ecmp {
                type types-router:ip-ecmp;
                default "1";
                description "Maximum equal-cost routes for routing table instance";
            }

            leaf entropy-label {
                type boolean;
                default "false";
                description "Use entropy label";
            }

            leaf fib-priority {
                type enumeration {
                    enum standard                       { value 1; }
                    enum high                           { value 2; }
                }
                default "standard";
                description "FIB priority for VPRN BGP routes";
            }

            leaf multicast-info-policy {
                type leafref {
                    path "../../../multicast-management/multicast-info-policy/policy-name";
                }
                description "Multicast policy name for virtual router";
            }

            leaf router-id {
                type types-router:router-id;
                description "Unique router ID for the router in the AS";
            }

            leaf weighted-ecmp {
                type enumeration {
                    enum false                          { value 0; }
                    enum true                           { value 1; }
                    enum strict                         { value 2; }
                }
                default "false";
                description "Weighted load-balancing capability for ECMP routes";
            }

            leaf route-distinguisher {
                status obsolete;
                type types-services:vpn-route-distinguisher-or-auto-rd;
                description "Route distinguisher";
            }

            leaf label-mode {
                type enumeration {
                    enum vrf                            { value 1; }
                    enum next-hop                       { value 2; }
                }
                sros-ext:auto-restart-to-modify;
                default "vrf";
                description "Allocation mode for VPRN service labels";
            }

            leaf allow-export-bgp-vpn {
                type boolean;
                default "false";
                description "Include BGP-VPN routes for export";
            }

            leaf ignore-nh-metric {
                type boolean;
                default "false";
                description "Ignore next hop metric";
            }

            leaf export-inactive-bgp-enhanced {
                type boolean;
                default "false";
                description "Export best BGP route when better non-BGP route present";
            }

            leaf export-inactive-bgp {
                type boolean;
                default "false";
                description "Export preferred BGP route even if inactive";
            }

            leaf ecmp-unequal-cost {
                type boolean;
                default "false";
                description "Enable ECMP unequal cost capability";
            }

            leaf class-forwarding {
                type boolean;
                default "false";
                description "Allow packet forwarding based on forwarding class";
            }

            leaf vprn-type {
                type enumeration {
                    enum regular                        { value 1; }
                    enum hub                            { value 2; }
                    enum spoke                          { value 3; }
                    enum subscriber-split-horizon       { value 4; }
                }
                sros-ext:auto-restart-to-modify;
                default "regular";
                description "VPRN type";
            }

            leaf carrier-carrier-vpn {
                type boolean;
                default "false";
                description "Allow VPRN service to support a Carrier Supporting Carrier model";
            }

            leaf selective-fib {
                type boolean;
                default "true";
                description "Enable selective FIB";
            }

            leaf local-routes-domain-id {
                type types-services:domain-id;
                description "Local routes domain ID";
            }

            leaf d-path-length-ignore {
                type boolean;
                default "false";
                description "Enable D-PATH length ignore";
            }

            leaf-list apply-groups {
                type leafref {
                    path "../../../groups/group/name";
                }
                max-elements 8;
                ordered-by user;
                description "Apply a configuration group at this level";
            }

            leaf-list apply-groups-exclude {
                type leafref {
                    path "../../../groups/group/name";
                }
                max-elements 8;
                ordered-by user;
                description "Exclude a configuration group at this level";
            }

            container nat {
                presence "Enable the nat context";
                description "Enable the nat context";

                leaf-list apply-groups {
                    type leafref {
                        path "../../../../groups/group/name";
                    }
                    max-elements 8;
                    ordered-by user;
                    description "Apply a configuration group at this level";
                }

                leaf-list apply-groups-exclude {
                    type leafref {
                        path "../../../../groups/group/name";
                    }
                    max-elements 8;
                    ordered-by user;
                    description "Exclude a configuration group at this level";
                }

                container inside {
                    description "Enter the inside context";

                    container l2-aware {
                        description "Enter the l2-aware context";

                        leaf force-unique-ip-addresses {
                            type boolean;
                            default "false";
                            description "Enforce unique IPv4 addresses for L2-aware subscribers";
                        }

                        list subscribers {
                            key "prefix";
                            description "Add a list entry for subscribers";

                            leaf prefix {
                                type types-sros:ipv4-prefix-with-host-bits;
                                description "Layer-2 Aware NAT subscriber prefix";
                            }

                        } // list subscribers

                    } // container l2-aware

                    container large-scale {
                        description "Enter the large-scale context";

                        leaf nat-policy {
                            type leafref {
                                path "../../../../../nat/nat-policy/name";
                            }
                            sros-ext:isa-auto-clear-on-modify;
                            description "NAT policy name for LSN";
                        }

                        container traffic-identification {
                            description "Enter the traffic-identification context";

                            leaf source-prefix-only {
                                type boolean;
                                default "false";
                                description "Allow traffic associated with source prefixes only";
                            }

                        } // container traffic-identification

                        container static-port-forwards {
                            description "Enter the static-port-forwards context";

                            list spf-nat-policy {
                                key "nat-policy";
                                description "Add a list entry for spf-nat-policy";

                                leaf nat-policy {
                                    type leafref {
                                        path "../../../../../../../nat/nat-policy/name";
                                    }
                                    description "NAT policy";
                                }

                            } // list spf-nat-policy

                        } // container static-port-forwards

                        container nat44 {
                            description "Enter the nat44 context";

                            leaf max-subscriber-limit {
                                type types-nat:lsn-max-subscriber-limit;
                                sros-ext:isa-auto-clear-on-modify;
                                description "Largest value for all subscriber limits in each deterministic pool";
                            }

                            leaf-list nat-import {
                                type leafref {
                                    path "../../../../../../../policy-options/policy-statement/name";
                                }
                                max-elements 5;
                                ordered-by user;
                                description "Import BGP-VPN routes in NAT inside routing context";
                            }

                            list destination-prefix {
                                key "ip-prefix-length";
                                max-elements 6144;
                                description "Enter the destination-prefix list instance";

                                leaf ip-prefix-length {
                                    type types-sros:ipv4-unicast-prefix;
                                    description "IP prefix for the destination address";
                                }

                                leaf nat-policy {
                                    type leafref {
                                        path "../../../../../../../nat/nat-policy/name";
                                    }
                                    sros-ext:isa-auto-clear-on-modify;
                                    description "NAT policy";
                                }

                                leaf-list apply-groups {
                                    type leafref {
                                        path "../../../../../../../../groups/group/name";
                                    }
                                    max-elements 8;
                                    ordered-by user;
                                    description "Apply a configuration group at this level";
                                }

                                leaf-list apply-groups-exclude {
                                    type leafref {
                                        path "../../../../../../../../groups/group/name";
                                    }
                                    max-elements 8;
                                    ordered-by user;
                                    description "Exclude a configuration group at this level";
                                }

                            } // list destination-prefix

                            list source-prefix {
                                key "ip-prefix-length";
                                description "Enter the source-prefix list instance";

                                leaf ip-prefix-length {
                                    type types-sros:ipv4-unicast-prefix;
                                    description "IPv4 prefix length";
                                }

                                leaf nat-policy {
                                    type leafref {
                                        path "../../../../../../../nat/nat-policy/name";
                                    }
                                    sros-ext:immutable;
                                    sros-ext:isa-auto-clear-on-modify;
                                    mandatory true;
                                    description "AT policy associated with the source prefix";
                                }

                                leaf-list apply-groups {
                                    type leafref {
                                        path "../../../../../../../../groups/group/name";
                                    }
                                    max-elements 8;
                                    ordered-by user;
                                    description "Apply a configuration group at this level";
                                }

                                leaf-list apply-groups-exclude {
                                    type leafref {
                                        path "../../../../../../../../groups/group/name";
                                    }
                                    max-elements 8;
                                    ordered-by user;
                                    description "Exclude a configuration group at this level";
                                }

                            } // list source-prefix

                            container deterministic {
                                description "Enter the deterministic context";

                                list address-map {
                                    key "from to nat-policy";
                                    description "Enter the address-map list instance";

                                    leaf from {
                                        type types-sros:ipv4-address;
                                        description "First IP address of inside IP NAT range";
                                    }

                                    leaf to {
                                        type types-sros:ipv4-address;
                                        description "Ending IP address of inside IP NAT range";
                                    }

                                    leaf nat-policy {
                                        type leafref {
                                            path "../../../../../../../../nat/nat-policy/name";
                                        }
                                        description "NAT policy name for LSN";
                                    }

                                    leaf admin-state {
                                        type types-sros:admin-state;
                                        default "disable";
                                        description "Administrative state of address map";
                                    }

                                    leaf outside-range {
                                        type types-sros:ipv4-address;
                                        sros-ext:auto-restart-to-modify;
                                        description "First outside IP address in NAT pool";
                                    }

                                    leaf-list apply-groups {
                                        type leafref {
                                            path "../../../../../../../../../groups/group/name";
                                        }
                                        max-elements 8;
                                        ordered-by user;
                                        sros-ext:auto-restart-to-modify;
                                        description "Apply a configuration group at this level";
                                    }

                                    leaf-list apply-groups-exclude {
                                        type leafref {
                                            path "../../../../../../../../../groups/group/name";
                                        }
                                        max-elements 8;
                                        ordered-by user;
                                        sros-ext:auto-restart-to-modify;
                                        description "Exclude a configuration group at this level";
                                    }

                                } // list address-map

                                list policy-map {
                                    status obsolete;
                                    key "source-prefix";
                                    description "Enter the policy-map list instance";

                                    leaf source-prefix {
                                        status obsolete;
                                        type types-sros:ipv4-unicast-prefix;
                                        description "Source prefix that adds traffic to NAT pool";
                                    }

                                    leaf nat-policy {
                                        status obsolete;
                                        type leafref {
                                            path "../../../../../../../../nat/nat-policy/name";
                                        }
                                        sros-ext:immutable;
                                        sros-ext:isa-auto-clear-on-modify;
                                        mandatory true;
                                        description "NAT policy";
                                    }

                                    leaf admin-state {
                                        status obsolete;
                                        type types-sros:admin-state;
                                        default "disable";
                                        description "Administrative state of the prefix";
                                    }

                                    leaf-list apply-groups {
                                        status obsolete;
                                        type leafref {
                                            path "../../../../../../../../../groups/group/name";
                                        }
                                        max-elements 8;
                                        ordered-by user;
                                        description "Apply a configuration group at this level";
                                    }

                                    leaf-list apply-groups-exclude {
                                        status obsolete;
                                        type leafref {
                                            path "../../../../../../../../../groups/group/name";
                                        }
                                        max-elements 8;
                                        ordered-by user;
                                        description "Exclude a configuration group at this level";
                                    }

                                    list map {
                                        status obsolete;
                                        key "from to";
                                        description "Enter the map list instance";

                                        leaf from {
                                            status obsolete;
                                            type types-sros:ipv4-address;
                                            description "Beginning of the range for IPv4 addresses";
                                        }

                                        leaf to {
                                            status obsolete;
                                            type types-sros:ipv4-address;
                                            description "End of the range for IPv4 addresses";
                                        }

                                        leaf first-outside-address {
                                            status obsolete;
                                            type types-sros:ipv4-address;
                                            sros-ext:immutable;
                                            mandatory true;
                                            description "Outside IP address mapped to inside IP address range";
                                        }

                                        leaf-list apply-groups {
                                            status obsolete;
                                            type leafref {
                                                path "../../../../../../../../../../groups/group/name";
                                            }
                                            max-elements 8;
                                            ordered-by user;
                                            description "Apply a configuration group at this level";
                                        }

                                        leaf-list apply-groups-exclude {
                                            status obsolete;
                                            type leafref {
                                                path "../../../../../../../../../../groups/group/name";
                                            }
                                            max-elements 8;
                                            ordered-by user;
                                            description "Exclude a configuration group at this level";
                                        }

                                    } // list map

                                } // list policy-map

                                list prefix-map {
                                    key "source-prefix nat-policy";
                                    description "Enter the prefix-map list instance";

                                    leaf source-prefix {
                                        type types-sros:ipv4-unicast-prefix;
                                        description "Traffic sent from sources within this prefix will be NATed";
                                    }

                                    leaf nat-policy {
                                        type leafref {
                                            path "../../../../../../../../nat/nat-policy/name";
                                        }
                                        description "NAT policy";
                                    }

                                    leaf admin-state {
                                        type types-sros:admin-state;
                                        default "disable";
                                        description "Administrative state of the prefix";
                                    }

                                    leaf-list apply-groups {
                                        type leafref {
                                            path "../../../../../../../../../groups/group/name";
                                        }
                                        max-elements 8;
                                        ordered-by user;
                                        sros-ext:auto-restart-to-modify;
                                        description "Apply a configuration group at this level";
                                    }

                                    leaf-list apply-groups-exclude {
                                        type leafref {
                                            path "../../../../../../../../../groups/group/name";
                                        }
                                        max-elements 8;
                                        ordered-by user;
                                        sros-ext:auto-restart-to-modify;
                                        description "Exclude a configuration group at this level";
                                    }

                                    list map {
                                        key "from to";
                                        description "Enter the map list instance";

                                        leaf from {
                                            type types-sros:ipv4-address;
                                            description "First IP address of inside IP NAT range";
                                        }

                                        leaf to {
                                            type types-sros:ipv4-address;
                                            description "Ending IP address of inside IP NAT range";
                                        }

                                        leaf first-outside-address {
                                            type types-sros:ipv4-address;
                                            sros-ext:immutable;
                                            mandatory true;
                                            description "Outside IP address mapped to inside IP address range";
                                        }

                                        leaf-list apply-groups {
                                            type leafref {
                                                path "../../../../../../../../../../groups/group/name";
                                            }
                                            max-elements 8;
                                            ordered-by user;
                                            description "Apply a configuration group at this level";
                                        }

                                        leaf-list apply-groups-exclude {
                                            type leafref {
                                                path "../../../../../../../../../../groups/group/name";
                                            }
                                            max-elements 8;
                                            ordered-by user;
                                            description "Exclude a configuration group at this level";
                                        }

                                    } // list map

                                } // list prefix-map

                            } // container deterministic

                        } // container nat44

                        container dual-stack-lite {
                            description "Enter the dual-stack-lite context";

                            leaf admin-state {
                                type types-sros:admin-state;
                                default "disable";
                                description "Administrative state of Dual Stack Lite";
                            }

                            leaf max-subscriber-limit {
                                type types-nat:lsn-max-subscriber-limit;
                                sros-ext:isa-auto-clear-on-modify;
                                description "Largest value for all subscriber limits in each deterministic pool";
                            }

                            leaf subscriber-prefix-length {
                                type types-nat:ipv6-subscriber-prefix-length;
                                sros-ext:auto-restart-to-modify;
                                sros-ext:isa-auto-clear-on-modify;
                                description "IPv6 prefix length of the Dual Stack Lite subscribers";
                            }

                            list endpoint {
                                key "address";
                                max-elements 128;
                                description "Enter the endpoint list instance";

                                leaf address {
                                    type types-sros:ipv6-address;
                                    description "Dual Stack Lite IPv6 address";
                                }

                                leaf ip-fragmentation {
                                    type types-nat:ip-fragmentation;
                                    description "Fragmentation control of the AFTR originated downstream IPv6 traffic";
                                }

                                leaf tunnel-mtu {
                                    type uint32 {
                                        range "464..9212";
                                    }
                                    default "1500";
                                    description "DS-Lite tunnel MTU for this address";
                                }

                                leaf reassembly {
                                    type boolean;
                                    default "false";
                                    description "Reassembly of IPv6 payload datagrams";
                                }

                                leaf min-first-fragment-size-rx {
                                    type uint32 {
                                        range "512..1280";
                                    }
                                    default "1280";
                                    description "Minimum MTU size for upstream packets";
                                }

                                leaf-list apply-groups {
                                    type leafref {
                                        path "../../../../../../../../groups/group/name";
                                    }
                                    max-elements 8;
                                    ordered-by user;
                                    description "Apply a configuration group at this level";
                                }

                                leaf-list apply-groups-exclude {
                                    type leafref {
                                        path "../../../../../../../../groups/group/name";
                                    }
                                    max-elements 8;
                                    ordered-by user;
                                    description "Exclude a configuration group at this level";
                                }

                            } // list endpoint

                            container deterministic {
                                description "Enter the deterministic context";

                                list address-map {
                                    key "from to nat-policy";
                                    description "Enter the address-map list instance";

                                    leaf from {
                                        type types-sros:ipv6-prefix;
                                        description "Lower bound of IPv6 address of inside IPv6 NAT range";
                                    }

                                    leaf to {
                                        type types-sros:ipv6-prefix;
                                        description "Upper bound of IPv6 address of inside IPv6 NAT range";
                                    }

                                    leaf nat-policy {
                                        type leafref {
                                            path "../../../../../../../../nat/nat-policy/name";
                                        }
                                        description "NAT policy name for LSN";
                                    }

                                    leaf admin-state {
                                        type types-sros:admin-state;
                                        default "disable";
                                        description "Administrative state of address map";
                                    }

                                    leaf outside-range {
                                        type types-sros:ipv4-address;
                                        sros-ext:auto-restart-to-modify;
                                        description "First outside IP address in NAT pool";
                                    }

                                    leaf-list apply-groups {
                                        type leafref {
                                            path "../../../../../../../../../groups/group/name";
                                        }
                                        max-elements 8;
                                        ordered-by user;
                                        sros-ext:auto-restart-to-modify;
                                        description "Apply a configuration group at this level";
                                    }

                                    leaf-list apply-groups-exclude {
                                        type leafref {
                                            path "../../../../../../../../../groups/group/name";
                                        }
                                        max-elements 8;
                                        ordered-by user;
                                        sros-ext:auto-restart-to-modify;
                                        description "Exclude a configuration group at this level";
                                    }

                                } // list address-map

                                list policy-map {
                                    status obsolete;
                                    key "source-prefix";
                                    description "Enter the policy-map list instance";

                                    leaf source-prefix {
                                        status obsolete;
                                        type types-sros:ipv6-unicast-prefix;
                                        description "Source prefix that adds traffic to NAT pool";
                                    }

                                    leaf nat-policy {
                                        status obsolete;
                                        type leafref {
                                            path "../../../../../../../../nat/nat-policy/name";
                                        }
                                        sros-ext:immutable;
                                        sros-ext:isa-auto-clear-on-modify;
                                        mandatory true;
                                        description "NAT policy";
                                    }

                                    leaf admin-state {
                                        status obsolete;
                                        type types-sros:admin-state;
                                        default "disable";
                                        description "Administrative state of the prefix";
                                    }

                                    leaf-list apply-groups {
                                        status obsolete;
                                        type leafref {
                                            path "../../../../../../../../../groups/group/name";
                                        }
                                        max-elements 8;
                                        ordered-by user;
                                        description "Apply a configuration group at this level";
                                    }

                                    leaf-list apply-groups-exclude {
                                        status obsolete;
                                        type leafref {
                                            path "../../../../../../../../../groups/group/name";
                                        }
                                        max-elements 8;
                                        ordered-by user;
                                        description "Exclude a configuration group at this level";
                                    }

                                    list map {
                                        status obsolete;
                                        key "from to";
                                        description "Enter the map list instance";

                                        leaf from {
                                            status obsolete;
                                            type types-sros:ipv6-prefix;
                                            description "Lower bound of IPv6 address of inside IPv6 NAT range";
                                        }

                                        leaf to {
                                            status obsolete;
                                            type types-sros:ipv6-prefix;
                                            description "Upper bound of IPv6 address of inside IPv6 NAT range";
                                        }

                                        leaf first-outside-address {
                                            status obsolete;
                                            type types-sros:ipv4-address;
                                            sros-ext:immutable;
                                            mandatory true;
                                            description "Outside IP address mapped to inside IP address range";
                                        }

                                        leaf-list apply-groups {
                                            status obsolete;
                                            type leafref {
                                                path "../../../../../../../../../../groups/group/name";
                                            }
                                            max-elements 8;
                                            ordered-by user;
                                            description "Apply a configuration group at this level";
                                        }

                                        leaf-list apply-groups-exclude {
                                            status obsolete;
                                            type leafref {
                                                path "../../../../../../../../../../groups/group/name";
                                            }
                                            max-elements 8;
                                            ordered-by user;
                                            description "Exclude a configuration group at this level";
                                        }

                                    } // list map

                                } // list policy-map

                                list prefix-map {
                                    key "source-prefix nat-policy";
                                    description "Enter the prefix-map list instance";

                                    leaf source-prefix {
                                        type types-sros:ipv6-unicast-prefix;
                                        description "List containing source IP addresses on the private side";
                                    }

                                    leaf nat-policy {
                                        type leafref {
                                            path "../../../../../../../../nat/nat-policy/name";
                                        }
                                        description "NAT policy";
                                    }

                                    leaf admin-state {
                                        type types-sros:admin-state;
                                        default "disable";
                                        description "Administrative state of the prefix";
                                    }

                                    leaf-list apply-groups {
                                        type leafref {
                                            path "../../../../../../../../../groups/group/name";
                                        }
                                        max-elements 8;
                                        ordered-by user;
                                        sros-ext:auto-restart-to-modify;
                                        description "Apply a configuration group at this level";
                                    }

                                    leaf-list apply-groups-exclude {
                                        type leafref {
                                            path "../../../../../../../../../groups/group/name";
                                        }
                                        max-elements 8;
                                        ordered-by user;
                                        sros-ext:auto-restart-to-modify;
                                        description "Exclude a configuration group at this level";
                                    }

                                    list map {
                                        key "from to";
                                        description "Enter the map list instance";

                                        leaf from {
                                            type types-sros:ipv6-prefix;
                                            description "Beginning of the range for IPv6 addresses";
                                        }

                                        leaf to {
                                            type types-sros:ipv6-prefix;
                                            description "End of the range for IPv6 addresses";
                                        }

                                        leaf first-outside-address {
                                            type types-sros:ipv4-address;
                                            sros-ext:immutable;
                                            mandatory true;
                                            description "Outside IP address mapped to inside IP address range";
                                        }

                                        leaf-list apply-groups {
                                            type leafref {
                                                path "../../../../../../../../../../groups/group/name";
                                            }
                                            max-elements 8;
                                            ordered-by user;
                                            description "Apply a configuration group at this level";
                                        }

                                        leaf-list apply-groups-exclude {
                                            type leafref {
                                                path "../../../../../../../../../../groups/group/name";
                                            }
                                            max-elements 8;
                                            ordered-by user;
                                            description "Exclude a configuration group at this level";
                                        }

                                    } // list map

                                } // list prefix-map

                            } // container deterministic

                        } // container dual-stack-lite

                        container nat64 {
                            presence "Enable the nat64 context";
                            description "Enable the nat64 context";

                            leaf admin-state {
                                type types-sros:admin-state;
                                default "disable";
                                description "Administrative state of NAT64";
                            }

                            leaf drop-zero-ipv4-checksum {
                                type boolean;
                                sros-ext:auto-restart-to-modify;
                                default "false";
                                description "Drop UDP datagrams with zero IPv4 checksum";
                            }

                            leaf insert-ipv6-fragment-header {
                                type boolean;
                                sros-ext:auto-restart-to-modify;
                                default "false";
                                description "Include IPv6 fragment header to indicate that the sender allows fragmentation";
                            }

                            leaf ip-fragmentation {
                                type types-nat:ip-fragmentation;
                                sros-ext:auto-restart-to-modify;
                                description "Control fragmentation of originated downstream IPv6 traffic";
                            }

                            leaf ipv6-mtu {
                                type uint32 {
                                    range "1280..9212";
                                }
                                sros-ext:auto-restart-to-modify;
                                default "1520";
                                description "Size of the IPv6 downstream packet in NAT64";
                            }

                            leaf prefix {
                                type types-sros:ipv6-prefix;
                                sros-ext:auto-restart-to-modify;
                                sros-ext:isa-auto-clear-on-modify;
                                default "64:ff9b::/96";
                                description "IPv6 prefix to derive the IPv6 address from the IPv4 address";
                            }

                            leaf subscriber-prefix-length {
                                type types-nat:ipv6-subscriber-prefix-length;
                                sros-ext:auto-restart-to-modify;
                                sros-ext:isa-auto-clear-on-modify;
                                description "IPv6 prefix length for the NAT64 subscribers";
                            }

                            leaf-list apply-groups {
                                type leafref {
                                    path "../../../../../../../groups/group/name";
                                }
                                max-elements 8;
                                ordered-by user;
                                sros-ext:auto-restart-to-modify;
                                description "Apply a configuration group at this level";
                            }

                            leaf-list apply-groups-exclude {
                                type leafref {
                                    path "../../../../../../../groups/group/name";
                                }
                                max-elements 8;
                                ordered-by user;
                                sros-ext:auto-restart-to-modify;
                                description "Exclude a configuration group at this level";
                            }

                            container tos {
                                sros-ext:auto-restart-to-modify;
                                description "Enter the tos context";

                                container upstream {
                                    sros-ext:auto-restart-to-modify;
                                    description "Enter the upstream context";

                                    leaf set-tos {
                                        type union {
                                            type enumeration {
                                                enum use-ipv6                       { value -1; }
                                            }
                                            type uint32 {
                                                range "0..255";
                                            }
                                        }
                                        sros-ext:auto-restart-to-modify;
                                        default "use-ipv6";
                                        description "TOS/DSCP bits in IPv4 frame in the upstream direction";
                                    }

                                } // container upstream

                                container downstream {
                                    sros-ext:auto-restart-to-modify;
                                    description "Enter the downstream context";

                                    leaf use-ipv4 {
                                        type boolean;
                                        sros-ext:auto-restart-to-modify;
                                        default "false";
                                        description "Copy TOS/DSCP bits from the incoming IPv4 frame to the outgoing IPv6 frame";
                                    }

                                } // container downstream

                            } // container tos


                        } // container nat64

                        container subscriber-identification {
                            description "Enter the subscriber-identification context";

                            leaf admin-state {
                                type types-sros:admin-state;
                                default "disable";
                                description "Administrative state of subscriber identification";
                            }

                            leaf description {
                                type types-sros:description;
                                description "Text description";
                            }

                            leaf drop-unidentified-traffic {
                                type boolean;
                                sros-ext:auto-restart-to-modify;
                                default "false";
                                description "Drop traffic from unidentified flows";
                            }

                            leaf-list apply-groups {
                                type leafref {
                                    path "../../../../../../../groups/group/name";
                                }
                                max-elements 8;
                                ordered-by user;
                                description "Apply a configuration group at this level";
                            }

                            leaf-list apply-groups-exclude {
                                type leafref {
                                    path "../../../../../../../groups/group/name";
                                }
                                max-elements 8;
                                ordered-by user;
                                description "Exclude a configuration group at this level";
                            }

                            container attribute {
                                description "Enter the attribute context";

                                leaf vendor {
                                    type types-nat:nat-subscriber-identification-attr-vendor-id;
                                    sros-ext:auto-restart-to-modify;
                                    default "nokia";
                                    description "The RADIUS Vendor";
                                }

                                leaf type {
                                    type types-nat:nat-subscriber-identification-attr-type;
                                    sros-ext:auto-restart-to-modify;
                                    default "alc-sub-string";
                                    description "RADIUS attribute used as subscriber identifier";
                                }

                            } // container attribute

                            container radius-proxy-server {
                                presence "Enable the radius-proxy-server context";
                                description "Enable the radius-proxy-server context";

                                leaf router-instance {
                                    type string;
                                    sros-ext:auto-restart-to-modify;
                                    mandatory true;
                                    description "Router instance";
                                }

                                leaf server {
                                    type types-sros:named-item;
                                    sros-ext:auto-restart-to-modify;
                                    mandatory true;
                                    description "Server name";
                                }

                            } // container radius-proxy-server

                        } // container subscriber-identification

                        container dnat-only {
                            description "Enter the dnat-only context";

                            leaf source-prefix-list {
                                type leafref {
                                    path "../../../../../../nat/prefix-list/name";
                                }
                                description "NAT prefix list that contains source IP addresses";
                            }

                        } // container dnat-only

                        container redundancy {
                            description "Enter the redundancy context";

                            leaf peer {
                                type types-sros:ipv4-unicast-address;
                                description "IP address of the NAT redundancy peer for this virtual router instance";
                            }

                            leaf peer6 {
                                type types-sros:ipv6-unicast-address;
                                description "IPv6 address of the NAT redundancy peer for this virtual router instance";
                            }

                            leaf steering-route {
                                type types-sros:ipv4-unicast-prefix;
                                description "IP address and prefix length of the steering route";
                            }

                        } // container redundancy

                        container filters {
                            description "Enter the filters context";

                            container downstream {
                                description "Enter the downstream context";

                                leaf ipv4 {
                                    type leafref {
                                        path "../../../../../../../../filter/ip-filter/filter-name";
                                    }
                                    description "IPv4 filter policy name";
                                }

                            } // container downstream

                        } // container filters

                    } // container large-scale

                } // container inside

                container outside {
                    description "Enter the outside context";

                    leaf mtu {
                        type uint32 {
                            range "512..9000";
                        }
                        description "MTU for downstream traffic";
                    }

                    container filters {
                        description "Enter the filters context";

                        container downstream {
                            description "Enter the downstream context";

                            leaf ipv4 {
                                type leafref {
                                    path "../../../../../../../filter/ip-filter/filter-name";
                                }
                                description "IPv4 filter policy name";
                            }

                            leaf ipv6 {
                                type leafref {
                                    path "../../../../../../../filter/ipv6-filter/filter-name";
                                }
                                description "IPv6 filter policy name";
                            }

                        } // container downstream

                        container upstream {
                            description "Enter the upstream context";

                            leaf ipv4 {
                                type leafref {
                                    path "../../../../../../../filter/ip-filter/filter-name";
                                }
                                description "IPv4 filter policy name";
                            }

                            leaf ipv6 {
                                type leafref {
                                    path "../../../../../../../filter/ipv6-filter/filter-name";
                                }
                                description "IPv6 filter policy name";
                            }

                        } // container upstream

                    } // container filters

                    container dnat-only {
                        description "Enter the dnat-only context";

                        leaf route-limit {
                            type uint32 {
                                range "1..131072";
                            }
                            default "32768";
                            description "Limit for internal routes for downstream traffic";
                        }

                    } // container dnat-only

                    list pool {
                        key "name";
                        max-elements 4096;
                        description "Enter the pool list instance";

                        leaf name {
                            type types-sros:named-item;
                            description "NAT pool name";
                        }

                        leaf type {
                            type types-nat:pool-type;
                            sros-ext:immutable;
                            sros-ext:isa-auto-clear-on-modify;
                            mandatory true;
                            description "NAT pool type";
                        }

                        leaf address-pooling {
                            type enumeration {
                                enum paired                         { value 1; }
                                enum arbitrary                      { value 2; }
                            }
                            sros-ext:auto-restart-to-modify;
                            default "paired";
                            description "Outside IP address allocation mode for a NAT subscriber";
                        }

                        leaf description {
                            type types-sros:description;
                            description "Text description";
                        }

                        leaf icmp-echo-reply {
                            type boolean;
                            default "false";
                            description "Allow NAT pool IP addresses to respond to ICMP PINGs";
                        }

                        leaf mode {
                            type types-nat:pool-mode;
                            sros-ext:auto-restart-to-modify;
                            sros-ext:isa-auto-clear-on-modify;
                            description "Mode of operation of this NAT address pool";
                        }

                        leaf admin-state {
                            type types-sros:admin-state;
                            default "disable";
                            description "Administrative state of the outside routing NAT pool";
                        }

                        leaf-list apply-groups {
                            type leafref {
                                path "../../../../../../groups/group/name";
                            }
                            max-elements 8;
                            ordered-by user;
                            description "Apply a configuration group at this level";
                        }

                        leaf-list apply-groups-exclude {
                            type leafref {
                                path "../../../../../../groups/group/name";
                            }
                            max-elements 8;
                            ordered-by user;
                            description "Exclude a configuration group at this level";
                        }

                        choice isa {
                            mandatory true;
                            case nat {

                                leaf nat-group {
                                    type leafref {
                                        path "../../../../../../isa/nat-group/id";
                                    }
                                    sros-ext:immutable;
                                    sros-ext:isa-auto-clear-on-modify;
                                    description "Create a NAT group";
                                }

                            }
                            case wlan-gw {

                                leaf wlan-gw-group {
                                    type leafref {
                                        path "../../../../../../isa/wlan-gw-group/id";
                                    }
                                    sros-ext:immutable;
                                    sros-ext:isa-auto-clear-on-modify;
                                    description "Create a WLAN GW group for NAT";
                                }

                            }
                        }
                        container applications {
                            description "Enter the applications context";

                            leaf agnostic {
                                when "../../type = 'large-scale'" {
                                    description "type must be large-scale";
                                }
                                type boolean;
                                sros-ext:immutable;
                                sros-ext:isa-auto-clear-on-modify;
                                default "false";
                                description "NAT pool to create in the outside routing context";
                            }

                            leaf flexible-port-allocation {
                                when "../../type = 'large-scale'" {
                                    description "type must be large-scale";
                                }
                                type boolean;
                                sros-ext:immutable;
                                sros-ext:isa-auto-clear-on-modify;
                                default "false";
                                description "Allocates individual ports per subscriber in a pool";
                            }

                        } // container applications

                        container port-forwarding {
                            description "Enter the port-forwarding context";

                            leaf dynamic-block-reservation {
                                when "not(../../type = 'l2-aware')" {
                                    description "type must not be l2-aware";
                                }
                                type boolean;
                                sros-ext:isa-auto-clear-on-modify;
                                default "false";
                                description "Reserve dynamic block for subscriber";
                            }

                            leaf range-start {
                                type uint16 {
                                    range "0|1|1025..65535";
                                }
                                sros-ext:auto-restart-to-modify;
                                description "Start of the wildcard range for port forwards";
                            }

                            leaf range-end {
                                type uint16 {
                                    range "0|1023..65535";
                                }
                                sros-ext:auto-restart-to-modify;
                                sros-ext:isa-auto-clear-on-modify;
                                description "End of the wildcard range for port forwards";
                            }

                        } // container port-forwarding

                        container port-reservation {
                            description "Enter the port-reservation context";

                            choice port-reservation {
                                default "port-blocks";
                                case port-blocks {

                                    leaf port-blocks {
                                        type uint16 {
                                            range "0..64512";
                                        }
                                        sros-ext:auto-restart-to-modify;
                                        sros-ext:isa-auto-clear-on-modify;
                                        description "Port block size for NAT subscribers";
                                    }

                                }
                                case ports {

                                    leaf ports {
                                        type uint16 {
                                            range "0..64512";
                                        }
                                        sros-ext:auto-restart-to-modify;
                                        sros-ext:isa-auto-clear-on-modify;
                                        description "Size of the port block for NAT subscribers";
                                    }

                                }
                            }
                        } // container port-reservation

                        container watermarks {
                            presence "Enable the watermarks context";
                            description "Enable the watermarks context";

                            leaf high {
                                type types-sros:percent;
                                mandatory true;
                                description "High watermark percentage";
                            }

                            leaf low {
                                type types-sros:percent;
                                mandatory true;
                                description "Low watermark percentage";
                            }

                        } // container watermarks

                        container large-scale {
                            when "../type = 'large-scale'" {
                                description "type must be large-scale";
                            }
                            description "Enter the large-scale context";

                            leaf subscriber-limit {
                                type uint32 {
                                    range "1..65535|4294967295";
                                }
                                sros-ext:isa-auto-clear-on-modify;
                                description "Maximum number of subscribers per IP address";
                            }

                            container redundancy {
                                description "Enter the redundancy context";

                                choice redundancy {
                                    default "export-monitor-route";
                                    case follow-pool {

                                        container follow {
                                            description "Enter the follow context";

                                            leaf router-instance {
                                                type string;
                                                description "Router instance where the lead pool resides";
                                            }

                                            leaf name {
                                                type types-sros:named-item;
                                                description "Name of the pool where activity is shared";
                                            }

                                        } // container follow

                                    }
                                    case export-monitor-route {

                                        leaf export-route {
                                            type types-sros:ipv4-unicast-prefix;
                                            description "Route to export to the peer";
                                        }

                                        leaf monitor-route {
                                            type types-sros:ipv4-unicast-prefix;
                                            description "Monitor the peer route";
                                        }

                                        leaf admin-state {
                                            type types-sros:admin-state;
                                            default "disable";
                                            description "Administrative state of NAT pool redundancy";
                                        }

                                    }
                                }
                            } // container redundancy

                            container flexible-port-allocation {
                                when "../../applications/flexible-port-allocation = 'true'" {
                                    description "application must be flexible-port-allocation";
                                }
                                description "Enter the flexible-port-allocation context";

                                container free-port-limit {
                                    description "Enter the free-port-limit context";

                                    leaf tcp {
                                        type uint32 {
                                            range "1..10000";
                                        }
                                        sros-ext:auto-restart-to-modify;
                                        description "Limit of free ports for TCP per outside IP address";
                                    }

                                    leaf udp {
                                        type uint32 {
                                            range "1..10000";
                                        }
                                        sros-ext:auto-restart-to-modify;
                                        description "Limit of free ports for UDP per outside IP address";
                                    }

                                    leaf icmp {
                                        type uint32 {
                                            range "1..10000";
                                        }
                                        sros-ext:auto-restart-to-modify;
                                        description "Limit of free ports for ICMP per outside IP address";
                                    }

                                } // container free-port-limit

                            } // container flexible-port-allocation

                            container deterministic {
                                description "Enter the deterministic context";

                                leaf port-reservation {
                                    type types-nat:port-number;
                                    sros-ext:auto-restart-to-modify;
                                    sros-ext:isa-auto-clear-on-modify;
                                    description "Number of ports per deterministic port-block";
                                }

                                container watermarks {
                                    presence "Enable the watermarks context";
                                    description "Enable the watermarks context";

                                    leaf high {
                                        type types-sros:percent;
                                        mandatory true;
                                        description "High watermark percentage";
                                    }

                                    leaf low {
                                        type types-sros:percent;
                                        mandatory true;
                                        description "Low watermark percentage";
                                    }

                                } // container watermarks

                            } // container deterministic

                            container default-host {
                                presence "Enable the default-host context";
                                description "Enable the default-host context";

                                leaf ip-address {
                                    type types-sros:ipv4-unicast-address;
                                    description "IP address of the default DMZ host";
                                }

                                leaf inside-router-instance {
                                    type string;
                                    description "Router instance of the DMZ";
                                }

                                leaf rate-limit {
                                    type int32 {
                                        range "1..10000";
                                    }
                                    units "megabps";
                                    default "10";
                                    description "Rate limit for unknown traffic sent to default DMZ host";
                                }

                            } // container default-host

                        } // container large-scale

                        container l2-aware {
                            when "../type = 'l2-aware'" {
                                description "type must be l2-aware";
                            }
                            description "Enter the l2-aware context";

                            leaf external-assignment {
                                type boolean;
                                sros-ext:auto-restart-to-modify;
                                sros-ext:isa-auto-clear-on-modify;
                                default "false";
                                description "External IP address for Layer-2-aware";
                            }

                            container port-block-extension {
                                presence "Enable the port-block-extension context";
                                sros-ext:auto-restart-to-modify;
                                description "Enable the port-block-extension context";

                                leaf ports {
                                    type uint32 {
                                        range "10..5000";
                                    }
                                    sros-ext:auto-restart-to-modify;
                                    mandatory true;
                                    description "Number of ports per dynamic port-block";
                                }

                                leaf subscriber-limit {
                                    type uint32 {
                                        range "2..2000";
                                    }
                                    sros-ext:auto-restart-to-modify;
                                    mandatory true;
                                    description "Number of L2-Aware NAT subscribers per outside address";
                                }

                                container subscriber {
                                    description "Enter the subscriber context";

                                    container watermarks {
                                        presence "Enable the watermarks context";
                                        description "Enable the watermarks context";

                                        leaf high {
                                            type types-sros:percent;
                                            mandatory true;
                                            description "High watermark percentage";
                                        }

                                        leaf low {
                                            type types-sros:percent;
                                            mandatory true;
                                            description "Low watermark percentage";
                                        }

                                    } // container watermarks

                                } // container subscriber

                                container watermarks {
                                    presence "Enable the watermarks context";
                                    description "Enable the watermarks context";

                                    leaf high {
                                        type types-sros:percent;
                                        mandatory true;
                                        description "High watermark percentage";
                                    }

                                    leaf low {
                                        type types-sros:percent;
                                        mandatory true;
                                        description "Low watermark percentage";
                                    }

                                } // container watermarks

                            } // container port-block-extension

                            container default-host {
                                presence "Enable the default-host context";
                                description "Enable the default-host context";

                                leaf ip-address {
                                    type types-sros:ipv4-unicast-address;
                                    description "IP address of the default DMZ host";
                                }

                                leaf inside-router-instance {
                                    type string;
                                    description "Router instance of the DMZ";
                                }

                                leaf rate-limit {
                                    type int32 {
                                        range "1..10000";
                                    }
                                    units "megabps";
                                    default "10";
                                    description "Rate limit for unknown traffic sent to default DMZ host";
                                }

                            } // container default-host

                        } // container l2-aware

                        list address-range {
                            key "start end";
                            max-elements 4096;
                            description "Enter the address-range list instance";

                            leaf start {
                                type types-sros:ipv4-unicast-address;
                                description "Lower bound of the NAT address range";
                            }

                            leaf end {
                                type types-sros:ipv4-unicast-address;
                                description "Upper bound of the NAT address range";
                            }

                            leaf description {
                                type types-sros:description;
                                description "Text description";
                            }

                            leaf drain {
                                type boolean;
                                default "false";
                                description "Start or stop draining this NAT address range";
                            }

                            leaf-list apply-groups {
                                type leafref {
                                    path "../../../../../../../groups/group/name";
                                }
                                max-elements 8;
                                ordered-by user;
                                description "Apply a configuration group at this level";
                            }

                            leaf-list apply-groups-exclude {
                                type leafref {
                                    path "../../../../../../../groups/group/name";
                                }
                                max-elements 8;
                                ordered-by user;
                                description "Exclude a configuration group at this level";
                            }

                        } // list address-range

                    } // list pool

                } // container outside

                container map {
                    description "Enter the map context";

                    list map-domain {
                        key "domain-name";
                        description "Add a list entry for map-domain";

                        leaf domain-name {
                            type leafref {
                                path "../../../../../nat/map-t/domain/name";
                            }
                            description "MAP domain template name";
                        }

                    } // list map-domain

                } // container map

            } // container nat

            container firewall {
                description "Enter the firewall context";

                leaf-list apply-groups {
                    type leafref {
                        path "../../../../groups/group/name";
                    }
                    max-elements 8;
                    ordered-by user;
                    description "Apply a configuration group at this level";
                }

                leaf-list apply-groups-exclude {
                    type leafref {
                        path "../../../../groups/group/name";
                    }
                    max-elements 8;
                    ordered-by user;
                    description "Exclude a configuration group at this level";
                }

                list domain {
                    key "name";
                    max-elements 1024;
                    description "Enter the domain list instance";

                    leaf name {
                        type types-sros:named-item;
                        description "Firewall domain name";
                    }

                    leaf admin-state {
                        type types-sros:admin-state;
                        default "disable";
                        description "Administrative state of the firewall domain";
                    }

                    leaf-list apply-groups {
                        type leafref {
                            path "../../../../../groups/group/name";
                        }
                        max-elements 8;
                        ordered-by user;
                        description "Apply a configuration group at this level";
                    }

                    leaf-list apply-groups-exclude {
                        type leafref {
                            path "../../../../../groups/group/name";
                        }
                        max-elements 8;
                        ordered-by user;
                        description "Exclude a configuration group at this level";
                    }

                    choice isa {
                        mandatory true;
                        case nat {

                            leaf nat-group {
                                type leafref {
                                    path "../../../../../isa/nat-group/id";
                                }
                                sros-ext:immutable;
                                description "NAT group for this domain";
                            }

                        }
                        case wlan-gw {

                            leaf wlan-gw-group {
                                type leafref {
                                    path "../../../../../isa/wlan-gw-group/id";
                                }
                                sros-ext:immutable;
                                description "WLAN GW group used for NAT";
                            }

                        }
                    }
                    container dhcpv6-server {
                        description "Enter the dhcpv6-server context";

                        leaf router-instance {
                            type string;
                            sros-ext:auto-restart-to-modify;
                            description "Router name";
                        }

                        leaf name {
                            type types-sros:named-item;
                            sros-ext:auto-restart-to-modify;
                            description "DHCPv6 server name";
                        }

                    } // container dhcpv6-server

                    list prefix {
                        key "ip-prefix";
                        max-elements 4096;
                        description "Enter the prefix list instance";

                        leaf ip-prefix {
                            type types-sros:ipv6-unicast-prefix;
                            description "IP prefix and prefix length for the domain firewall";
                        }

                        leaf description {
                            type types-sros:description;
                            description "Text description";
                        }

                        leaf-list apply-groups {
                            type leafref {
                                path "../../../../../../groups/group/name";
                            }
                            max-elements 8;
                            ordered-by user;
                            description "Apply a configuration group at this level";
                        }

                        leaf-list apply-groups-exclude {
                            type leafref {
                                path "../../../../../../groups/group/name";
                            }
                            max-elements 8;
                            ordered-by user;
                            description "Exclude a configuration group at this level";
                        }

                    } // list prefix

                } // list domain

            } // container firewall

            container gtp {
                description "Enter the gtp context";

                container s11 {
                    description "Enter the s11 context";

                    list interface {
                        key "interface-name";
                        description "Enter the interface list instance";

                        leaf interface-name {
                            type leafref {
                                path "../../../../../vprn[service-name=current()/../../../../service-name]/interface/interface-name";
                            }
                            description "Interface name";
                        }

                        leaf apn-policy {
                            type leafref {
                                path "../../../../../../subscriber-mgmt/gtp/apn-policy/name";
                            }
                            description "Access Point Name (APN) policy for the S11 interface";
                        }

                        leaf-list apply-groups {
                            type leafref {
                                path "../../../../../../groups/group/name";
                            }
                            max-elements 8;
                            ordered-by user;
                            description "Apply a configuration group at this level";
                        }

                        leaf-list apply-groups-exclude {
                            type leafref {
                                path "../../../../../../groups/group/name";
                            }
                            max-elements 8;
                            ordered-by user;
                            description "Exclude a configuration group at this level";
                        }

                    } // list interface

                    container peer-profile-map {
                        description "Enter the peer-profile-map context";

                        list prefix {
                            key "peer-prefix";
                            description "Enter the prefix list instance";

                            leaf peer-prefix {
                                type types-sros:ip-unicast-prefix;
                                description "IP prefix and prefix length of the subnet";
                            }

                            leaf peer-profile {
                                type leafref {
                                    path "../../../../../../../subscriber-mgmt/gtp/peer-profile/name";
                                }
                                mandatory true;
                                description "Peer profile used for peers in this prefix";
                            }

                            leaf-list apply-groups {
                                type leafref {
                                    path "../../../../../../../groups/group/name";
                                }
                                max-elements 8;
                                ordered-by user;
                                description "Apply a configuration group at this level";
                            }

                            leaf-list apply-groups-exclude {
                                type leafref {
                                    path "../../../../../../../groups/group/name";
                                }
                                max-elements 8;
                                ordered-by user;
                                description "Exclude a configuration group at this level";
                            }

                        } // list prefix

                    } // container peer-profile-map

                } // container s11

                container upf-data-endpoint {
                    presence "Enable the upf-data-endpoint context";
                    description "Enable the upf-data-endpoint context";

                    leaf interface {
                        type leafref {
                            path "../../../../vprn[service-name=current()/../../../service-name]/interface/interface-name";
                        }
                        mandatory true;
                        description "Interface on which the GTP-U packets terminate";
                    }

                    leaf fpe {
                        type leafref {
                            path "../../../../../fwd-path-ext/fpe/fpe-id";
                        }
                        mandatory true;
                        description "FPE used to encapsulate and decapsulate GTP-U traffic";
                    }

                    leaf secondary-interface {
                        type leafref {
                            path "../../../../vprn[service-name=current()/../../../service-name]/interface/interface-name";
                        }
                        description "Secondary interface on which GTP traffic terminates";
                    }

                    leaf-list apply-groups {
                        type leafref {
                            path "../../../../../groups/group/name";
                        }
                        max-elements 8;
                        ordered-by user;
                        description "Apply a configuration group at this level";
                    }

                    leaf-list apply-groups-exclude {
                        type leafref {
                            path "../../../../../groups/group/name";
                        }
                        max-elements 8;
                        ordered-by user;
                        description "Exclude a configuration group at this level";
                    }

                } // container upf-data-endpoint

                container uplink {
                    presence "Enable the uplink context";
                    description "Enable the uplink context";

                    leaf apn {
                        type string {
                            length "1..80";
                            pattern "([a-zA-Z0-9]+-+)*([a-zA-Z0-9]+\\.([a-zA-Z0-9]+-+)*)*[a-zA-Z0-9]+" {
                                error-message "wrong format of apn name";
                            }
                        }
                        description "Network Identifier part of APN";
                    }

                    leaf pdn-type {
                        type enumeration {
                            enum ipv4                           { value 0; }
                            enum ipv6                           { value 1; }
                            enum ipv4v6                         { value 2; }
                        }
                        default "ipv4";
                        description "Default 3GPP PDN in GTP";
                    }

                    leaf-list apply-groups {
                        type leafref {
                            path "../../../../../groups/group/name";
                        }
                        max-elements 8;
                        ordered-by user;
                        description "Apply a configuration group at this level";
                    }

                    leaf-list apply-groups-exclude {
                        type leafref {
                            path "../../../../../groups/group/name";
                        }
                        max-elements 8;
                        ordered-by user;
                        description "Exclude a configuration group at this level";
                    }

                    container peer-profile-map {
                        description "Enter the peer-profile-map context";

                        list prefix {
                            key "peer-prefix";
                            description "Enter the prefix list instance";

                            leaf peer-prefix {
                                type types-sros:ip-unicast-prefix;
                                description "IP prefix and prefix length of the subnet";
                            }

                            leaf peer-profile {
                                type leafref {
                                    path "../../../../../../../subscriber-mgmt/gtp/peer-profile/name";
                                }
                                mandatory true;
                                description "Peer profile name";
                            }

                            leaf-list apply-groups {
                                type leafref {
                                    path "../../../../../../../groups/group/name";
                                }
                                max-elements 8;
                                ordered-by user;
                                description "Apply a configuration group at this level";
                            }

                            leaf-list apply-groups-exclude {
                                type leafref {
                                    path "../../../../../../../groups/group/name";
                                }
                                max-elements 8;
                                ordered-by user;
                                description "Exclude a configuration group at this level";
                            }

                        } // list prefix

                    } // container peer-profile-map

                } // container uplink

            } // container gtp

            container l2tp {
                presence "Enable the l2tp context";
                description "Enable the l2tp context";

                leaf admin-state {
                    type types-sros:admin-state;
                    default "disable";
                    description "Administrative state of L2TP";
                }

                leaf local-address {
                    type types-sros:ipv4-unicast-address;
                    description "Local address";
                }

                leaf receive-window-size {
                    type types-l2tp:base-receive-window-size;
                    description "L2TP receive window size";
                }

                leaf hello-interval {
                    type types-l2tp:base-hello-interval;
                    description "Hello interval";
                }

                leaf idle-timeout {
                    type types-l2tp:base-idle-timeout;
                    description "Idle timeout";
                }

                leaf destruct-timeout {
                    type types-l2tp:base-destruct-timeout;
                    description "Destruction timeout";
                }

                leaf max-retries-estab {
                    type types-l2tp:base-max-retries;
                    description "Maximum retries for established tunnels";
                }

                leaf max-retries-not-estab {
                    type types-l2tp:base-max-retries;
                    description "Maximum retries for unestablished tunnels";
                }

                leaf rtm-debounce-time {
                    type types-l2tp:rtm-debounce-time;
                    description "Debounce timer that declares L2TP action for route table management events";
                }

                leaf radius-accounting-policy {
                    type leafref {
                        path "../../../../aaa/radius/l2tp-accounting-policy/name";
                    }
                    description "RADIUS accounting policy";
                }

                leaf peer-address-change-policy {
                    type types-l2tp:peer-address-change-policy-option;
                    description "Reaction for L2TP response from a different address";
                }

                leaf local-name {
                    type types-l2tp:host-name;
                    description "Local host name";
                }

                leaf password {
                    type types-sros:encrypted-leaf {
                        length "1..115";
                    }
                    description "L2TP password";
                }

                leaf challenge {
                    type boolean;
                    default "false";
                    description "Use challenge-response authentication";
                }

                leaf avp-hiding {
                    type types-l2tp:base-avp-hiding;
                    description "Attribute of the Value Pair (AVP) hiding algorithm";
                }

                leaf session-limit {
                    type types-l2tp:base-session-limit;
                    description "L2TP session limit of this router";
                }

                leaf group-session-limit {
                    type types-l2tp:base-session-limit;
                    description "L2TP session limit for each group of this router";
                }

                leaf tunnel-session-limit {
                    type types-l2tp:base-tunnel-session-limit;
                    description "L2TP session limit for each tunnel of this router";
                }

                leaf session-assign-method {
                    type types-l2tp:base-session-assign-method;
                    description "Session assignment method";
                }

                leaf next-attempt {
                    type enumeration {
                        enum same-preference-level          { value 0; }
                        enum next-preference-level          { value 1; }
                    }
                    default "next-preference-level";
                    description "Tunnel that is selected when previous session setup failed";
                }

                leaf-list apply-groups {
                    type leafref {
                        path "../../../../groups/group/name";
                    }
                    max-elements 8;
                    ordered-by user;
                    description "Apply a configuration group at this level";
                }

                leaf-list apply-groups-exclude {
                    type leafref {
                        path "../../../../groups/group/name";
                    }
                    max-elements 8;
                    ordered-by user;
                    description "Exclude a configuration group at this level";
                }

                container exclude-avps {
                    description "Enter the exclude-avps context";

                    leaf calling-number {
                        type boolean;
                        default "false";
                        description "Calling Number AVP to exclude";
                    }

                    leaf initial-rx-lcp-conf-req {
                        type boolean;
                        default "false";
                        description "Exclude the Initial Received LCP CONFREQ AVP";
                    }

                } // container exclude-avps

                container ignore-avps {
                    description "Enter the ignore-avps context";

                    leaf sequencing-required {
                        type boolean;
                        default "false";
                        description "Ignore Sequencing Required AVP";
                    }

                } // container ignore-avps

                container replace-result-code {
                    description "Enter the replace-result-code context";

                    leaf cdn-invalid-dst {
                        type boolean;
                        default "false";
                        description "Replace result code with general error code";
                    }

                    leaf cdn-permanent-no-facilities {
                        type boolean;
                        default "false";
                        description "Replace result code with general error";
                    }

                    leaf cdn-temporary-no-facilities {
                        type boolean;
                        default "false";
                        description "Replace result code with general error";
                    }

                } // container replace-result-code

                container lac {
                    description "Enter the lac context";

                    leaf df-bit {
                        type boolean;
                        default "true";
                        description "Send all L2TP packets with DF bit set to 1";
                    }

                    leaf calling-number-format {
                        type types-sros:ascii-specification {
                            length "1..255";
                            pattern "([^%]+|%[Scrsl%])+";
                        }
                        default "%S %s";
                        description "Calling Number AVP for L2TP control messages";
                    }

                    container cisco-nas-port {
                        description "Enter the cisco-nas-port context";

                        leaf ethernet {
                            type types-sros:binary-specification {
                                pattern "([01]|(\\*[0123456789]+)?[smpoi])+";
                            }
                            description "L2TP Cisco NAS port AVP with binary patterns for Ethernet";
                        }

                    } // container cisco-nas-port

                } // container lac

                container tunnel-selection-blacklist {
                    description "Enter the tunnel-selection-blacklist context";

                    leaf max-time {
                        type int32 {
                            range "1..60";
                        }
                        units "minutes";
                        default "5";
                        description "Time that a tunnel or peer can remain in the denylist";
                    }

                    leaf max-list-length {
                        type union {
                            type int32 {
                                range "1..65535";
                            }
                            type enumeration {
                                enum infinite                       { value -1; }
                            }
                        }
                        default "infinite";
                        description "Number of tunnels or peers in the denylist";
                    }

                    leaf timeout-action {
                        type enumeration {
                            enum remove-from-blacklist          { value 0; }
                            enum try-one-session                { value 1; }
                        }
                        default "remove-from-blacklist";
                        description "Action when a tunnel or peer exceeds time in denylist";
                    }

                    container add-tunnel-on {
                        description "Enter the add-tunnel-on context";

                        leaf address-change-timeout {
                            type boolean;
                            default "false";
                            description "Enable a timed-out tunnel to be forced to the denylist";
                        }

                        leaf cdn-err-code {
                            type boolean;
                            default "false";
                            description "Add to deny if CDN is received with code: General error";
                        }

                        leaf cdn-invalid-dst {
                            type boolean;
                            default "false";
                            description "Force tunnel to the denylist in case of Result Codes 6";
                        }

                        leaf cdn-permanent-no-facilities {
                            type boolean;
                            default "false";
                            description "Force tunnel to the denylist in case of Result Codes 5";
                        }

                        leaf cdn-temporary-no-facilities {
                            type boolean;
                            default "false";
                            description "Force tunnel to the denylist in case of Result Codes 4";
                        }

                        leaf stop-ccn-err-code {
                            type boolean;
                            default "false";
                            description "Add to denylist if received with general error code";
                        }

                        leaf stop-ccn-other {
                            type boolean;
                            default "false";
                            description "Add to denylist if StopCCN received with general error";
                        }

                        leaf tx-cdn-not-established-in-time {
                            type boolean;
                            default "false";
                            description "Add to denylist if CDN transmitted with result code";
                        }

                    } // container add-tunnel-on

                } // container tunnel-selection-blacklist

                container failover {
                    description "Enter the failover context";

                    leaf recovery-method {
                        type types-l2tp:base-failover-recovery-method;
                        description "Recovery method of the sequence numbers after failover";
                    }

                    leaf recovery-time {
                        type types-l2tp:base-failover-recovery-time;
                        description "Time requested from the L2TP peer before assuming failover as failed";
                    }

                    leaf recovery-max-session-lifetime {
                        type uint32 {
                            range "2..4294967295";
                        }
                        units "centiseconds";
                        default "2";
                        description "Subset of sessions that this system attempts to synchronize in the Session State Synchronization phase";
                    }

                    list track-srrp {
                        key "id";
                        description "Enter the track-srrp list instance";

                        leaf id {
                            type leafref {
                                path "../../../../../../redundancy/multi-chassis/peer/sync/track-srrp/id";
                            }
                            description "SRRP instance ID for multi-chassis redundancy failover";
                        }

                        leaf peer {
                            type leafref {
                                path "../../../../../../redundancy/multi-chassis/peer/ip-address";
                            }
                            mandatory true;
                            description "Multi-chassis peer address";
                        }

                        leaf sync-tag {
                            type types-sros:named-item;
                            mandatory true;
                            description "Synchronization tag on the multi-chassis peer";
                        }

                        leaf-list apply-groups {
                            type leafref {
                                path "../../../../../../groups/group/name";
                            }
                            max-elements 8;
                            ordered-by user;
                            description "Apply a configuration group at this level";
                        }

                        leaf-list apply-groups-exclude {
                            type leafref {
                                path "../../../../../../groups/group/name";
                            }
                            max-elements 8;
                            ordered-by user;
                            description "Exclude a configuration group at this level";
                        }

                    } // list track-srrp

                } // container failover

                container l2tpv3 {
                    description "Enter the l2tpv3 context";

                    leaf password {
                        type types-sros:encrypted-leaf {
                            length "1..115";
                        }
                        description "L2TPv3 password";
                    }

                    leaf cookie-length {
                        type types-l2tp:base-v3-cookie-length;
                        description "Cookie field length";
                    }

                    leaf digest-type {
                        type types-l2tp:base-v3-digest-type;
                        description "Hashing algorithm that calculates the message digest";
                    }

                    leaf nonce-length {
                        type types-l2tp:base-v3-nonce-length;
                        description "Length of the local L2TPv3 nonce (random number)";
                    }

                    leaf public-tcp-mss-adjust {
                        type types-l2tp:base-v3-tcp-mss-adjust;
                        description "TCP maximum segment size (MSS) on public network";
                    }

                    leaf private-tcp-mss-adjust {
                        type types-l2tp:base-v3-tcp-mss-adjust;
                        description "TCP maximum segment size (MSS) on private network";
                    }

                    container transport-type {
                        description "Enter the transport-type context";

                        leaf ip {
                            type boolean;
                            default "false";
                            description "Use IP as the transport type for the L2TPv3 tunnel";
                        }

                    } // container transport-type

                } // container l2tpv3

                container ethernet-tunnel {
                    description "Enter the ethernet-tunnel context";

                    leaf reconnect-timeout {
                        type types-l2tp:base-v3-reconnect-timeout;
                        description "Timeout for a session setup retry";
                    }

                } // container ethernet-tunnel

                list group {
                    key "tunnel-group-name";
                    description "Enter the group list instance";

                    leaf tunnel-group-name {
                        type types-sros:named-item-64 {
                            length "1..63";
                        }
                        description "Tunnel group name";
                    }

                    leaf admin-state {
                        type types-sros:admin-state;
                        default "disable";
                        description "Administrative state of the L2TP tunnel group";
                    }

                    leaf description {
                        type types-sros:description;
                        description "Text description";
                    }

                    leaf protocol {
                        type types-l2tp:protocol-version;
                        sros-ext:immutable;
                        description "Protocol version";
                    }

                    leaf local-address {
                        type types-sros:ipv4-unicast-address;
                        description "Local address";
                    }

                    leaf receive-window-size {
                        type types-l2tp:child-receive-window-size;
                        description "L2TP receive window size";
                    }

                    leaf hello-interval {
                        type types-l2tp:child-hello-interval;
                        description "Hello interval";
                    }

                    leaf idle-timeout {
                        type types-l2tp:child-idle-timeout;
                        description "Idle timeout";
                    }

                    leaf destruct-timeout {
                        type types-l2tp:child-destruct-timeout;
                        description "Destruction timeout";
                    }

                    leaf max-retries-estab {
                        type types-l2tp:child-max-retries;
                        description "Maximum retries for established tunnels";
                    }

                    leaf max-retries-not-estab {
                        type types-l2tp:child-max-retries;
                        description "Maximum retries for unestablished tunnels";
                    }

                    leaf radius-accounting-policy {
                        type leafref {
                            path "../../../../../aaa/radius/l2tp-accounting-policy/name";
                        }
                        description "RADIUS accounting policy";
                    }

                    leaf local-name {
                        type types-l2tp:host-name;
                        description "Local host name used to distinguish tunnels";
                    }

                    leaf password {
                        type types-sros:encrypted-leaf {
                            length "1..115";
                        }
                        description "Password between L2TP LAC and LNS";
                    }

                    leaf challenge {
                        type types-sros:bool-with-inherit;
                        description "Enable use of challenge-response authentication";
                    }

                    leaf avp-hiding {
                        type types-l2tp:child-avp-hiding;
                        description "The AVP hiding algorithm";
                    }

                    leaf session-limit {
                        type types-l2tp:child-session-limit;
                        description "Session limit";
                    }

                    leaf session-assign-method {
                        type types-l2tp:child-session-assign-method;
                        description "Session assignment method";
                    }

                    leaf-list apply-groups {
                        type leafref {
                            path "../../../../../groups/group/name";
                        }
                        max-elements 8;
                        ordered-by user;
                        description "Apply a configuration group at this level";
                    }

                    leaf-list apply-groups-exclude {
                        type leafref {
                            path "../../../../../groups/group/name";
                        }
                        max-elements 8;
                        ordered-by user;
                        description "Exclude a configuration group at this level";
                    }

                    container failover {
                        when "../protocol = 'v2'" {
                            description "Protocol must be v2 to access this container";
                        }
                        description "Enter the failover context";

                        leaf recovery-method {
                            type types-l2tp:child-failover-recovery-method;
                            description "Recovery method of the sequence numbers after failover";
                        }

                        leaf recovery-time {
                            type types-l2tp:child-failover-recovery-time;
                            description "Time requested from the L2TP peer before assuming failover as failed";
                        }

                    } // container failover

                    container lac {
                        when "../protocol = 'v2'" {
                            description "Protocol must be v2 to access this container";
                        }
                        description "Enter the lac context";

                        leaf df-bit {
                            type types-sros:bool-with-inherit;
                            description "DF (do not fragment) bit in data traffic transmitted as LAC";
                        }

                    } // container lac

                    container l2tpv3 {
                        when "not(../protocol = 'v2')" {
                            description "Protocol must be v3 or v3draft to access this container";
                        }
                        description "Enter the l2tpv3 context";

                        leaf rem-router-id {
                            type types-sros:ipv4-address;
                            default "0.0.0.0";
                            description "Filter on remote router ID";
                        }

                        leaf password {
                            type types-sros:encrypted-leaf {
                                length "1..115";
                            }
                            description "L2TPv3 password";
                        }

                        leaf track-password-change {
                            type boolean;
                            default "false";
                            description "Enable tracking of password changes";
                        }

                        leaf cookie-length {
                            type types-l2tp:child-v3-cookie-length;
                            description "Cookie field length";
                        }

                        leaf digest-type {
                            type types-l2tp:child-v3-digest-type;
                            description "Hashing algorithm that calculates the message digest";
                        }

                        leaf nonce-length {
                            type types-l2tp:child-v3-nonce-length;
                            description "Length for the local L2TPv3 nonce (random number)";
                        }

                        leaf public-tcp-mss-adjust {
                            type types-l2tp:child-v3-tcp-mss-adjust;
                            description "TCP Maximum Segment Size (MSS) on public network";
                        }

                        leaf private-tcp-mss-adjust {
                            type types-l2tp:child-v3-tcp-mss-adjust;
                            description "TCP maximum segment size (MSS) on private network";
                        }

                        container pw-cap-list {
                            description "Enter the pw-cap-list context";

                            leaf ethernet {
                                type boolean;
                                sros-ext:auto-restart-to-modify;
                                default "false";
                                description "Advertise Ethernet pseudowire type";
                            }

                            leaf ethernet-vlan {
                                type boolean;
                                sros-ext:auto-restart-to-modify;
                                default "false";
                                description "Advertise Ethernet VLAN pseudowire type";
                            }

                        } // container pw-cap-list

                    } // container l2tpv3

                    container ethernet-tunnel {
                        when "not(../protocol = 'v2')" {
                            description "Protocol must be v3 or v3draft to access this container";
                        }
                        description "Enter the ethernet-tunnel context";

                        leaf reconnect-timeout {
                            type types-l2tp:child-v3-reconnect-timeout;
                            description "Timeout for a session setup retry at group level";
                        }

                    } // container ethernet-tunnel

                    container lns {
                        when "../protocol = 'v2'" {
                            description "Protocol must be v2 to access this container";
                        }
                        description "Enter the lns context";

                        leaf load-balance-method {
                            type types-l2tp:base-load-balance-method;
                            default "per-session";
                            description "New sessions for L2TP ISA MDA";
                        }

                        leaf lns-group {
                            type leafref {
                                path "../../../../../../isa/lns-group/id";
                            }
                            description "ISA LNS group";
                        }

                        container ppp {
                            description "Enter the ppp context";

                            leaf authentication-policy {
                                type types-sros:named-item;
                                description "Authentication policy when a DHCP message is received";
                            }

                            leaf user-db {
                                type types-sros:named-item;
                                description "Local user database for PPP PAP and CHAP authentication";
                            }

                            leaf proxy-lcp {
                                type boolean;
                                default "false";
                                description "Proxy LCP AVPs that are received from LAC";
                            }

                            leaf lcp-ignore-magic-numbers {
                                type boolean;
                                default "false";
                                description "Check magic number in echo request and reply messages";
                            }

                            leaf lcp-force-ack-accm {
                                type boolean;
                                default "false";
                                description "Force acknowledgement of the LCP Asynchronous Control Character Map (ACCM) option";
                            }

                            leaf reject-disabled-ncp {
                                type boolean;
                                default "false";
                                description "Force LCP Protocol Reject for IPv6CP Configure Request";
                            }

                            leaf mtu {
                                type types-l2tp:base-ppp-mtu;
                                default "1500";
                                description "Maximum PPP MTU size";
                            }

                            leaf proxy-authentication {
                                type boolean;
                                default "false";
                                description "Use authentication AVPs that are received from LAC";
                            }

                            leaf authentication {
                                type types-l2tp:base-ppp-auth-protocol;
                                default "pref-chap";
                                description "PPP authentication protocol to negotiate";
                            }

                            leaf ipcp-subnet-negotiation {
                                type boolean;
                                default "false";
                                description "Allow IPCP subnet negotiation for PPPoE hosts";
                            }

                            container default-group-interface {
                                description "Enter the default-group-interface context";

                                leaf interface {
                                    type types-sros:named-item;
                                    description "Group interface";
                                }

                                leaf service-name {
                                    type types-services:service-name;
                                    description "Administrative service name";
                                }

                            } // container default-group-interface

                            container keepalive {
                                description "Enter the keepalive context";

                                leaf interval {
                                    type types-l2tp:base-lcp-keepalive-interval;
                                    default "30";
                                    description "PPP keepalive interval";
                                }

                                leaf multiplier {
                                    type types-l2tp:base-lcp-keepalive-multiplier;
                                    default "3";
                                    description "PPP keepalive multiplier";
                                }

                            } // container keepalive

                            container chap-challenge-length {
                                description "Enter the chap-challenge-length context";

                                leaf start {
                                    type types-l2tp:base-chap-challenge-length;
                                    default "32";
                                    description "Lower bound of the PPP CHAP challenge length";
                                }

                                leaf end {
                                    type types-l2tp:base-chap-challenge-length;
                                    default "64";
                                    description "Upper bound of the PPP CHAP challenge length";
                                }

                            } // container chap-challenge-length

                        } // container ppp

                        container mlppp {
                            description "Enter the mlppp context";

                            leaf admin-state {
                                type types-sros:admin-state;
                                default "disable";
                                description "Administrative state of MLPPP in the L2TP tunnel group";
                            }

                            leaf max-links {
                                type types-l2tp:base-mlppp-max-links;
                                default "1";
                                description "Maximum MLPPP links";
                            }

                            leaf interleave {
                                type boolean;
                                default "false";
                                description "Enable link fragmentation and interleaving";
                            }

                            leaf max-fragment-delay {
                                type types-l2tp:base-mlppp-max-frag-delay;
                                default "no-fragmentation";
                                description "Maximum fragment delay caused by transmission on a link";
                            }

                            leaf reassembly-timeout {
                                type types-l2tp:base-mlppp-reassembly-timeout;
                                default "1000";
                                description "Reassembly timeout";
                            }

                            leaf short-sequence-numbers {
                                type boolean;
                                default "false";
                                description "Request a peer to send short sequence numbers";
                            }

                            leaf-list apply-groups {
                                type leafref {
                                    path "../../../../../../../groups/group/name";
                                }
                                max-elements 8;
                                ordered-by user;
                                description "Apply a configuration group at this level";
                            }

                            leaf-list apply-groups-exclude {
                                type leafref {
                                    path "../../../../../../../groups/group/name";
                                }
                                max-elements 8;
                                ordered-by user;
                                description "Exclude a configuration group at this level";
                            }

                            container endpoint {
                                description "Enter the endpoint context";

                                choice endpoint {
                                    case ip {

                                        leaf ip {
                                            type types-ppp:mlppp-ip-endpoint;
                                            description "Endpoint ID as an IP address";
                                        }

                                    }
                                    case mac {

                                        leaf mac {
                                            type types-ppp:mlppp-mac-endpoint;
                                            description "Endpoint ID as a MAC address";
                                        }

                                    }
                                }
                            } // container endpoint

                        } // container mlppp

                    } // container lns

                    list tunnel {
                        key "tunnel-name";
                        max-elements 31;
                        description "Enter the tunnel list instance";

                        leaf tunnel-name {
                            type types-sros:named-item {
                                length "1..32";
                            }
                            description "Tunnel name";
                        }

                        leaf admin-state {
                            type types-sros:admin-state;
                            default "disable";
                            description "Administrative state of the L2TP tunnel";
                        }

                        leaf description {
                            type types-sros:description;
                            description "Text description";
                        }

                        leaf preference {
                            type uint32 {
                                range "0..16777215";
                            }
                            default "50";
                            description "Tunnel preference number with its group";
                        }

                        leaf auto-establish {
                            type boolean;
                            default "false";
                            description "Allow the tunnel to be automatically set up by the system";
                        }

                        leaf peer {
                            type types-sros:ipv4-unicast-address;
                            description "Peer address";
                        }

                        leaf local-address {
                            type types-sros:ipv4-unicast-address;
                            description "Local address";
                        }

                        leaf receive-window-size {
                            type types-l2tp:child-receive-window-size;
                            description "L2TP receive window size";
                        }

                        leaf hello-interval {
                            type types-l2tp:child-hello-interval;
                            description "Hello interval";
                        }

                        leaf idle-timeout {
                            type types-l2tp:child-idle-timeout;
                            description "Idle timeout";
                        }

                        leaf destruct-timeout {
                            type types-l2tp:child-destruct-timeout;
                            description "Destruction timeout";
                        }

                        leaf max-retries-estab {
                            type types-l2tp:child-max-retries;
                            description "Maximum retries for established tunnels";
                        }

                        leaf max-retries-not-estab {
                            type types-l2tp:child-max-retries;
                            description "Maximum retries for unestablished tunnels";
                        }

                        leaf radius-accounting-policy {
                            type leafref {
                                path "../../../../../../aaa/radius/l2tp-accounting-policy/name";
                            }
                            description "RADIUS accounting policy";
                        }

                        leaf remote-name {
                            type types-l2tp:host-name;
                            description "Remote tunnel host name";
                        }

                        leaf local-name {
                            type types-l2tp:host-name;
                            description "Local host name used to distinguish tunnels";
                        }

                        leaf password {
                            type types-sros:encrypted-leaf {
                                length "1..115";
                            }
                            description "Password between L2TP LAC and LNS";
                        }

                        leaf challenge {
                            type types-sros:bool-with-inherit;
                            description "Enable use of challenge-response authentication";
                        }

                        leaf avp-hiding {
                            type types-l2tp:child-avp-hiding;
                            description "The AVP hiding algorithm";
                        }

                        leaf session-limit {
                            type types-l2tp:child-tunnel-session-limit;
                            description "L2TP session limit for each tunnel of this router";
                        }

                        leaf-list apply-groups {
                            type leafref {
                                path "../../../../../../groups/group/name";
                            }
                            max-elements 8;
                            ordered-by user;
                            description "Apply a configuration group at this level";
                        }

                        leaf-list apply-groups-exclude {
                            type leafref {
                                path "../../../../../../groups/group/name";
                            }
                            max-elements 8;
                            ordered-by user;
                            description "Exclude a configuration group at this level";
                        }

                        container failover {
                            when "../../protocol = 'v2'" {
                                description "Protocol must be v2 to access this container";
                            }
                            description "Enter the failover context";

                            leaf recovery-method {
                                type types-l2tp:child-failover-recovery-method;
                                description "Recovery method of the sequence numbers after failover";
                            }

                            leaf recovery-time {
                                type types-l2tp:child-failover-recovery-time;
                                description "Time requested from the L2TP peer before assuming failover as failed";
                            }

                        } // container failover

                        container lac {
                            when "../../protocol = 'v2'" {
                                description "Protocol must be v2 to access this container";
                            }
                            description "Enter the lac context";

                            leaf df-bit {
                                type types-sros:bool-with-inherit;
                                description "DF (do not fragment) bit in data traffic transmitted as LAC";
                            }

                        } // container lac

                        container l2tpv3 {
                            when "not(../../protocol = 'v2')" {
                                description "Protocol must be v3 or v3draft to access this container";
                            }
                            description "Enter the l2tpv3 context";

                            leaf public-tcp-mss-adjust {
                                type types-l2tp:child-v3-tcp-mss-adjust;
                                description "TCP maximum segment size (MSS) on public network";
                            }

                            leaf private-tcp-mss-adjust {
                                type types-l2tp:child-v3-tcp-mss-adjust;
                                description "TCP maximum segment size (MSS) on private network";
                            }

                        } // container l2tpv3

                        container lns {
                            when "../../protocol = 'v2'" {
                                description "Protocol must be v2 to access this container";
                            }
                            description "Enter the lns context";

                            leaf load-balance-method {
                                type types-l2tp:child-load-balance-method;
                                description "New sessions for L2TP ISA MDA";
                            }

                            leaf lns-group {
                                type leafref {
                                    path "../../../../../../../isa/lns-group/id";
                                }
                                description "ISA LNS group";
                            }

                            container ppp {
                                description "Enter the ppp context";

                                leaf authentication-policy {
                                    type types-sros:named-item;
                                    description "Authentication policy when a DHCP message is received";
                                }

                                leaf user-db {
                                    type types-sros:named-item;
                                    description "Local user database for PPP PAP and CHAP authentication";
                                }

                                leaf proxy-lcp {
                                    type types-sros:bool-with-inherit;
                                    description "Use the Proxy LCP AVPs that are received from the LAC";
                                }

                                leaf lcp-ignore-magic-numbers {
                                    type types-sros:bool-with-inherit;
                                    description "Magic-Number field in LCP Echo-Request and LCP Echo-Reply messages that are checked";
                                }

                                leaf lcp-force-ack-accm {
                                    type types-sros:bool-with-inherit;
                                    description "Forced acknowledgement of the LCP Asynchronous Control Character Map (ACCM) option";
                                }

                                leaf reject-disabled-ncp {
                                    type types-sros:bool-with-inherit;
                                    description "Force LCP Project Reject for IPv6CP Configure Request";
                                }

                                leaf mtu {
                                    type types-l2tp:child-ppp-mtu;
                                    description "Maximum PPP MTU size";
                                }

                                leaf proxy-authentication {
                                    type types-sros:bool-with-inherit;
                                    description "Authentication AVPs that are received from LAC";
                                }

                                leaf authentication {
                                    type types-l2tp:child-ppp-auth-protocol;
                                    description "PPP authentication protocol to negotiate";
                                }

                                leaf ipcp-subnet-negotiation {
                                    type types-sros:bool-with-inherit;
                                    description "Use of IPCP subnet negotiation for PPPoE hosts";
                                }

                                container default-group-interface {
                                    description "Enter the default-group-interface context";

                                    leaf interface {
                                        type types-sros:named-item;
                                        description "Group interface";
                                    }

                                    leaf service-name {
                                        type types-services:service-name;
                                        description "Administrative service name";
                                    }

                                } // container default-group-interface

                                container keepalive {
                                    description "Enter the keepalive context";

                                    leaf interval {
                                        type types-l2tp:child-lcp-keepalive-interval;
                                        description "PPP keepalive interval";
                                    }

                                    leaf multiplier {
                                        type types-l2tp:child-lcp-keepalive-multiplier;
                                        description "PPP keepalive multiplier";
                                    }

                                } // container keepalive

                                container chap-challenge-length {
                                    description "Enter the chap-challenge-length context";

                                    leaf start {
                                        type types-l2tp:child-chap-challenge-length;
                                        description "Lower bound of the PPP CHAP challenge length";
                                    }

                                    leaf end {
                                        type types-l2tp:child-chap-challenge-length;
                                        description "Upper bound of the PPP CHAP challenge length";
                                    }

                                } // container chap-challenge-length

                            } // container ppp

                            container mlppp {
                                description "Enter the mlppp context";

                                leaf admin-state {
                                    type types-sros:admin-state-with-inherit;
                                    description "Administrative state of MLPPP in the L2TP tunnel";
                                }

                                leaf max-links {
                                    type types-l2tp:child-mlppp-max-links;
                                    description "Maximum MLPPP links";
                                }

                                leaf interleave {
                                    type types-sros:bool-with-inherit;
                                    description "Use of Link fragmentation and interleaving";
                                }

                                leaf max-fragment-delay {
                                    type types-l2tp:child-mlppp-max-frag-delay;
                                    description "Maximum fragment delay caused by transmission on a link";
                                }

                                leaf reassembly-timeout {
                                    type types-l2tp:child-mlppp-reassembly-timeout;
                                    description "Reassembly timeout";
                                }

                                leaf short-sequence-numbers {
                                    type types-sros:bool-with-inherit;
                                    description "Request a peer to send short sequence numbers";
                                }

                                leaf-list apply-groups {
                                    type leafref {
                                        path "../../../../../../../../groups/group/name";
                                    }
                                    max-elements 8;
                                    ordered-by user;
                                    description "Apply a configuration group at this level";
                                }

                                leaf-list apply-groups-exclude {
                                    type leafref {
                                        path "../../../../../../../../groups/group/name";
                                    }
                                    max-elements 8;
                                    ordered-by user;
                                    description "Exclude a configuration group at this level";
                                }

                                container endpoint {
                                    description "Enter the endpoint context";

                                    choice endpoint {
                                        case ip {

                                            leaf ip {
                                                type types-ppp:mlppp-ip-endpoint;
                                                description "Endpoint ID as an IP address";
                                            }

                                        }
                                        case mac {

                                            leaf mac {
                                                type types-ppp:mlppp-mac-endpoint;
                                                description "Endpoint ID as a MAC address";
                                            }

                                        }
                                    }
                                } // container endpoint

                            } // container mlppp

                        } // container lns

                    } // list tunnel

                } // list group

            } // container l2tp

            container igmp {
                presence "Enable the igmp context";
                description "Enable the igmp context";

                leaf group-if-query-source-address {
                    type types-sros:ipv4-unicast-address;
                    description "Default query-source address for all group interfaces";
                }

                leaf query-interval {
                    type uint32 {
                        range "2..1024";
                    }
                    units "seconds";
                    default "125";
                    description "Time between two consecutive host-query messages";
                }

                leaf query-last-member-interval {
                    type uint32 {
                        range "1..1023";
                    }
                    units "seconds";
                    default "1";
                    description "Time between group-specific query messages";
                }

                leaf query-response-interval {
                    type uint32 {
                        range "1..1023";
                    }
                    units "seconds";
                    default "10";
                    description "Time to wait for a response to the host-query messages";
                }

                leaf robust-count {
                    type uint32 {
                        range "2..10";
                    }
                    default "2";
                    description "Number of retries after expected message loss";
                }

                leaf admin-state {
                    type types-sros:admin-state;
                    default "enable";
                    description "Administrative state of IGMP";
                }

                leaf-list apply-groups {
                    type leafref {
                        path "../../../../groups/group/name";
                    }
                    max-elements 8;
                    ordered-by user;
                    description "Apply a configuration group at this level";
                }

                leaf-list apply-groups-exclude {
                    type leafref {
                        path "../../../../groups/group/name";
                    }
                    max-elements 8;
                    ordered-by user;
                    description "Exclude a configuration group at this level";
                }

                container ssm-translate {
                    description "Enter the ssm-translate context";

                    list group-range {
                        key "start end";
                        description "Enter the group-range list instance";

                        leaf start {
                            type types-sros:ipv4-multicast-address;
                            description "Lower bound of the IP address group range";
                        }

                        leaf end {
                            type types-sros:ipv4-multicast-address;
                            description "Upper bound of the IP address group range";
                        }

                        leaf-list apply-groups {
                            type leafref {
                                path "../../../../../../groups/group/name";
                            }
                            max-elements 8;
                            ordered-by user;
                            description "Apply a configuration group at this level";
                        }

                        leaf-list apply-groups-exclude {
                            type leafref {
                                path "../../../../../../groups/group/name";
                            }
                            max-elements 8;
                            ordered-by user;
                            description "Exclude a configuration group at this level";
                        }

                        list source {
                            key "source-address";
                            min-elements 1;
                            description "Add a list entry for source";

                            leaf source-address {
                                type types-sros:ipv4-unicast-address;
                                description "Source IP address of multicast channel sending data";
                            }

                        } // list source

                    } // list group-range

                } // container ssm-translate

                list interface {
                    key "ip-interface-name";
                    description "Enter the interface list instance";

                    leaf ip-interface-name {
                        type types-sros:interface-name;
                        description "IP interface name";
                    }

                    leaf router-alert-check {
                        type boolean;
                        default "true";
                        description "Enable router alert checking for IGMP or MLD messages";
                    }

                    leaf maximum-number-groups {
                        type uint32 {
                            range "1..16000";
                        }
                        description "Maximum number of groups for this interface";
                    }

                    leaf maximum-number-group-sources {
                        type uint32 {
                            range "1..32000";
                        }
                        description "Maximum number of group sources for this interface";
                    }

                    leaf maximum-number-sources {
                        type uint32 {
                            range "1..1000";
                        }
                        description "Maximum number of sources that are allowed per group";
                    }

                    leaf query-interval {
                        type uint32 {
                            range "2..1024";
                        }
                        description "Time between two consecutive host-query messages";
                    }

                    leaf query-response-interval {
                        type uint32 {
                            range "1..1023";
                        }
                        description "Time to wait for a response to the host-query messages";
                    }

                    leaf query-last-member-interval {
                        type uint32 {
                            range "1..1023";
                        }
                        description "Time between group-specific query messages";
                    }

                    leaf admin-state {
                        type types-sros:admin-state;
                        default "enable";
                        description "Administrative state of IGMP";
                    }

                    leaf import-policy {
                        type leafref {
                            path "../../../../../policy-options/policy-statement/name";
                        }
                        description "Import policy that filters IGMP packets";
                    }

                    leaf subnet-check {
                        type boolean;
                        default "true";
                        description "Allow subnet checking";
                    }

                    leaf version {
                        type types-igmp:igmp-version;
                        default "3";
                        description "IGMP protocol version";
                    }

                    leaf redundant-mcast {
                        type boolean;
                        default "false";
                        description "Use interface as a redundant-pair member for multicast";
                    }

                    leaf-list apply-groups {
                        type leafref {
                            path "../../../../../groups/group/name";
                        }
                        max-elements 8;
                        ordered-by user;
                        description "Apply a configuration group at this level";
                    }

                    leaf-list apply-groups-exclude {
                        type leafref {
                            path "../../../../../groups/group/name";
                        }
                        max-elements 8;
                        ordered-by user;
                        description "Exclude a configuration group at this level";
                    }

                    container mcac {
                        description "Enter the mcac context";

                        leaf interface-policy {
                            type leafref {
                                path "../../../../../../mcac/interface-policy/policy-name";
                            }
                            description "Name of multicast CAC interface policy";
                        }

                        leaf policy {
                            type leafref {
                                path "../../../../../../mcac/policy/policy-name";
                            }
                            description "Multicast CAC policy name";
                        }

                        container mc-constraints {
                            description "Enter the mc-constraints context";

                            leaf use-lag-port-weight {
                                type boolean;
                                default "false";
                                description "Use LAG port weight in calculating MCAC constraints";
                            }

                            list level {
                                key "level-id";
                                description "Enter the level list instance";

                                leaf level-id {
                                    type types-mcast-cac:constraints-level;
                                    description "Bandwidth level ID for an MCAC constraint";
                                }

                                leaf bandwidth {
                                    type types-mcast-cac:bandwidth {
                                        range "0..2147483647";
                                    }
                                    mandatory true;
                                    description "Bandwidth available for this level";
                                }

                                leaf-list apply-groups {
                                    type leafref {
                                        path "../../../../../../../../groups/group/name";
                                    }
                                    max-elements 8;
                                    ordered-by user;
                                    description "Apply a configuration group at this level";
                                }

                                leaf-list apply-groups-exclude {
                                    type leafref {
                                        path "../../../../../../../../groups/group/name";
                                    }
                                    max-elements 8;
                                    ordered-by user;
                                    description "Exclude a configuration group at this level";
                                }

                            } // list level

                            list number-down {
                                key "number-lag-port-down";
                                description "Enter the number-down list instance";

                                leaf number-lag-port-down {
                                    type uint32 {
                                        range "1..64";
                                    }
                                    description "Number of ports that are down in this LAG link";
                                }

                                leaf level {
                                    type types-mcast-cac:constraints-level;
                                    mandatory true;
                                    description "Level ID to associate with number of down LAG ports";
                                }

                                leaf-list apply-groups {
                                    type leafref {
                                        path "../../../../../../../../groups/group/name";
                                    }
                                    max-elements 8;
                                    ordered-by user;
                                    description "Apply a configuration group at this level";
                                }

                                leaf-list apply-groups-exclude {
                                    type leafref {
                                        path "../../../../../../../../groups/group/name";
                                    }
                                    max-elements 8;
                                    ordered-by user;
                                    description "Exclude a configuration group at this level";
                                }

                            } // list number-down

                        } // container mc-constraints

                        container bandwidth {
                            description "Enter the bandwidth context";

                            leaf total {
                                type types-mcast-cac:bandwidth-limit;
                                description "Maximum allowed bandwidth";
                            }

                            leaf mandatory {
                                type types-mcast-cac:bandwidth-limit;
                                description "Pre-reserved bandwidth for all mandatory channels";
                            }

                        } // container bandwidth

                    } // container mcac

                    container ssm-translate {
                        description "Enter the ssm-translate context";

                        list group-range {
                            key "start end";
                            description "Enter the group-range list instance";

                            leaf start {
                                type types-sros:ipv4-multicast-address;
                                description "Lower bound of the IP address group range";
                            }

                            leaf end {
                                type types-sros:ipv4-multicast-address;
                                description "Upper bound of the IP address group range";
                            }

                            leaf-list apply-groups {
                                type leafref {
                                    path "../../../../../../../groups/group/name";
                                }
                                max-elements 8;
                                ordered-by user;
                                description "Apply a configuration group at this level";
                            }

                            leaf-list apply-groups-exclude {
                                type leafref {
                                    path "../../../../../../../groups/group/name";
                                }
                                max-elements 8;
                                ordered-by user;
                                description "Exclude a configuration group at this level";
                            }

                            list source {
                                key "source-address";
                                min-elements 1;
                                description "Add a list entry for source";

                                leaf source-address {
                                    type types-sros:ipv4-unicast-address;
                                    description "Source IP address of multicast channel sending data";
                                }

                            } // list source

                        } // list group-range

                    } // container ssm-translate

                    container static {
                        description "Enter the static context";

                        list group {
                            key "group-address";
                            description "Enter the group list instance";

                            leaf group-address {
                                type types-sros:ipv4-multicast-address;
                                description "Group address of static IGMP multicast channel";
                            }

                            leaf-list apply-groups {
                                type leafref {
                                    path "../../../../../../../groups/group/name";
                                }
                                max-elements 8;
                                ordered-by user;
                                description "Apply a configuration group at this level";
                            }

                            leaf-list apply-groups-exclude {
                                type leafref {
                                    path "../../../../../../../groups/group/name";
                                }
                                max-elements 8;
                                ordered-by user;
                                description "Exclude a configuration group at this level";
                            }

                            choice source-or-starg {
                                mandatory true;
                                case source {

                                    list source {
                                        key "source-address";
                                        description "Add a list entry for source";

                                        leaf source-address {
                                            type types-sros:ipv4-unicast-address;
                                            description "Source IP address of multicast channel sending data";
                                        }

                                    } // list source

                                }
                                case starg {

                                    leaf starg {
                                        type empty;
                                        description "any source address (*,G)";
                                    }

                                }
                            }
                        } // list group

                        list group-range {
                            key "start end step";
                            description "Enter the group-range list instance";

                            leaf start {
                                type types-sros:ipv4-multicast-address;
                                description "IP address for the start of the static group range";
                            }

                            leaf end {
                                type types-sros:ipv4-multicast-address;
                                description "IP address for the end of the static group range";
                            }

                            leaf step {
                                type types-sros:ipv4-address;
                                description "Step interval in the group-range address";
                            }

                            leaf-list apply-groups {
                                type leafref {
                                    path "../../../../../../../groups/group/name";
                                }
                                max-elements 8;
                                ordered-by user;
                                description "Apply a configuration group at this level";
                            }

                            leaf-list apply-groups-exclude {
                                type leafref {
                                    path "../../../../../../../groups/group/name";
                                }
                                max-elements 8;
                                ordered-by user;
                                description "Exclude a configuration group at this level";
                            }

                            choice source-or-starg {
                                mandatory true;
                                case source {

                                    list source {
                                        key "source-address";
                                        description "Add a list entry for source";

                                        leaf source-address {
                                            type types-sros:ipv4-unicast-address;
                                            description "Source IP address of multicast channel sending data";
                                        }

                                    } // list source

                                }
                                case starg {

                                    leaf starg {
                                        type empty;
                                        description "any source address (*,G)";
                                    }

                                }
                            }
                        } // list group-range

                    } // container static

                } // list interface

                list group-interface {
                    key "group-interface-name";
                    description "Enter the group-interface list instance";

                    leaf group-interface-name {
                        type leafref {
                            path "../../../subscriber-interface/group-interface/group-interface-name";
                        }
                        description "Group interface name";
                    }

                    leaf router-alert-check {
                        type boolean;
                        default "true";
                        description "Enable router alert checking for IGMP or MLD messages";
                    }

                    leaf maximum-number-groups {
                        type uint32 {
                            range "1..16000";
                        }
                        description "Maximum number of groups for this interface";
                    }

                    leaf maximum-number-group-sources {
                        type uint32 {
                            range "1..32000";
                        }
                        description "Maximum number of group sources for this interface";
                    }

                    leaf maximum-number-sources {
                        type uint32 {
                            range "1..1000";
                        }
                        description "Maximum number of sources that are allowed per group";
                    }

                    leaf query-interval {
                        type uint32 {
                            range "2..1024";
                        }
                        description "Time between two consecutive host-query messages";
                    }

                    leaf query-response-interval {
                        type uint32 {
                            range "1..1023";
                        }
                        description "Time to wait for a response to the host-query messages";
                    }

                    leaf query-last-member-interval {
                        type uint32 {
                            range "1..1023";
                        }
                        description "Time between group-specific query messages";
                    }

                    leaf admin-state {
                        type types-sros:admin-state;
                        default "enable";
                        description "Administrative state of IGMP";
                    }

                    leaf import-policy {
                        type leafref {
                            path "../../../../../policy-options/policy-statement/name";
                        }
                        description "Import policy that filters IGMP packets";
                    }

                    leaf subnet-check {
                        type boolean;
                        default "true";
                        description "Allow subnet checking";
                    }

                    leaf version {
                        type types-igmp:igmp-version;
                        default "3";
                        description "IGMP protocol version";
                    }

                    leaf sub-hosts-only {
                        type boolean;
                        default "true";
                        description "Allow IGMP traffic from known hosts only";
                    }

                    leaf query-source-address {
                        type types-sros:ipv4-unicast-address;
                        description "Source address for IGMP queries";
                    }

                    leaf-list apply-groups {
                        type leafref {
                            path "../../../../../groups/group/name";
                        }
                        max-elements 8;
                        ordered-by user;
                        description "Apply a configuration group at this level";
                    }

                    leaf-list apply-groups-exclude {
                        type leafref {
                            path "../../../../../groups/group/name";
                        }
                        max-elements 8;
                        ordered-by user;
                        description "Exclude a configuration group at this level";
                    }

                    container mcac {
                        description "Enter the mcac context";

                        leaf interface-policy {
                            type leafref {
                                path "../../../../../../mcac/interface-policy/policy-name";
                            }
                            description "Name of multicast CAC interface policy";
                        }

                        leaf policy {
                            type leafref {
                                path "../../../../../../mcac/policy/policy-name";
                            }
                            description "Multicast CAC policy name";
                        }

                        container bandwidth {
                            description "Enter the bandwidth context";

                            leaf total {
                                type types-mcast-cac:bandwidth-limit;
                                description "Maximum allowed bandwidth";
                            }

                            leaf mandatory {
                                type types-mcast-cac:bandwidth-limit;
                                description "Pre-reserved bandwidth for all mandatory channels";
                            }

                        } // container bandwidth

                    } // container mcac

                } // list group-interface

                list forwarding-group-interface {
                    key "forwarding-service group-interface-name";
                    description "Enter the forwarding-group-interface list instance";

                    leaf forwarding-service {
                        type types-services:service-name;
                        description "Forwarding service for a subscriber interface in a retailer context";
                    }

                    leaf group-interface-name {
                        type leafref {
                            path "../../../../vprn[service-name=current()/../forwarding-service]/subscriber-interface/group-interface/group-interface-name";
                        }
                        description "Group interface name";
                    }

                    leaf router-alert-check {
                        type boolean;
                        default "true";
                        description "Enable router alert checking for IGMP or MLD messages";
                    }

                    leaf maximum-number-groups {
                        type uint32 {
                            range "1..16000";
                        }
                        description "Maximum number of groups for this interface";
                    }

                    leaf maximum-number-group-sources {
                        type uint32 {
                            range "1..32000";
                        }
                        description "Maximum number of group sources for this interface";
                    }

                    leaf maximum-number-sources {
                        type uint32 {
                            range "1..1000";
                        }
                        description "Maximum number of sources that are allowed per group";
                    }

                    leaf query-interval {
                        type uint32 {
                            range "2..1024";
                        }
                        description "Time between two consecutive host-query messages";
                    }

                    leaf query-response-interval {
                        type uint32 {
                            range "1..1023";
                        }
                        description "Time to wait for a response to the host-query messages";
                    }

                    leaf query-last-member-interval {
                        type uint32 {
                            range "1..1023";
                        }
                        description "Time between group-specific query messages";
                    }

                    leaf admin-state {
                        type types-sros:admin-state;
                        default "enable";
                        description "Administrative state of IGMP";
                    }

                    leaf import-policy {
                        type leafref {
                            path "../../../../../policy-options/policy-statement/name";
                        }
                        description "Import policy that filters IGMP packets";
                    }

                    leaf subnet-check {
                        type boolean;
                        default "true";
                        description "Allow subnet checking";
                    }

                    leaf version {
                        type types-igmp:igmp-version;
                        default "3";
                        description "IGMP protocol version";
                    }

                    leaf sub-hosts-only {
                        type boolean;
                        default "true";
                        description "Allow IGMP traffic from known hosts only";
                    }

                    leaf query-source-address {
                        type types-sros:ipv4-unicast-address;
                        description "Source address for IGMP queries";
                    }

                    leaf-list apply-groups {
                        type leafref {
                            path "../../../../../groups/group/name";
                        }
                        max-elements 8;
                        ordered-by user;
                        description "Apply a configuration group at this level";
                    }

                    leaf-list apply-groups-exclude {
                        type leafref {
                            path "../../../../../groups/group/name";
                        }
                        max-elements 8;
                        ordered-by user;
                        description "Exclude a configuration group at this level";
                    }

                    container mcac {
                        description "Enter the mcac context";

                        leaf interface-policy {
                            type leafref {
                                path "../../../../../../mcac/interface-policy/policy-name";
                            }
                            description "Name of multicast CAC interface policy";
                        }

                        leaf policy {
                            type leafref {
                                path "../../../../../../mcac/policy/policy-name";
                            }
                            description "Multicast CAC policy name";
                        }

                        container bandwidth {
                            description "Enter the bandwidth context";

                            leaf total {
                                type types-mcast-cac:bandwidth-limit;
                                description "Maximum allowed bandwidth";
                            }

                            leaf mandatory {
                                type types-mcast-cac:bandwidth-limit;
                                description "Pre-reserved bandwidth for all mandatory channels";
                            }

                        } // container bandwidth

                    } // container mcac

                } // list forwarding-group-interface

            } // container igmp

            container ipsec {
                description "Enter the ipsec context";

                leaf allow-reverse-route-override {
                    status obsolete;
                    type boolean;
                    default "false";
                    description "Create new dynamic tunnel with reverse route";
                }

                leaf allow-reverse-route-override-type {
                    type enumeration {
                        enum same-idi                       { value 1; }
                        enum any-idi                        { value 2; }
                    }
                    description "System behavior for new reverse route";
                }

                list security-policy {
                    key "id";
                    description "Enter the security-policy list instance";

                    leaf id {
                        type uint32 {
                            range "1..32768";
                        }
                        description "IPsec security policy ID";
                    }

                    leaf-list apply-groups {
                        type leafref {
                            path "../../../../../groups/group/name";
                        }
                        max-elements 8;
                        ordered-by user;
                        description "Apply a configuration group at this level";
                    }

                    leaf-list apply-groups-exclude {
                        type leafref {
                            path "../../../../../groups/group/name";
                        }
                        max-elements 8;
                        ordered-by user;
                        description "Exclude a configuration group at this level";
                    }

                    list entry {
                        key "entry-id";
                        description "Enter the entry list instance";

                        leaf entry-id {
                            type uint32 {
                                range "1..16";
                            }
                            description "IPsec security policy entry ID";
                        }

                        leaf-list apply-groups {
                            type leafref {
                                path "../../../../../../groups/group/name";
                            }
                            max-elements 8;
                            ordered-by user;
                            description "Apply a configuration group at this level";
                        }

                        leaf-list apply-groups-exclude {
                            type leafref {
                                path "../../../../../../groups/group/name";
                            }
                            max-elements 8;
                            ordered-by user;
                            description "Exclude a configuration group at this level";
                        }

                        container local-ip {
                            description "Enter the local-ip context";

                            choice any-or-ip {
                                default "any";
                                case any {

                                    leaf any {
                                        type boolean;
                                        default "false";
                                        description "Use any IP address";
                                    }

                                }
                                case ip {

                                    leaf address {
                                        type types-sros:ipv4-prefix;
                                        description "Destination IPv4 address of the aggregate route";
                                    }

                                }
                            }
                        } // container local-ip

                        container local-ipv6 {
                            description "Enter the local-ipv6 context";

                            choice any-or-ip {
                                default "any";
                                case any {

                                    leaf any {
                                        type boolean;
                                        default "false";
                                        description "Use any IP address";
                                    }

                                }
                                case ip {

                                    leaf address {
                                        type types-sros:ipv6-prefix;
                                        description "Destination IPv6 address of the aggregate route";
                                    }

                                }
                            }
                        } // container local-ipv6

                        container remote-ip {
                            description "Enter the remote-ip context";

                            choice any-or-ip {
                                default "any";
                                case any {

                                    leaf any {
                                        type boolean;
                                        default "false";
                                        description "Use any IP address";
                                    }

                                }
                                case ip {

                                    leaf address {
                                        type types-sros:ipv4-prefix;
                                        description "Destination IPv4 address of the aggregate route";
                                    }

                                }
                            }
                        } // container remote-ip

                        container remote-ipv6 {
                            description "Enter the remote-ipv6 context";

                            choice any-or-ip {
                                default "any";
                                case any {

                                    leaf any {
                                        type boolean;
                                        default "false";
                                        description "Use any IP address";
                                    }

                                }
                                case ip {

                                    leaf address {
                                        type types-sros:ipv6-prefix;
                                        description "Destination IPv6 address of the aggregate route";
                                    }

                                }
                            }
                        } // container remote-ipv6

                    } // list entry

                } // list security-policy

                list multi-chassis-shunt-interface {
                    key "name";
                    description "Enter the multi-chassis-shunt-interface list instance";

                    leaf name {
                        type leafref {
                            path "../../../../vprn/interface/interface-name";
                        }
                        description "Multi-chassis shunt interface name";
                    }

                    leaf-list apply-groups {
                        type leafref {
                            path "../../../../../groups/group/name";
                        }
                        max-elements 8;
                        ordered-by user;
                        description "Apply a configuration group at this level";
                    }

                    leaf-list apply-groups-exclude {
                        type leafref {
                            path "../../../../../groups/group/name";
                        }
                        max-elements 8;
                        ordered-by user;
                        description "Exclude a configuration group at this level";
                    }

                    container next-hop {
                        description "Enter the next-hop context";

                        leaf address {
                            type types-sros:ip-unicast-address;
                            description "Next hop address for the shunting interface";
                        }

                    } // container next-hop

                } // list multi-chassis-shunt-interface

                list multi-chassis-shunting-profile {
                    key "name";
                    max-elements 64;
                    description "Enter the multi-chassis-shunting-profile list instance";

                    leaf name {
                        type types-sros:named-item;
                        description "Multi-chassis shunting profile name";
                    }

                    leaf-list apply-groups {
                        type leafref {
                            path "../../../../../groups/group/name";
                        }
                        max-elements 8;
                        ordered-by user;
                        description "Apply a configuration group at this level";
                    }

                    leaf-list apply-groups-exclude {
                        type leafref {
                            path "../../../../../groups/group/name";
                        }
                        max-elements 8;
                        ordered-by user;
                        description "Exclude a configuration group at this level";
                    }

                    list peer {
                        key "ip-address";
                        max-elements 3;
                        description "Enter the peer list instance";

                        leaf ip-address {
                            type leafref {
                                path "../../../../../../redundancy/multi-chassis/peer/ip-address";
                            }
                            description "Peer address";
                        }

                        leaf multi-chassis-shunt-interface {
                            type leafref {
                                path "../../../../../vprn/ipsec/multi-chassis-shunt-interface/name";
                            }
                            description "Multi-chassis shunt interface";
                        }

                        leaf-list apply-groups {
                            type leafref {
                                path "../../../../../../groups/group/name";
                            }
                            max-elements 8;
                            ordered-by user;
                            description "Apply a configuration group at this level";
                        }

                        leaf-list apply-groups-exclude {
                            type leafref {
                                path "../../../../../../groups/group/name";
                            }
                            max-elements 8;
                            ordered-by user;
                            description "Exclude a configuration group at this level";
                        }

                    } // list peer

                } // list multi-chassis-shunting-profile

            } // container ipsec

            container mld {
                presence "Enable the mld context";
                description "Enable the mld context";

                leaf group-if-query-source-address {
                    type types-sros:ipv6-unicast-or-linklocal-address;
                    description "Source address in queries for group interfaces when not configured at group interface level";
                }

                leaf query-interval {
                    type uint32 {
                        range "2..1024";
                    }
                    units "seconds";
                    default "125";
                    description "Time between two consecutive host-query messages";
                }

                leaf query-last-member-interval {
                    type uint32 {
                        range "1..1023";
                    }
                    units "seconds";
                    default "1";
                    description "Time between group-specific query messages";
                }

                leaf query-response-interval {
                    type uint32 {
                        range "1..1023";
                    }
                    units "seconds";
                    default "10";
                    description "Time to wait for a response to the host-query messages";
                }

                leaf robust-count {
                    type uint32 {
                        range "2..10";
                    }
                    default "2";
                    description "Number of retries after expected message loss";
                }

                leaf admin-state {
                    type types-sros:admin-state;
                    default "enable";
                    description "Administrative state of MLD";
                }

                leaf-list apply-groups {
                    type leafref {
                        path "../../../../groups/group/name";
                    }
                    max-elements 8;
                    ordered-by user;
                    description "Apply a configuration group at this level";
                }

                leaf-list apply-groups-exclude {
                    type leafref {
                        path "../../../../groups/group/name";
                    }
                    max-elements 8;
                    ordered-by user;
                    description "Exclude a configuration group at this level";
                }

                container ssm-translate {
                    description "Enter the ssm-translate context";

                    list group-range {
                        key "start end";
                        description "Enter the group-range list instance";

                        leaf start {
                            type types-sros:ipv6-multicast-address;
                            description "Lower bound of the group range";
                        }

                        leaf end {
                            type types-sros:ipv6-multicast-address;
                            description "Upper bound of the group range";
                        }

                        leaf-list apply-groups {
                            type leafref {
                                path "../../../../../../groups/group/name";
                            }
                            max-elements 8;
                            ordered-by user;
                            description "Apply a configuration group at this level";
                        }

                        leaf-list apply-groups-exclude {
                            type leafref {
                                path "../../../../../../groups/group/name";
                            }
                            max-elements 8;
                            ordered-by user;
                            description "Exclude a configuration group at this level";
                        }

                        list source {
                            key "source-address";
                            min-elements 1;
                            description "Add a list entry for source";

                            leaf source-address {
                                type types-sros:ipv6-unicast-address;
                                description "Source IP address";
                            }

                        } // list source

                    } // list group-range

                } // container ssm-translate

                list interface {
                    key "ip-interface-name";
                    description "Enter the interface list instance";

                    leaf ip-interface-name {
                        type types-sros:interface-name;
                        description "IP interface name";
                    }

                    leaf router-alert-check {
                        type boolean;
                        default "true";
                        description "Enable router alert checking for IGMP or MLD messages";
                    }

                    leaf maximum-number-groups {
                        type uint32 {
                            range "1..16000";
                        }
                        description "Maximum number of groups for this interface";
                    }

                    leaf maximum-number-group-sources {
                        type uint32 {
                            range "1..32000";
                        }
                        description "Maximum number of group sources for this interface";
                    }

                    leaf maximum-number-sources {
                        type uint32 {
                            range "1..1000";
                        }
                        description "Maximum number of sources that are allowed per group";
                    }

                    leaf query-interval {
                        type uint32 {
                            range "2..1024";
                        }
                        description "Time between two consecutive host-query messages";
                    }

                    leaf query-response-interval {
                        type uint32 {
                            range "1..1023";
                        }
                        description "Time to wait for a response to the host-query messages";
                    }

                    leaf query-last-member-interval {
                        type uint32 {
                            range "1..1023";
                        }
                        description "Time between group-specific query messages";
                    }

                    leaf import-policy {
                        type leafref {
                            path "../../../../../policy-options/policy-statement/name";
                        }
                        description "Import policy to filter MLD packets";
                    }

                    leaf admin-state {
                        type types-sros:admin-state;
                        default "enable";
                        description "Administrative state of the MLD interface";
                    }

                    leaf version {
                        type types-igmp:mld-version;
                        default "2";
                        description "MLD protocol version";
                    }

                    leaf-list apply-groups {
                        type leafref {
                            path "../../../../../groups/group/name";
                        }
                        max-elements 8;
                        ordered-by user;
                        description "Apply a configuration group at this level";
                    }

                    leaf-list apply-groups-exclude {
                        type leafref {
                            path "../../../../../groups/group/name";
                        }
                        max-elements 8;
                        ordered-by user;
                        description "Exclude a configuration group at this level";
                    }

                    container mcac {
                        description "Enter the mcac context";

                        leaf interface-policy {
                            type leafref {
                                path "../../../../../../mcac/interface-policy/policy-name";
                            }
                            description "Name of multicast CAC interface policy";
                        }

                        leaf policy {
                            type leafref {
                                path "../../../../../../mcac/policy/policy-name";
                            }
                            description "Multicast CAC policy name";
                        }

                        container mc-constraints {
                            description "Enter the mc-constraints context";

                            leaf use-lag-port-weight {
                                type boolean;
                                default "false";
                                description "Use LAG port weight in calculating MCAC constraints";
                            }

                            list level {
                                key "level-id";
                                description "Enter the level list instance";

                                leaf level-id {
                                    type types-mcast-cac:constraints-level;
                                    description "Bandwidth level ID for an MCAC constraint";
                                }

                                leaf bandwidth {
                                    type types-mcast-cac:bandwidth {
                                        range "0..2147483647";
                                    }
                                    mandatory true;
                                    description "Bandwidth available for this level";
                                }

                                leaf-list apply-groups {
                                    type leafref {
                                        path "../../../../../../../../groups/group/name";
                                    }
                                    max-elements 8;
                                    ordered-by user;
                                    description "Apply a configuration group at this level";
                                }

                                leaf-list apply-groups-exclude {
                                    type leafref {
                                        path "../../../../../../../../groups/group/name";
                                    }
                                    max-elements 8;
                                    ordered-by user;
                                    description "Exclude a configuration group at this level";
                                }

                            } // list level

                            list number-down {
                                key "number-lag-port-down";
                                description "Enter the number-down list instance";

                                leaf number-lag-port-down {
                                    type uint32 {
                                        range "1..64";
                                    }
                                    description "Number of ports that are down in this LAG link";
                                }

                                leaf level {
                                    type types-mcast-cac:constraints-level;
                                    mandatory true;
                                    description "Level ID to associate with number of down LAG ports";
                                }

                                leaf-list apply-groups {
                                    type leafref {
                                        path "../../../../../../../../groups/group/name";
                                    }
                                    max-elements 8;
                                    ordered-by user;
                                    description "Apply a configuration group at this level";
                                }

                                leaf-list apply-groups-exclude {
                                    type leafref {
                                        path "../../../../../../../../groups/group/name";
                                    }
                                    max-elements 8;
                                    ordered-by user;
                                    description "Exclude a configuration group at this level";
                                }

                            } // list number-down

                        } // container mc-constraints

                        container bandwidth {
                            description "Enter the bandwidth context";

                            leaf total {
                                type types-mcast-cac:bandwidth-limit;
                                description "Maximum allowed bandwidth";
                            }

                            leaf mandatory {
                                type types-mcast-cac:bandwidth-limit;
                                description "Pre-reserved bandwidth for all mandatory channels";
                            }

                        } // container bandwidth

                    } // container mcac

                    container ssm-translate {
                        description "Enter the ssm-translate context";

                        list group-range {
                            key "start end";
                            description "Enter the group-range list instance";

                            leaf start {
                                type types-sros:ipv6-multicast-address;
                                description "Lower bound of the group range";
                            }

                            leaf end {
                                type types-sros:ipv6-multicast-address;
                                description "Upper bound of the group range";
                            }

                            leaf-list apply-groups {
                                type leafref {
                                    path "../../../../../../../groups/group/name";
                                }
                                max-elements 8;
                                ordered-by user;
                                description "Apply a configuration group at this level";
                            }

                            leaf-list apply-groups-exclude {
                                type leafref {
                                    path "../../../../../../../groups/group/name";
                                }
                                max-elements 8;
                                ordered-by user;
                                description "Exclude a configuration group at this level";
                            }

                            list source {
                                key "source-address";
                                min-elements 1;
                                description "Add a list entry for source";

                                leaf source-address {
                                    type types-sros:ipv6-unicast-address;
                                    description "Source IP address";
                                }

                            } // list source

                        } // list group-range

                    } // container ssm-translate

                    container static {
                        description "Enter the static context";

                        list group {
                            key "group-address";
                            description "Enter the group list instance";

                            leaf group-address {
                                type types-sros:ipv6-multicast-address;
                                description "Group address of multicast channel";
                            }

                            leaf-list apply-groups {
                                type leafref {
                                    path "../../../../../../../groups/group/name";
                                }
                                max-elements 8;
                                ordered-by user;
                                description "Apply a configuration group at this level";
                            }

                            leaf-list apply-groups-exclude {
                                type leafref {
                                    path "../../../../../../../groups/group/name";
                                }
                                max-elements 8;
                                ordered-by user;
                                description "Exclude a configuration group at this level";
                            }

                            choice source-or-starg {
                                mandatory true;
                                case source {

                                    list source {
                                        key "source-address";
                                        description "Add a list entry for source";

                                        leaf source-address {
                                            type types-sros:ipv6-unicast-address;
                                            description "Source IP address";
                                        }

                                    } // list source

                                }
                                case starg {

                                    leaf starg {
                                        type empty;
                                        description "any source address (*,G)";
                                    }

                                }
                            }
                        } // list group

                        list group-range {
                            key "start end step";
                            description "Enter the group-range list instance";

                            leaf start {
                                type types-sros:ipv6-multicast-address;
                                description "Lower bound of the static multicast group";
                            }

                            leaf end {
                                type types-sros:ipv6-multicast-address;
                                description "Upper bound of the static multicast group";
                            }

                            leaf step {
                                type types-sros:ipv6-address;
                                description "Step interval for the group-range addresses";
                            }

                            leaf-list apply-groups {
                                type leafref {
                                    path "../../../../../../../groups/group/name";
                                }
                                max-elements 8;
                                ordered-by user;
                                description "Apply a configuration group at this level";
                            }

                            leaf-list apply-groups-exclude {
                                type leafref {
                                    path "../../../../../../../groups/group/name";
                                }
                                max-elements 8;
                                ordered-by user;
                                description "Exclude a configuration group at this level";
                            }

                            choice source-or-starg {
                                mandatory true;
                                case source {

                                    list source {
                                        key "source-address";
                                        description "Add a list entry for source";

                                        leaf source-address {
                                            type types-sros:ipv6-unicast-address;
                                            description "Source IP address";
                                        }

                                    } // list source

                                }
                                case starg {

                                    leaf starg {
                                        type empty;
                                        description "any source address (*,G)";
                                    }

                                }
                            }
                        } // list group-range

                    } // container static

                } // list interface

                list group-interface {
                    key "group-interface-name";
                    description "Enter the group-interface list instance";

                    leaf group-interface-name {
                        type leafref {
                            path "../../../subscriber-interface/group-interface/group-interface-name";
                        }
                        description "Group interface name";
                    }

                    leaf router-alert-check {
                        type boolean;
                        default "true";
                        description "Enable router alert checking for IGMP or MLD messages";
                    }

                    leaf maximum-number-groups {
                        type uint32 {
                            range "1..16000";
                        }
                        description "Maximum number of groups for this interface";
                    }

                    leaf maximum-number-group-sources {
                        type uint32 {
                            range "1..32000";
                        }
                        description "Maximum number of group sources for this interface";
                    }

                    leaf maximum-number-sources {
                        type uint32 {
                            range "1..1000";
                        }
                        description "Maximum number of sources that are allowed per group";
                    }

                    leaf query-interval {
                        type uint32 {
                            range "2..1024";
                        }
                        description "Time between two consecutive host-query messages";
                    }

                    leaf query-response-interval {
                        type uint32 {
                            range "1..1023";
                        }
                        description "Time to wait for a response to the host-query messages";
                    }

                    leaf query-last-member-interval {
                        type uint32 {
                            range "1..1023";
                        }
                        description "Time between group-specific query messages";
                    }

                    leaf import-policy {
                        type leafref {
                            path "../../../../../policy-options/policy-statement/name";
                        }
                        description "Import policy to filter MLD packets";
                    }

                    leaf admin-state {
                        type types-sros:admin-state;
                        default "enable";
                        description "Administrative state of the MLD interface";
                    }

                    leaf version {
                        type types-igmp:mld-version;
                        default "2";
                        description "MLD protocol version";
                    }

                    leaf subnet-check {
                        type boolean;
                        default "true";
                        description "Enable subnet checking";
                    }

                    leaf sub-hosts-only {
                        type boolean;
                        default "true";
                        description "Allow MLD traffic from known hosts only";
                    }

                    leaf query-source-address {
                        type types-sros:ipv6-unicast-or-linklocal-address;
                        description "Source address for MLD queries";
                    }

                    leaf-list apply-groups {
                        type leafref {
                            path "../../../../../groups/group/name";
                        }
                        max-elements 8;
                        ordered-by user;
                        description "Apply a configuration group at this level";
                    }

                    leaf-list apply-groups-exclude {
                        type leafref {
                            path "../../../../../groups/group/name";
                        }
                        max-elements 8;
                        ordered-by user;
                        description "Exclude a configuration group at this level";
                    }

                    container mcac {
                        description "Enter the mcac context";

                        leaf interface-policy {
                            type leafref {
                                path "../../../../../../mcac/interface-policy/policy-name";
                            }
                            description "Name of multicast CAC interface policy";
                        }

                        leaf policy {
                            type leafref {
                                path "../../../../../../mcac/policy/policy-name";
                            }
                            description "Multicast CAC policy name";
                        }

                        container bandwidth {
                            description "Enter the bandwidth context";

                            leaf total {
                                type types-mcast-cac:bandwidth-limit;
                                description "Maximum allowed bandwidth";
                            }

                            leaf mandatory {
                                type types-mcast-cac:bandwidth-limit;
                                description "Pre-reserved bandwidth for all mandatory channels";
                            }

                        } // container bandwidth

                    } // container mcac

                } // list group-interface

                list forwarding-group-interface {
                    key "forwarding-service group-interface-name";
                    description "Enter the forwarding-group-interface list instance";

                    leaf forwarding-service {
                        type types-services:service-name;
                        description "Forwarding service for a subscriber interface in a retailer context";
                    }

                    leaf group-interface-name {
                        type leafref {
                            path "../../../../vprn[service-name=current()/../forwarding-service]/subscriber-interface/group-interface/group-interface-name";
                        }
                        description "Group interface name";
                    }

                    leaf router-alert-check {
                        type boolean;
                        default "true";
                        description "Enable router alert checking for IGMP or MLD messages";
                    }

                    leaf maximum-number-groups {
                        type uint32 {
                            range "1..16000";
                        }
                        description "Maximum number of groups for this interface";
                    }

                    leaf maximum-number-group-sources {
                        type uint32 {
                            range "1..32000";
                        }
                        description "Maximum number of group sources for this interface";
                    }

                    leaf maximum-number-sources {
                        type uint32 {
                            range "1..1000";
                        }
                        description "Maximum number of sources that are allowed per group";
                    }

                    leaf query-interval {
                        type uint32 {
                            range "2..1024";
                        }
                        description "Time between two consecutive host-query messages";
                    }

                    leaf query-response-interval {
                        type uint32 {
                            range "1..1023";
                        }
                        description "Time to wait for a response to the host-query messages";
                    }

                    leaf query-last-member-interval {
                        type uint32 {
                            range "1..1023";
                        }
                        description "Time between group-specific query messages";
                    }

                    leaf import-policy {
                        type leafref {
                            path "../../../../../policy-options/policy-statement/name";
                        }
                        description "Import policy to filter MLD packets";
                    }

                    leaf admin-state {
                        type types-sros:admin-state;
                        default "enable";
                        description "Administrative state of the MLD interface";
                    }

                    leaf version {
                        type types-igmp:mld-version;
                        default "2";
                        description "MLD protocol version";
                    }

                    leaf subnet-check {
                        type boolean;
                        default "true";
                        description "Enable subnet checking";
                    }

                    leaf sub-hosts-only {
                        type boolean;
                        default "true";
                        description "Allow MLD traffic from known hosts only";
                    }

                    leaf query-source-address {
                        type types-sros:ipv6-unicast-or-linklocal-address;
                        description "Source address for MLD queries";
                    }

                    leaf-list apply-groups {
                        type leafref {
                            path "../../../../../groups/group/name";
                        }
                        max-elements 8;
                        ordered-by user;
                        description "Apply a configuration group at this level";
                    }

                    leaf-list apply-groups-exclude {
                        type leafref {
                            path "../../../../../groups/group/name";
                        }
                        max-elements 8;
                        ordered-by user;
                        description "Exclude a configuration group at this level";
                    }

                    container mcac {
                        description "Enter the mcac context";

                        leaf interface-policy {
                            type leafref {
                                path "../../../../../../mcac/interface-policy/policy-name";
                            }
                            description "Name of multicast CAC interface policy";
                        }

                        leaf policy {
                            type leafref {
                                path "../../../../../../mcac/policy/policy-name";
                            }
                            description "Multicast CAC policy name";
                        }

                        container bandwidth {
                            description "Enter the bandwidth context";

                            leaf total {
                                type types-mcast-cac:bandwidth-limit;
                                description "Maximum allowed bandwidth";
                            }

                            leaf mandatory {
                                type types-mcast-cac:bandwidth-limit;
                                description "Pre-reserved bandwidth for all mandatory channels";
                            }

                        } // container bandwidth

                    } // container mcac

                } // list forwarding-group-interface

            } // container mld

            container pim {
                presence "Enable the pim context";
                description "Enable the pim context";

                leaf admin-state {
                    type types-sros:admin-state;
                    default "enable";
                    description "Administrative state of PIM";
                }

                leaf apply-to {
                    type enumeration {
                        enum all                            { value 3; }
                        enum none                           { value 4; }
                    }
                    default "none";
                    description "IES and non-IES interfaces to create in PIM";
                }

                leaf mc-ecmp-balance {
                    type boolean;
                    default "true";
                    description "Enable multicast balancing of traffic over ECMP links";
                }

                leaf mc-ecmp-balance-hold {
                    type uint32 {
                        range "2..600";
                    }
                    units "minutes";
                    description "Hold time for multicast balancing over ECMP links";
                }

                leaf non-dr-attract-traffic {
                    type boolean;
                    default "false";
                    description "Attract traffic when the router is not the designated one";
                }

                leaf bgp-nh-override {
                    type boolean;
                    default "false";
                    description "Disable VRF import EC support for next-hop resolution";
                }

                leaf mtu-over-head {
                    type int32 {
                        range "0|44|76|140|268|536";
                    }
                    default "0";
                    description "MVPN tunnel MTU size reduction to allow for BIER header";
                }

                leaf-list apply-groups {
                    type leafref {
                        path "../../../../groups/group/name";
                    }
                    max-elements 8;
                    ordered-by user;
                    description "Apply a configuration group at this level";
                }

                leaf-list apply-groups-exclude {
                    type leafref {
                        path "../../../../groups/group/name";
                    }
                    max-elements 8;
                    ordered-by user;
                    description "Exclude a configuration group at this level";
                }

                container ipv4 {
                    description "Enter the ipv4 context";

                    leaf ssm-assert-compatible-mode {
                        type boolean;
                        default "false";
                        description "Enable SSM assert compatible mode";
                    }

                    leaf admin-state {
                        type types-sros:admin-state;
                        default "enable";
                        description "Administrative state of PIM operation for IPv4";
                    }

                    leaf rpf-table {
                        type enumeration {
                            enum rtable-m                       { value 0; }
                            enum rtable-u                       { value 1; }
                            enum both                           { value 2; }
                        }
                        default "rtable-u";
                        description "Route table for RPF lookup";
                    }

                    leaf ssm-default-range {
                        type boolean;
                        default "true";
                        description "SSM default range";
                    }

                    container source-address {
                        description "Enter the source-address context";

                        leaf register-message {
                            type types-sros:ipv4-unicast-address;
                            description "Source IPv4 address for PIM register messages";
                        }

                    } // container source-address

                    container grt-extranet {
                        description "Enter the grt-extranet context";

                        choice prefix {
                            case any {

                                leaf any {
                                    type empty;
                                    description "GRT or VRF extranet for the instance";
                                }

                            }
                            case group-prefix {

                                list group-prefix {
                                    key "ip-prefix";
                                    description "Enter the group-prefix list instance";

                                    leaf ip-prefix {
                                        type types-sros:ip-multicast-prefix;
                                        description "IP address and mask length";
                                    }

                                    leaf starg {
                                        type boolean;
                                        default "false";
                                        description "Add a static (*,G) entry";
                                    }

                                    leaf-list apply-groups {
                                        type leafref {
                                            path "../../../../../../../groups/group/name";
                                        }
                                        max-elements 8;
                                        ordered-by user;
                                        description "Apply a configuration group at this level";
                                    }

                                    leaf-list apply-groups-exclude {
                                        type leafref {
                                            path "../../../../../../../groups/group/name";
                                        }
                                        max-elements 8;
                                        ordered-by user;
                                        description "Exclude a configuration group at this level";
                                    }

                                } // list group-prefix

                            }
                        }
                    } // container grt-extranet

                } // container ipv4

                container ipv6 {
                    description "Enter the ipv6 context";

                    leaf admin-state {
                        type types-sros:admin-state;
                        default "disable";
                        description "Administrative state of PIM operation for IPv6";
                    }

                    leaf rpf-table {
                        type enumeration {
                            enum rtable-m                       { value 0; }
                            enum rtable-u                       { value 1; }
                            enum both                           { value 2; }
                        }
                        default "rtable-u";
                        description "Route table for RPF lookup";
                    }

                    leaf ssm-default-range {
                        type boolean;
                        default "true";
                        description "SSM default range";
                    }

                    container source-address {
                        description "Enter the source-address context";

                        leaf register-message {
                            type types-sros:ipv6-unicast-address;
                            description "Source IPv6 address for PIM register messages";
                        }

                    } // container source-address

                } // container ipv6

                container mc-ecmp-hashing {
                    presence "Enable the mc-ecmp-hashing context";
                    description "Enable the mc-ecmp-hashing context";

                    leaf rebalance {
                        type boolean;
                        default "false";
                        description "Rebalance flows to newly added links immediately instead of waiting until they are pruned";
                    }

                } // container mc-ecmp-hashing

                container import {
                    description "Enter the import context";

                    leaf-list join-policy {
                        type leafref {
                            path "../../../../../policy-options/policy-statement/name";
                        }
                        max-elements 5;
                        ordered-by user;
                        description "Policy name";
                    }

                    leaf-list register-policy {
                        type leafref {
                            path "../../../../../policy-options/policy-statement/name";
                        }
                        max-elements 5;
                        ordered-by user;
                        description "Policy name";
                    }

                } // container import

                list interface {
                    key "interface-name";
                    description "Enter the interface list instance";

                    leaf interface-name {
                        type types-sros:interface-name;
                        description "Interface name";
                    }

                    leaf admin-state {
                        type types-sros:admin-state;
                        default "enable";
                        description "Administrative state of the PIM interface";
                    }

                    leaf assert-period {
                        type int32 {
                            range "1..300";
                        }
                        default "60";
                        description "Time for periodic refreshes of PIM Assert messages on an interface";
                    }

                    leaf hello-interval {
                        type int32 {
                            range "0..255";
                        }
                        default "30";
                        description "Frequency at which PIM Hello messages are sent over this interface";
                    }

                    leaf hello-multiplier {
                        type uint32 {
                            range "20..100";
                        }
                        default "35";
                        description "Multiplier to determine the hold time for PIM neighbor";
                    }

                    leaf instant-prune-echo {
                        type boolean;
                        default "false";
                        description "Allow PIM to send an instant prune echo when router starts the prune pending timer for PIM interface";
                    }

                    leaf max-groups {
                        type uint32 {
                            range "0|1..16000";
                        }
                        default "0";
                        description "Maximum number of groups for the interface";
                    }

                    leaf priority {
                        type uint32 {
                            range "1..max";
                        }
                        default "1";
                        description "DR election priority for this interface";
                    }

                    leaf three-way-hello {
                        type boolean;
                        default "false";
                        description "Allow three-way hello compatibility mode";
                    }

                    leaf tracking-support {
                        type boolean;
                        default "false";
                        description "Allow upstream routers to explicitly track join membership";
                    }

                    leaf bsm-check-rtr-alert {
                        type boolean;
                        default "false";
                        description "Check router alert option in bootstrap messages received";
                    }

                    leaf improved-assert {
                        type boolean;
                        default "true";
                        description "Allow improved assert processing on interface";
                    }

                    leaf multicast-senders {
                        type enumeration {
                            enum auto                           { value 0; }
                            enum always                         { value 1; }
                            enum never                          { value 2; }
                        }
                        default "auto";
                        description "Subnet matching for the incoming data packets";
                    }

                    leaf-list apply-groups {
                        type leafref {
                            path "../../../../../groups/group/name";
                        }
                        max-elements 8;
                        ordered-by user;
                        description "Apply a configuration group at this level";
                    }

                    leaf-list apply-groups-exclude {
                        type leafref {
                            path "../../../../../groups/group/name";
                        }
                        max-elements 8;
                        ordered-by user;
                        description "Exclude a configuration group at this level";
                    }

                    container p2mp-ldp-tree-join {
                        description "Enter the p2mp-ldp-tree-join context";

                        leaf ipv4 {
                            type boolean;
                            default "false";
                            description "Allow dynamic mLDP in-band signaling for IPv4 PIM joins";
                        }

                        leaf ipv6 {
                            type boolean;
                            default "false";
                            description "Allow dynamic mLDP in-band signaling for IPv6 PIM joins";
                        }

                    } // container p2mp-ldp-tree-join

                    container bfd-liveness {
                        description "Enter the bfd-liveness context";

                        leaf ipv4 {
                            type boolean;
                            default "false";
                            description "Use Bidirectional Forwarding Detection for IPv4 on PIM interface";
                        }

                        leaf ipv6 {
                            type boolean;
                            default "false";
                            description "Use Bidirectional Forwarding Detection for IPv6 on PIM interface";
                        }

                    } // container bfd-liveness

                    container ipv4 {
                        description "Enter the ipv4 context";

                        leaf multicast {
                            type boolean;
                            default "true";
                            description "Enable PIM interface operation";
                        }

                        leaf-list apply-groups {
                            type leafref {
                                path "../../../../../../groups/group/name";
                            }
                            max-elements 8;
                            ordered-by user;
                            description "Apply a configuration group at this level";
                        }

                        leaf-list apply-groups-exclude {
                            type leafref {
                                path "../../../../../../groups/group/name";
                            }
                            max-elements 8;
                            ordered-by user;
                            description "Exclude a configuration group at this level";
                        }

                        container monitor-oper-group {
                            description "Enter the monitor-oper-group context";

                            leaf name {
                                type leafref {
                                    path "../../../../../../oper-group/name";
                                }
                                description "Operational group identifier";
                            }

                            leaf operation {
                                type enumeration {
                                    enum add                            { value 1; }
                                    enum subtract                       { value 2; }
                                    enum set                            { value 3; }
                                }
                                description "Operation performed when operational group is active";
                            }

                            leaf priority-delta {
                                type uint32 {
                                    range "1..4294967295";
                                }
                                description "Delta priority with operation when operational group is active";
                            }

                        } // container monitor-oper-group

                    } // container ipv4

                    container ipv6 {
                        description "Enter the ipv6 context";

                        leaf multicast {
                            type boolean;
                            default "true";
                            description "Enable PIM interface operation";
                        }

                        leaf-list apply-groups {
                            type leafref {
                                path "../../../../../../groups/group/name";
                            }
                            max-elements 8;
                            ordered-by user;
                            description "Apply a configuration group at this level";
                        }

                        leaf-list apply-groups-exclude {
                            type leafref {
                                path "../../../../../../groups/group/name";
                            }
                            max-elements 8;
                            ordered-by user;
                            description "Exclude a configuration group at this level";
                        }

                        container monitor-oper-group {
                            description "Enter the monitor-oper-group context";

                            leaf name {
                                type leafref {
                                    path "../../../../../../oper-group/name";
                                }
                                description "Operational group identifier";
                            }

                            leaf operation {
                                type enumeration {
                                    enum add                            { value 1; }
                                    enum subtract                       { value 2; }
                                    enum set                            { value 3; }
                                }
                                description "Operation performed when operational group is active";
                            }

                            leaf priority-delta {
                                type uint32 {
                                    range "1..4294967295";
                                }
                                description "Delta priority with operation when operational group is active";
                            }

                        } // container monitor-oper-group

                    } // container ipv6

                    container sticky-dr {
                        presence "Enable the sticky-dr context";
                        description "Enable the sticky-dr context";

                        leaf priority {
                            type uint32 {
                                range "1..max";
                            }
                            default "1024";
                            description "DR election priority for this interface";
                        }

                    } // container sticky-dr

                    container mcac {
                        description "Enter the mcac context";

                        leaf interface-policy {
                            type leafref {
                                path "../../../../../../mcac/interface-policy/policy-name";
                            }
                            description "Name of multicast CAC interface policy";
                        }

                        leaf policy {
                            type leafref {
                                path "../../../../../../mcac/policy/policy-name";
                            }
                            description "Multicast CAC policy name";
                        }

                        container bandwidth {
                            description "Enter the bandwidth context";

                            leaf total {
                                type types-mcast-cac:bandwidth-limit;
                                description "Maximum allowed bandwidth";
                            }

                            leaf mandatory {
                                type types-mcast-cac:bandwidth-limit;
                                description "Pre-reserved bandwidth for all mandatory channels";
                            }

                        } // container bandwidth

                        container mc-constraints {
                            description "Enter the mc-constraints context";

                            leaf use-lag-port-weight {
                                type boolean;
                                default "false";
                                description "Use LAG port weight in calculating MCAC constraints";
                            }

                            leaf admin-state {
                                type types-sros:admin-state;
                                default "enable";
                                description "Administrative state of the multicast CAC constraints";
                            }

                            list level {
                                key "level-id";
                                description "Enter the level list instance";

                                leaf level-id {
                                    type types-mcast-cac:constraints-level;
                                    description "Bandwidth level ID for an MCAC constraint";
                                }

                                leaf bandwidth {
                                    type types-mcast-cac:bandwidth {
                                        range "0..2147483647";
                                    }
                                    mandatory true;
                                    description "Bandwidth available for this level";
                                }

                                leaf-list apply-groups {
                                    type leafref {
                                        path "../../../../../../../../groups/group/name";
                                    }
                                    max-elements 8;
                                    ordered-by user;
                                    description "Apply a configuration group at this level";
                                }

                                leaf-list apply-groups-exclude {
                                    type leafref {
                                        path "../../../../../../../../groups/group/name";
                                    }
                                    max-elements 8;
                                    ordered-by user;
                                    description "Exclude a configuration group at this level";
                                }

                            } // list level

                            list number-down {
                                key "number-lag-port-down";
                                description "Enter the number-down list instance";

                                leaf number-lag-port-down {
                                    type uint32 {
                                        range "1..64";
                                    }
                                    description "Number of ports that are down in this LAG link";
                                }

                                leaf level {
                                    type types-mcast-cac:constraints-level;
                                    mandatory true;
                                    description "Level ID to associate with number of down LAG ports";
                                }

                                leaf-list apply-groups {
                                    type leafref {
                                        path "../../../../../../../../groups/group/name";
                                    }
                                    max-elements 8;
                                    ordered-by user;
                                    description "Apply a configuration group at this level";
                                }

                                leaf-list apply-groups-exclude {
                                    type leafref {
                                        path "../../../../../../../../groups/group/name";
                                    }
                                    max-elements 8;
                                    ordered-by user;
                                    description "Exclude a configuration group at this level";
                                }

                            } // list number-down

                        } // container mc-constraints

                    } // container mcac

                } // list interface

                container rp {
                    description "Enter the rp context";

                    container bootstrap {
                        description "Enter the bootstrap context";

                        leaf-list import {
                            type leafref {
                                path "../../../../../../policy-options/policy-statement/name";
                            }
                            max-elements 5;
                            ordered-by user;
                            description "Import policy to control the flow of bootstrap messages";
                        }

                        leaf-list export {
                            type leafref {
                                path "../../../../../../policy-options/policy-statement/name";
                            }
                            max-elements 5;
                            ordered-by user;
                            description "Export policy to control the flow of bootstrap messages";
                        }

                    } // container bootstrap

                    container ipv4 {
                        description "Enter the ipv4 context";

                        leaf auto-rp-discovery {
                            type boolean;
                            default "false";
                            description "Enable auto-RP discovery mode and auto-RP listener";
                        }

                        leaf candidate {
                            type boolean;
                            default "false";
                            description "Enable auto-RP to advertise candidate RP information";
                        }

                        leaf mapping-agent {
                            type boolean;
                            default "false";
                            description "Enable the mapping agent on the node";
                        }

                        list anycast {
                            key "ipv4-address rp-set-peer";
                            description "Add a list entry for anycast";

                            leaf ipv4-address {
                                type types-sros:ipv4-unicast-address;
                                description "Loopback IP address shared by routes in RP set";
                            }

                            leaf rp-set-peer {
                                type types-sros:ipv4-unicast-address;
                                description "Peer in the anycast RP-set";
                            }

                        } // list anycast

                        container bsr-candidate {
                            description "Enter the bsr-candidate context";

                            leaf admin-state {
                                type types-sros:admin-state;
                                default "disable";
                                description "Administrative state of the Candidate BSR";
                            }

                            leaf priority {
                                type int32 {
                                    range "0..255";
                                }
                                default "0";
                                description "Bootstrap priority of the router";
                            }

                            leaf address {
                                type types-sros:ipv4-unicast-address;
                                description "Candidate BSR IP address for Bootstrap Router election";
                            }

                            leaf hash-mask-len {
                                type int32 {
                                    range "0..32";
                                }
                                default "30";
                                description "Length for bootstrap hash mask";
                            }

                        } // container bsr-candidate

                        container rp-candidate {
                            description "Enter the rp-candidate context";

                            leaf admin-state {
                                type types-sros:admin-state;
                                default "disable";
                                description "Administrative state of the Candidate RP";
                            }

                            leaf holdtime {
                                type int32 {
                                    range "5..255";
                                }
                                units "seconds";
                                default "150";
                                description "Time during which the neighboring router considers this router to be up";
                            }

                            leaf priority {
                                type int32 {
                                    range "0..255";
                                }
                                default "192";
                                description "Candidate RP priority";
                            }

                            leaf address {
                                type types-sros:ipv4-unicast-address;
                                description "Local RP address";
                            }

                            list group-range {
                                key "ipv4-prefix";
                                description "Add a list entry for group-range";

                                leaf ipv4-prefix {
                                    type types-sros:ipv4-multicast-prefix;
                                    description "IPv4 address and prefix length";
                                }

                            } // list group-range

                        } // container rp-candidate

                        container static {
                            description "Enter the static context";

                            list address {
                                key "ipv4-address";
                                description "Enter the address list instance";

                                leaf ipv4-address {
                                    type types-sros:ipv4-unicast-address;
                                    description "IPv4 address for the static RP";
                                }

                                leaf override {
                                    type boolean;
                                    default "false";
                                    description "Change the precedence for static RP over dynamically learnt RP";
                                }

                                leaf-list apply-groups {
                                    type leafref {
                                        path "../../../../../../../../groups/group/name";
                                    }
                                    max-elements 8;
                                    ordered-by user;
                                    description "Apply a configuration group at this level";
                                }

                                leaf-list apply-groups-exclude {
                                    type leafref {
                                        path "../../../../../../../../groups/group/name";
                                    }
                                    max-elements 8;
                                    ordered-by user;
                                    description "Exclude a configuration group at this level";
                                }

                                list group-prefix {
                                    key "ipv4-prefix";
                                    description "Add a list entry for group-prefix";

                                    leaf ipv4-prefix {
                                        type types-sros:ipv4-multicast-prefix;
                                        description "IPv4 address and prefix length";
                                    }

                                } // list group-prefix

                            } // list address

                        } // container static

                    } // container ipv4

                    container ipv6 {
                        description "Enter the ipv6 context";

                        list anycast {
                            key "ipv6-address rp-set-peer";
                            description "Add a list entry for anycast";

                            leaf ipv6-address {
                                type types-sros:ipv6-unicast-address;
                                description "Loopback IP address shared by routes in RP set";
                            }

                            leaf rp-set-peer {
                                type types-sros:ipv6-unicast-address;
                                description "Peer in the anycast RP set";
                            }

                        } // list anycast

                        container bsr-candidate {
                            description "Enter the bsr-candidate context";

                            leaf admin-state {
                                type types-sros:admin-state;
                                default "disable";
                                description "Administrative state of the Candidate BSR";
                            }

                            leaf priority {
                                type int32 {
                                    range "0..255";
                                }
                                default "0";
                                description "Bootstrap priority of the router";
                            }

                            leaf address {
                                type types-sros:ipv6-unicast-address;
                                description "Candidate BSR IP address for Bootstrap Router election";
                            }

                            leaf hash-mask-len {
                                type int32 {
                                    range "0..128";
                                }
                                default "126";
                                description "Length for bootstrap hash mask";
                            }

                        } // container bsr-candidate

                        container embedded-rp {
                            presence "Enable the embedded-rp context";
                            description "Enable the embedded-rp context";

                            leaf admin-state {
                                type types-sros:admin-state;
                                default "disable";
                                description "Administrative state of embedded RP";
                            }

                            list group-range {
                                key "ipv6-prefix";
                                description "Add a list entry for group-range";

                                leaf ipv6-prefix {
                                    type types-sros:ipv6-multicast-prefix;
                                    description "IPv6 address and prefix length";
                                }

                            } // list group-range

                        } // container embedded-rp

                        container rp-candidate {
                            description "Enter the rp-candidate context";

                            leaf admin-state {
                                type types-sros:admin-state;
                                default "disable";
                                description "Administrative state of the Candidate RP";
                            }

                            leaf holdtime {
                                type int32 {
                                    range "5..255";
                                }
                                units "seconds";
                                default "150";
                                description "Time during which the neighboring router considers this router to be up";
                            }

                            leaf priority {
                                type int32 {
                                    range "0..255";
                                }
                                default "192";
                                description "Candidate RP priority";
                            }

                            leaf address {
                                type types-sros:ipv6-unicast-address;
                                description "Local RP address";
                            }

                            list group-range {
                                key "ipv6-prefix";
                                description "Add a list entry for group-range";

                                leaf ipv6-prefix {
                                    type types-sros:ipv6-multicast-prefix;
                                    description "IPv6 address and prefix length";
                                }

                            } // list group-range

                        } // container rp-candidate

                        container static {
                            description "Enter the static context";

                            list address {
                                key "ipv6-address";
                                description "Enter the address list instance";

                                leaf ipv6-address {
                                    type types-sros:ipv6-unicast-address;
                                    description "Static IP address of the RP";
                                }

                                leaf override {
                                    type boolean;
                                    default "false";
                                    description "Change the precedence for static RP over dynamically learnt RP";
                                }

                                leaf-list apply-groups {
                                    type leafref {
                                        path "../../../../../../../../groups/group/name";
                                    }
                                    max-elements 8;
                                    ordered-by user;
                                    description "Apply a configuration group at this level";
                                }

                                leaf-list apply-groups-exclude {
                                    type leafref {
                                        path "../../../../../../../../groups/group/name";
                                    }
                                    max-elements 8;
                                    ordered-by user;
                                    description "Exclude a configuration group at this level";
                                }

                                list group-prefix {
                                    key "ipv6-prefix";
                                    description "Add a list entry for group-prefix";

                                    leaf ipv6-prefix {
                                        type types-sros:ipv6-multicast-prefix;
                                        description "IPv6 address and prefix length";
                                    }

                                } // list group-prefix

                            } // list address

                        } // container static

                    } // container ipv6

                } // container rp

                list spt-switchover {
                    key "ip-prefix";
                    description "Enter the spt-switchover list instance";

                    leaf ip-prefix {
                        type types-sros:ip-multicast-prefix;
                        description "IP address and mask length";
                    }

                    leaf threshold {
                        type union {
                            type uint32 {
                                range "1..4294967294";
                            }
                            type enumeration {
                                enum infinity                       { value -1; }
                            }
                        }
                        units "kilobps";
                        mandatory true;
                        description "SPT switchover threshold";
                    }

                    leaf-list apply-groups {
                        type leafref {
                            path "../../../../../groups/group/name";
                        }
                        max-elements 8;
                        ordered-by user;
                        description "Apply a configuration group at this level";
                    }

                    leaf-list apply-groups-exclude {
                        type leafref {
                            path "../../../../../groups/group/name";
                        }
                        max-elements 8;
                        ordered-by user;
                        description "Exclude a configuration group at this level";
                    }

                } // list spt-switchover

                container ssm-groups {
                    description "Enter the ssm-groups context";

                    list group-range {
                        key "ip-prefix";
                        description "Add a list entry for group-range";

                        leaf ip-prefix {
                            type types-sros:ip-multicast-prefix;
                            description "IP address and mask length";
                        }

                    } // list group-range

                } // container ssm-groups

            } // container pim

            container vrf-target {
                status obsolete;
                description "Enter the vrf-target context";

                choice vrf-target {
                    status obsolete;
                    case vrf-both-target {
                        status obsolete;

                        leaf community {
                            status obsolete;
                            type types-services:route-target;
                            description "Extended BGP community";
                        }

                    }
                    case vrf-ovr-target {
                        status obsolete;

                        leaf import-community {
                            status obsolete;
                            type types-services:route-target;
                            description "Communities accepted from remote PE neighbors";
                        }

                        leaf export-community {
                            status obsolete;
                            type types-services:route-target;
                            description "Communities to be sent to remote PE neighbors";
                        }

                    }
                }
            } // container vrf-target

            container bgp-shared-queue {
                presence "Enable the bgp-shared-queue context";
                description "Enable the bgp-shared-queue context";

                leaf cir {
                    type types-qos:bgp-shared-queue-cir-rate;
                    units "kilobps";
                    default "4000";
                    description "Committed information rate for shared queue";
                }

                leaf pir {
                    type types-qos:bgp-shared-queue-pir-rate;
                    units "kilobps";
                    default "4000";
                    description "Peak information rate for shared queue";
                }

            } // container bgp-shared-queue

            container vrf-import {
                status obsolete;
                presence "Enable the vrf-import context";
                description "Enable the vrf-import context";

                leaf-list policy {
                    status obsolete;
                    type types-sros:vrf-policy;
                    min-elements 1;
                    max-elements 15;
                    ordered-by user;
                    description "Route policy name";
                }

                leaf-list apply-groups {
                    status obsolete;
                    type leafref {
                        path "../../../../groups/group/name";
                    }
                    max-elements 8;
                    ordered-by user;
                    description "Apply a configuration group at this level";
                }

                leaf-list apply-groups-exclude {
                    status obsolete;
                    type leafref {
                        path "../../../../groups/group/name";
                    }
                    max-elements 8;
                    ordered-by user;
                    description "Exclude a configuration group at this level";
                }

            } // container vrf-import

            container vrf-export {
                status obsolete;
                presence "Enable the vrf-export context";
                description "Enable the vrf-export context";

                leaf-list policy {
                    status obsolete;
                    type types-sros:vrf-policy;
                    min-elements 1;
                    max-elements 15;
                    ordered-by user;
                    description "Route policy name";
                }

                leaf-list apply-groups {
                    status obsolete;
                    type leafref {
                        path "../../../../groups/group/name";
                    }
                    max-elements 8;
                    ordered-by user;
                    description "Apply a configuration group at this level";
                }

                leaf-list apply-groups-exclude {
                    status obsolete;
                    type leafref {
                        path "../../../../groups/group/name";
                    }
                    max-elements 8;
                    ordered-by user;
                    description "Exclude a configuration group at this level";
                }

            } // container vrf-export

            container wpp {
                presence "Enable the wpp context";
                description "Enable the wpp context";

                leaf admin-state {
                    type types-sros:admin-state;
                    default "disable";
                    description "Administrative state of WPP";
                }

                leaf-list apply-groups {
                    type leafref {
                        path "../../../../groups/group/name";
                    }
                    max-elements 8;
                    ordered-by user;
                    description "Apply a configuration group at this level";
                }

                leaf-list apply-groups-exclude {
                    type leafref {
                        path "../../../../groups/group/name";
                    }
                    max-elements 8;
                    ordered-by user;
                    description "Exclude a configuration group at this level";
                }

                list portal {
                    key "name";
                    description "Enter the portal list instance";

                    leaf name {
                        type types-sros:named-item;
                        description "Web portal name";
                    }

                    leaf address {
                        type types-sros:ip-unicast-without-local-address;
                        sros-ext:immutable;
                        mandatory true;
                        description "WPP portal address";
                    }

                    leaf admin-state {
                        type types-sros:admin-state;
                        default "disable";
                        description "Administrative state of the WPP portal server";
                    }

                    leaf secret {
                        type types-sros:encrypted-leaf {
                            length "1..115";
                        }
                        description "Message authentication between portal and BRAS by applying the secret used by WPPv2";
                    }

                    leaf version {
                        type uint32 {
                            range "1|2";
                        }
                        default "1";
                        description "Protocol version to be expected by the WPP portal";
                    }

                    leaf retry-interval {
                        type uint32 {
                            range "10..2000";
                        }
                        units "milliseconds";
                        default "2000";
                        description "Time between two consecutive retransmissions";
                    }

                    leaf ntf-logout-retry-count {
                        type uint32 {
                            range "0..5";
                        }
                        default "5";
                        description "Number of retransmissions of an NTF_LOGOUT message";
                    }

                    leaf ack-auth-retry-count {
                        type uint32 {
                            range "0..5";
                        }
                        default "5";
                        description "Number of retransmissions of an ACK_OUT message";
                    }

                    leaf port-format {
                        type enumeration {
                            enum standard                       { value 1; }
                            enum vendor-specific                { value 2; }
                        }
                        default "standard";
                        description "Format of the port in the ACK_INO message";
                    }

                    leaf-list apply-groups {
                        type leafref {
                            path "../../../../../groups/group/name";
                        }
                        max-elements 8;
                        ordered-by user;
                        description "Apply a configuration group at this level";
                    }

                    leaf-list apply-groups-exclude {
                        type leafref {
                            path "../../../../../groups/group/name";
                        }
                        max-elements 8;
                        ordered-by user;
                        description "Exclude a configuration group at this level";
                    }

                } // list portal

            } // container wpp

            container mvpn {
                description "Enter the mvpn context";

                leaf c-mcast-signaling {
                    type enumeration {
                        enum bgp                            { value 0; }
                        enum pim                            { value 1; }
                    }
                    default "pim";
                    description "Protocol for PE-to-PE signaling of CE multicast states";
                }

                leaf mdt-type {
                    type enumeration {
                        enum sender-only                    { value 0; }
                        enum receiver-only                  { value 1; }
                        enum sender-receiver                { value 2; }
                    }
                    default "sender-receiver";
                    description "MVPN instance type per PE node";
                }

                leaf umh-selection {
                    type enumeration {
                        enum highest-ip                     { value 0; }
                        enum hash-based                     { value 1; }
                        enum tunnel-status                  { value 2; }
                        enum unicast-rt-pref                { value 3; }
                    }
                    default "highest-ip";
                    description "UMH selection mechanism";
                }

                leaf-list apply-groups {
                    type leafref {
                        path "../../../../groups/group/name";
                    }
                    max-elements 8;
                    ordered-by user;
                    description "Apply a configuration group at this level";
                }

                leaf-list apply-groups-exclude {
                    type leafref {
                        path "../../../../groups/group/name";
                    }
                    max-elements 8;
                    ordered-by user;
                    description "Exclude a configuration group at this level";
                }

                container auto-discovery {
                    description "Enter the auto-discovery context";

                    leaf type {
                        type enumeration {
                            enum bgp                            { value 1; }
                            enum mdt-safi                       { value 2; }
                        }
                        description "Status of multicast VPN membership auto-discovery";
                    }

                    leaf source-address {
                        type types-sros:ipv4-address;
                        default "0.0.0.0";
                        description "IPv4 source address";
                    }

                } // container auto-discovery

                container intersite-shared {
                    description "Enter the intersite-shared context";

                    leaf admin-state {
                        type types-sros:admin-state;
                        default "enable";
                        description "Administrative state of inter-site shared C-trees use";
                    }

                    leaf persistent-type5-advertisement {
                        type boolean;
                        default "false";
                        description "Ensure Type-5 S-A routes are generated for MCAST source";
                    }

                    leaf kat-type5-advertisement-withdraw {
                        type boolean;
                        default "false";
                        description "Enable KATs on source PEs for ng-MVPN deployments";
                    }

                } // container intersite-shared

                container redundant-source-list {
                    description "Enter the redundant-source-list context";

                    list source-prefix {
                        key "ip-prefix";
                        max-elements 16;
                        description "Add a list entry for source-prefix";

                        leaf ip-prefix {
                            type types-sros:ip-unicast-prefix;
                            description "Unicast address prefix and mask";
                        }

                    } // list source-prefix

                } // container redundant-source-list

                container rpf-select {
                    description "Enter the rpf-select context";

                    list core-mvpn {
                        key "core-mvpn-service-name";
                        description "Enter the core-mvpn list instance";

                        leaf core-mvpn-service-name {
                            type leafref {
                                path "../../../../../vprn/service-name";
                            }
                            description "Core MVPN service name";
                        }

                        leaf-list apply-groups {
                            type leafref {
                                path "../../../../../../groups/group/name";
                            }
                            max-elements 8;
                            ordered-by user;
                            description "Apply a configuration group at this level";
                        }

                        leaf-list apply-groups-exclude {
                            type leafref {
                                path "../../../../../../groups/group/name";
                            }
                            max-elements 8;
                            ordered-by user;
                            description "Exclude a configuration group at this level";
                        }

                        list group-prefix {
                            key "ip-group-prefix";
                            min-elements 1;
                            description "Enter the group-prefix list instance";

                            leaf ip-group-prefix {
                                type types-sros:ipv4-multicast-prefix;
                                description "IPv4 multicast address prefix and mask";
                            }

                            leaf starg {
                                type boolean;
                                sros-ext:immutable;
                                default "false";
                                description "Starg flag";
                            }

                            leaf-list apply-groups {
                                type leafref {
                                    path "../../../../../../../groups/group/name";
                                }
                                max-elements 8;
                                ordered-by user;
                                description "Apply a configuration group at this level";
                            }

                            leaf-list apply-groups-exclude {
                                type leafref {
                                    path "../../../../../../../groups/group/name";
                                }
                                max-elements 8;
                                ordered-by user;
                                description "Exclude a configuration group at this level";
                            }

                        } // list group-prefix

                    } // list core-mvpn

                } // container rpf-select

                container umh-pe-backup {
                    description "Enter the umh-pe-backup context";

                    list umh-pe {
                        key "ip-address";
                        description "Enter the umh-pe list instance";

                        leaf ip-address {
                            type types-sros:ipv4-unicast-address;
                            description "IP address for the standby PE";
                        }

                        leaf standby {
                            type types-sros:ipv4-unicast-address;
                            mandatory true;
                            description "IP address";
                        }

                        leaf-list apply-groups {
                            type leafref {
                                path "../../../../../../groups/group/name";
                            }
                            max-elements 8;
                            ordered-by user;
                            description "Apply a configuration group at this level";
                        }

                        leaf-list apply-groups-exclude {
                            type leafref {
                                path "../../../../../../groups/group/name";
                            }
                            max-elements 8;
                            ordered-by user;
                            description "Exclude a configuration group at this level";
                        }

                    } // list umh-pe

                } // container umh-pe-backup

                container vrf-import {
                    description "Enter the vrf-import context";

                    choice vrf-import {
                        case policy {

                            leaf-list policy {
                                type union {
                                    type types-sros:policy-expr-string;
                                    type string;
                                }
                                min-elements 1;
                                max-elements 15;
                                ordered-by user;
                                description "Route policy name";
                            }

                        }
                        case unicast {

                            leaf unicast {
                                type boolean;
                                default "false";
                                description "Enable the unicast VRF import policy for the MVPN";
                            }

                        }
                    }
                } // container vrf-import

                container vrf-export {
                    description "Enter the vrf-export context";

                    choice vrf-export {
                        case policy {

                            leaf-list policy {
                                type union {
                                    type types-sros:policy-expr-string;
                                    type string;
                                }
                                min-elements 1;
                                max-elements 15;
                                ordered-by user;
                                description "Route policy name";
                            }

                        }
                        case unicast {

                            leaf unicast {
                                type boolean;
                                default "false";
                                description "Enable the unicast VRF export policy for the MVPN";
                            }

                        }
                    }
                } // container vrf-export

                container vrf-target {
                    description "Enter the vrf-target context";

                    leaf community {
                        type types-services:route-target;
                        description "Extended community name for the MVPN";
                    }

                    leaf unicast {
                        type boolean;
                        default "false";
                        description "Enable unicast vrf-target for the MVPN";
                    }

                    container import {
                        description "Enter the import context";

                        leaf community {
                            type types-services:route-target;
                            description "Extended community name for the MVPN";
                        }

                        leaf unicast {
                            type boolean;
                            default "false";
                            description "Enable the unicast vrf-target for the MVPN";
                        }

                    } // container import

                    container export {
                        description "Enter the export context";

                        leaf community {
                            type types-services:route-target;
                            description "Extended community name for the MVPN";
                        }

                        leaf unicast {
                            type boolean;
                            default "false";
                            description "Enable the unicast vrf-target for the MVPN";
                        }

                    } // container export

                } // container vrf-target

                container provider-tunnel {
                    description "Enter the provider-tunnel context";

                    container inclusive {
                        description "Enter the inclusive context";

                        leaf bsr {
                            type enumeration {
                                enum unicast                        { value 1; }
                                enum spmsi                          { value 2; }
                            }
                            description "BSR signaling type";
                        }

                        leaf wildcard-spmsi {
                            type boolean;
                            default "false";
                            description "Enable RFC 6625 S-PMSI functionality for NG-MVPN";
                        }

                        leaf suppress-ipmsi {
                            type boolean;
                            default "false";
                            description "Suppress advertisement of I-PMSI";
                        }

                        choice ipmsi {
                            case rsvp {

                                container rsvp {
                                    presence "Enable the rsvp context";
                                    description "Enable the rsvp context";

                                    leaf admin-state {
                                        type types-sros:admin-state;
                                        default "disable";
                                        description "Administrative state of RSVP use for provider tunnels";
                                    }

                                    leaf bfd-leaf {
                                        type boolean;
                                        default "false";
                                        description "Enable unidirectional multi-point BFD on a receiver";
                                    }

                                    leaf lsp-template {
                                        type leafref {
                                            path "../../../../../../../router/mpls/lsp-template/template-name";
                                        }
                                        description "P2MP LSP created as the provider tunnel";
                                    }

                                    container bfd-root {
                                        presence "Enable the bfd-root context";
                                        description "Enable the bfd-root context";

                                        leaf transmit-interval {
                                            type uint32 {
                                                range "10..100000";
                                            }
                                            mandatory true;
                                            description "Transmit interval for the BFD session";
                                        }

                                        leaf multiplier {
                                            type uint32 {
                                                range "1..20";
                                            }
                                            default "3";
                                            description "Enable unidirectional multi-point BFD on a sender";
                                        }

                                    } // container bfd-root

                                } // container rsvp

                            }
                            case mldp {

                                container mldp {
                                    presence "Enable the mldp context";
                                    description "Enable the mldp context";

                                    leaf admin-state {
                                        type types-sros:admin-state;
                                        default "disable";
                                        description "Administrative state of MLDP LSP use for tunnels";
                                    }

                                } // container mldp

                            }
                            case pim {

                                container pim {
                                    presence "Enable the pim context";
                                    description "Enable the pim context";

                                    leaf mode {
                                        type enumeration {
                                            enum asm                            { value 1; }
                                            enum ssm                            { value 2; }
                                        }
                                        mandatory true;
                                        description "PIM mode for the inclusive provider tunnel";
                                    }

                                    leaf group-address {
                                        type types-sros:ipv4-multicast-address;
                                        mandatory true;
                                        description "Multicast group address";
                                    }

                                    leaf hello-interval {
                                        type uint32 {
                                            range "0..255";
                                        }
                                        default "30";
                                        description "Frequency at which PIM Hello messages are transmitted";
                                    }

                                    leaf hello-multiplier {
                                        type uint32 {
                                            range "20..100";
                                        }
                                        default "35";
                                        description "Multiplier to determine the holdtime for a PIM neighbor";
                                    }

                                    leaf improved-assert {
                                        type boolean;
                                        default "true";
                                        description "Enable the improved assert procedure";
                                    }

                                    leaf three-way-hello {
                                        type boolean;
                                        default "false";
                                        description "Enable PIM three-way hello";
                                    }

                                    leaf tracking-support {
                                        type boolean;
                                        default "false";
                                        description "Enable the T bit in the LAN Prune Delay option";
                                    }

                                    leaf admin-state {
                                        type types-sros:admin-state;
                                        default "enable";
                                        description "Administrative state of PIM use for provider tunnels";
                                    }

                                } // container pim

                            }
                            case bier {

                                container bier {
                                    presence "Enable the bier context";
                                    description "Enable the bier context";

                                    leaf admin-state {
                                        type types-sros:admin-state;
                                        default "disable";
                                        description "Administrative state of BIER";
                                    }

                                    leaf sub-domain {
                                        type int32 {
                                            range "0..255";
                                        }
                                        description "Sub-domain used to attach the BIER provider tunnel";
                                    }

                                } // container bier

                            }
                            case p2mp-sr {

                                container p2mp-sr {
                                    presence "Enable the p2mp-sr context";
                                    description "Enable the p2mp-sr context";

                                    leaf bfd-leaf {
                                        type boolean;
                                        default "false";
                                        description "Enable unidirectional multipoint BFD on the leaf PE";
                                    }

                                    leaf static-policy {
                                        status obsolete;
                                        type leafref {
                                            path "../../../../../../../router/p2mp-sr-tree/p2mp-policy/p2mp-policy-name";
                                        }
                                        description "Static policy for inclusive MVPN provider tunnel";
                                    }

                                    leaf static-policy-mpls {
                                        type leafref {
                                            path "../../../../../../../router/p2mp-sr-tree/p2mp-policy/p2mp-policy-name";
                                        }
                                        description "Static P2MP policy for inclusive MVPN provider tunnel";
                                    }

                                    leaf p2mp-policy {
                                        status obsolete;
                                        type boolean;
                                        default "false";
                                        description "Use P2MP policy for inclusive MVPN provider tunnel";
                                    }

                                    leaf p2mp-policy-mpls {
                                        type boolean;
                                        default "false";
                                        description "Use P2MP policy for MVPN provider tunnel";
                                    }

                                    leaf admin-state {
                                        type types-sros:admin-state;
                                        default "disable";
                                        description "Administrative state for P2MP SR";
                                    }

                                    container bfd-root {
                                        presence "Enable the bfd-root context";
                                        description "Enable the bfd-root context";

                                        leaf transmit-interval {
                                            type uint32 {
                                                range "10..100000";
                                            }
                                            mandatory true;
                                            description "Transmit interval of the BFD session";
                                        }

                                        leaf multiplier {
                                            type uint32 {
                                                range "1..20";
                                            }
                                            default "3";
                                            description "Multiplier for the transmit interval of the BFD session";
                                        }

                                    } // container bfd-root

                                } // container p2mp-sr

                            }
                        }
                        container umh-rate-monitoring {
                            description "Enter the umh-rate-monitoring context";

                            leaf traffic-rate-delta {
                                type uint32 {
                                    range "0..4294967294";
                                }
                                description "Rate delta between PMSIs under which traffic switches";
                            }

                            leaf revertive-timer {
                                type uint32 {
                                    range "0..3600";
                                }
                                description "Time until switch to primary PMSI after recovering rate";
                            }

                            leaf fpe {
                                type leafref {
                                    path "../../../../../../../fwd-path-ext/fpe/fpe-id";
                                }
                                description "Forward path extension (FPE) ID for the entry";
                            }

                        } // container umh-rate-monitoring

                    } // container inclusive

                    container selective {
                        description "Enter the selective context";

                        leaf auto-discovery {
                            type boolean;
                            default "false";
                            description "Enable C-trees to P-tunnel binding auto-discovery";
                        }

                        leaf data-delay-interval {
                            type uint32 {
                                range "3..180";
                            }
                            default "3";
                            description "Interval a PE switches from inclusive to selective";
                        }

                        leaf join-tlv-packing {
                            type boolean;
                            default "true";
                            description "Enable packing of MDT join TLVs into a single PDU";
                        }

                        leaf asm-mdt {
                            type boolean;
                            default "false";
                            description "Enable Data MDT with PIM-ASM mode on receiver PE node";
                        }

                        choice spmsi {
                            case rsvp {

                                container rsvp {
                                    presence "Enable the rsvp context";
                                    description "Enable the rsvp context";

                                    leaf lsp-template {
                                        type leafref {
                                            path "../../../../../../../router/mpls/lsp-template/template-name";
                                        }
                                        description "P2MP LSP created as the selective provider tunnel";
                                    }

                                    leaf admin-state {
                                        type types-sros:admin-state;
                                        default "disable";
                                        description "Administrative state of RSVP use for provider tunnels";
                                    }

                                    leaf maximum-p2mp-spmsi {
                                        type uint32 {
                                            range "1..4000";
                                        }
                                        default "10";
                                        description "Maximum number of RSVP P2MP or LDP P2MP S-PMSI tunnels";
                                    }

                                } // container rsvp

                            }
                            case mldp {

                                container mldp {
                                    presence "Enable the mldp context";
                                    description "Enable the mldp context";

                                    leaf admin-state {
                                        type types-sros:admin-state;
                                        default "disable";
                                        description "Administrative state of MLDP LSP use for tunnels";
                                    }

                                    leaf maximum-p2mp-spmsi {
                                        type uint32 {
                                            range "1..4000";
                                        }
                                        default "10";
                                        description "Maximum number of RSVP P2MP or LDP P2MP S-PMSI tunnels";
                                    }

                                } // container mldp

                            }
                            case pim {

                                container pim {
                                    presence "Enable the pim context";
                                    description "Enable the pim context";

                                    leaf mode {
                                        type enumeration {
                                            enum asm                            { value 1; }
                                            enum ssm                            { value 2; }
                                        }
                                        mandatory true;
                                        description "PIM mode";
                                    }

                                    leaf group-prefix {
                                        type types-sros:ipv4-multicast-prefix;
                                        mandatory true;
                                        description "Multicast group address and netmask length";
                                    }

                                } // container pim

                            }
                            case bier {

                                container bier {
                                    presence "Enable the bier context";
                                    description "Enable the bier context";

                                    leaf admin-state {
                                        type types-sros:admin-state;
                                        default "disable";
                                        description "Administrative state of BIER";
                                    }

                                    leaf sub-domain {
                                        type int32 {
                                            range "0..255";
                                        }
                                        description "Sub-domain used to attach the BIER provider tunnel";
                                    }

                                } // container bier

                            }
                            case p2mp-sr {

                                container p2mp-sr {
                                    presence "Enable the p2mp-sr context";
                                    description "Enable the p2mp-sr context";

                                    leaf static-policy {
                                        status obsolete;
                                        type leafref {
                                            path "../../../../../../../router/p2mp-sr-tree/p2mp-policy/p2mp-policy-name";
                                        }
                                        description "Static policy for selective MVPN provider tunnel";
                                    }

                                    leaf p2mp-policy {
                                        status obsolete;
                                        type boolean;
                                        default "false";
                                        description "Use P2MP policy for selective MVPN provider tunnel";
                                    }

                                    leaf static-policy-mpls {
                                        type leafref {
                                            path "../../../../../../../router/p2mp-sr-tree/p2mp-policy/p2mp-policy-name";
                                        }
                                        description "Static P2MP policy for selective MVPN provider tunnel";
                                    }

                                    leaf p2mp-policy-mpls {
                                        type boolean;
                                        default "false";
                                        description "Use P2MP policy for MVPN provider tunnel";
                                    }

                                    leaf admin-state {
                                        type types-sros:admin-state;
                                        default "disable";
                                        description "Administrative state of P2MP SR";
                                    }

                                } // container p2mp-sr

                            }
                        }
                        container data-threshold {
                            description "Enter the data-threshold context";

                            list group-prefix {
                                key "ip-group-prefix";
                                description "Enter the group-prefix list instance";

                                leaf ip-group-prefix {
                                    type types-sros:ip-multicast-prefix;
                                    description "IPv4 or IPv6 multicast group address and prefix";
                                }

                                leaf threshold {
                                    type int64 {
                                        range "0..4294967294";
                                    }
                                    units "kilobps";
                                    mandatory true;
                                    description "S-PMSI threshold";
                                }

                                leaf pe-threshold-add {
                                    type uint32 {
                                        range "1..65535";
                                    }
                                    default "65535";
                                    description "PE add threshold";
                                }

                                leaf pe-threshold-delete {
                                    type uint32 {
                                        range "2..65535";
                                    }
                                    default "65535";
                                    description "PE delete threshold";
                                }

                                leaf-list apply-groups {
                                    type leafref {
                                        path "../../../../../../../../groups/group/name";
                                    }
                                    max-elements 8;
                                    ordered-by user;
                                    description "Apply a configuration group at this level";
                                }

                                leaf-list apply-groups-exclude {
                                    type leafref {
                                        path "../../../../../../../../groups/group/name";
                                    }
                                    max-elements 8;
                                    ordered-by user;
                                    description "Exclude a configuration group at this level";
                                }

                            } // list group-prefix

                        } // container data-threshold

                        list multistream-spmsi {
                            key "multistream-id";
                            description "Enter the multistream-spmsi list instance";

                            leaf multistream-id {
                                type uint32 {
                                    range "1..1024";
                                }
                                description "Multistream spmsi id";
                            }

                            leaf admin-state {
                                type types-sros:admin-state;
                                default "disable";
                                description "Administrative state of multi-stream S-PMSI";
                            }

                            leaf-list apply-groups {
                                type leafref {
                                    path "../../../../../../../groups/group/name";
                                }
                                max-elements 8;
                                ordered-by user;
                                description "Apply a configuration group at this level";
                            }

                            leaf-list apply-groups-exclude {
                                type leafref {
                                    path "../../../../../../../groups/group/name";
                                }
                                max-elements 8;
                                ordered-by user;
                                description "Exclude a configuration group at this level";
                            }

                            choice spmsi {
                                case lsp-template {

                                    leaf lsp-template {
                                        type leafref {
                                            path "../../../../../../../router/mpls/lsp-template/template-name";
                                        }
                                        description "RSVP-TE LSP template for S-PMSI";
                                    }

                                }
                                case pim {

                                    container pim {
                                        presence "Enable the pim context";
                                        description "Enable the pim context";

                                        leaf mode {
                                            type enumeration {
                                                enum asm                            { value 1; }
                                                enum ssm                            { value 2; }
                                            }
                                            description "PIM mode for the selective provider tunnel";
                                        }

                                        leaf group-address {
                                            type types-sros:ipv4-multicast-address;
                                            description "Group address of the data MDT";
                                        }

                                    } // container pim

                                }
                                case p2mp-sr {

                                    container p2mp-sr {
                                        description "Enter the p2mp-sr context";

                                        leaf static-policy {
                                            status obsolete;
                                            type leafref {
                                                path "../../../../../../../../router/p2mp-sr-tree/p2mp-policy/p2mp-policy-name";
                                            }
                                            description "P2MP static policy for inclusive MVPN provider tunnel";
                                        }

                                        leaf static-policy-mpls {
                                            type leafref {
                                                path "../../../../../../../../router/p2mp-sr-tree/p2mp-policy/p2mp-policy-name";
                                            }
                                            description "Static P2MP policy for multistream MVPN provider tunnel";
                                        }

                                        leaf p2mp-policy {
                                            status obsolete;
                                            type boolean;
                                            default "false";
                                            description "Use P2MP policy for selective MVPN provider tunnel";
                                        }

                                        leaf p2mp-policy-mpls {
                                            type boolean;
                                            default "false";
                                            description "Use P2MP policy for multistream MVPN provider tunnel";
                                        }

                                    } // container p2mp-sr

                                }
                            }
                            list group-prefix {
                                key "ip-group-prefix source-prefix";
                                description "Add a list entry for group-prefix";

                                leaf ip-group-prefix {
                                    type types-sros:ip-multicast-prefix;
                                    description "IPv4 or IPv6 multicast group address and prefix";
                                }

                                leaf source-prefix {
                                    type types-sros:ip-unicast-prefix;
                                    description "IPv4 or IPv6 unicast source address and prefix";
                                }

                            } // list group-prefix

                        } // list multistream-spmsi

                        container umh-rate-monitoring {
                            description "Enter the umh-rate-monitoring context";

                            list group {
                                key "group-ip-address source";
                                description "Enter the group list instance";

                                leaf group-ip-address {
                                    type types-sros:ip-multicast-prefix;
                                    description "Group IP address";
                                }

                                leaf source {
                                    type types-sros:ip-unicast-prefix;
                                    description "Source IP address";
                                }

                                leaf traffic-rate-delta {
                                    type uint32 {
                                        range "0..4294967294";
                                    }
                                    description "Rate delta between PMSIs under which traffic switches";
                                }

                                leaf revertive-timer {
                                    type uint32 {
                                        range "0..3600";
                                    }
                                    description "Time until switch to primary PMSI after recovering rate";
                                }

                                leaf fpe {
                                    type leafref {
                                        path "../../../../../../../../fwd-path-ext/fpe/fpe-id";
                                    }
                                    description "Forward path extension (FPE) ID for the entry";
                                }

                                leaf-list apply-groups {
                                    type leafref {
                                        path "../../../../../../../../groups/group/name";
                                    }
                                    max-elements 8;
                                    ordered-by user;
                                    description "Apply a configuration group at this level";
                                }

                                leaf-list apply-groups-exclude {
                                    type leafref {
                                        path "../../../../../../../../groups/group/name";
                                    }
                                    max-elements 8;
                                    ordered-by user;
                                    description "Exclude a configuration group at this level";
                                }

                            } // list group

                        } // container umh-rate-monitoring

                    } // container selective

                } // container provider-tunnel

            } // container mvpn

            container ntp {
                presence "Enable the ntp context";
                description "Enable the ntp context";

                leaf authentication-check {
                    type boolean;
                    default "true";
                    description "Authenticate NTP PDUs and reject mismatches";
                }

                leaf admin-state {
                    type types-sros:admin-state;
                    default "disable";
                    description "Administrative state of NTP execution";
                }

                leaf authentication-keychain {
                    type leafref {
                        path "../../../../system/security/keychains/keychain/keychain-name";
                    }
                    description "Authentication keychain for unsolicited traffic";
                }

                leaf authenticate {
                    type boolean;
                    default "false";
                    description "Authentication of NTP PDUs when acting as a server";
                }

                leaf-list apply-groups {
                    type leafref {
                        path "../../../../groups/group/name";
                    }
                    max-elements 8;
                    ordered-by user;
                    description "Apply a configuration group at this level";
                }

                leaf-list apply-groups-exclude {
                    type leafref {
                        path "../../../../groups/group/name";
                    }
                    max-elements 8;
                    ordered-by user;
                    description "Exclude a configuration group at this level";
                }

                list authentication-key {
                    key "key-id";
                    description "Enter the authentication-key list instance";

                    leaf key-id {
                        type uint32 {
                            range "1..255";
                        }
                        description "Authentication key ID used for NTP packets";
                    }

                    leaf key {
                        type types-sros:encrypted-leaf {
                            length "1..71";
                        }
                        mandatory true;
                        description "Key to authenticate NTP packets";
                    }

                    leaf type {
                        type enumeration {
                            enum des                            { value 1; }
                            enum message-digest                 { value 2; }
                        }
                        mandatory true;
                        description "Authentication method to authenticate NTP packet";
                    }

                    leaf-list apply-groups {
                        type leafref {
                            path "../../../../../groups/group/name";
                        }
                        max-elements 8;
                        ordered-by user;
                        description "Apply a configuration group at this level";
                    }

                    leaf-list apply-groups-exclude {
                        type leafref {
                            path "../../../../../groups/group/name";
                        }
                        max-elements 8;
                        ordered-by user;
                        description "Exclude a configuration group at this level";
                    }

                } // list authentication-key

                list broadcast {
                    key "interface-name";
                    description "Enter the broadcast list instance";

                    leaf interface-name {
                        type leafref {
                            path "../../../../vprn[service-name=current()/../../../service-name]/interface/interface-name";
                        }
                        description "Local interface used to transmit NTP broadcast packets";
                    }

                    leaf version {
                        type uint32 {
                            range "2..4";
                        }
                        default "4";
                        description "NTP version number generated by the node";
                    }

                    leaf ttl {
                        type uint32 {
                            range "1..255";
                        }
                        default "127";
                        description "TTL of messages transmitted by the broadcast address";
                    }

                    leaf-list apply-groups {
                        type leafref {
                            path "../../../../../groups/group/name";
                        }
                        max-elements 8;
                        ordered-by user;
                        description "Apply a configuration group at this level";
                    }

                    leaf-list apply-groups-exclude {
                        type leafref {
                            path "../../../../../groups/group/name";
                        }
                        max-elements 8;
                        ordered-by user;
                        description "Exclude a configuration group at this level";
                    }

                    choice key-or-keychain {
                        case key {

                            leaf key-id {
                                type leafref {
                                    path "../../authentication-key/key-id";
                                }
                                description "Authentication key and type used by the node";
                            }

                        }
                        case keychain {

                            leaf authentication-keychain {
                                type leafref {
                                    path "../../../../../system/security/keychains/keychain/keychain-name";
                                }
                                description "Keychain used to authenticate broadcast messages";
                            }

                        }
                    }
                } // list broadcast

            } // container ntp

            list segment-routing-v6 {
                key "instance";
                description "Enter the segment-routing-v6 list instance";

                leaf instance {
                    type types-services:srv6-instance;
                    description "Segment routing IPv6 instance";
                }

                leaf-list apply-groups {
                    type leafref {
                        path "../../../../groups/group/name";
                    }
                    max-elements 8;
                    ordered-by user;
                    description "Apply a configuration group at this level";
                }

                leaf-list apply-groups-exclude {
                    type leafref {
                        path "../../../../groups/group/name";
                    }
                    max-elements 8;
                    ordered-by user;
                    description "Exclude a configuration group at this level";
                }

                list locator {
                    key "locator-name";
                    description "Enter the locator list instance";

                    leaf locator-name {
                        type leafref {
                            path "../../../../../router/segment-routing/segment-routing-v6/locator/locator-name";
                        }
                        description "SRv6 locator name";
                    }

                    leaf-list apply-groups {
                        type leafref {
                            path "../../../../../groups/group/name";
                        }
                        max-elements 8;
                        ordered-by user;
                        description "Apply a configuration group at this level";
                    }

                    leaf-list apply-groups-exclude {
                        type leafref {
                            path "../../../../../groups/group/name";
                        }
                        max-elements 8;
                        ordered-by user;
                        description "Exclude a configuration group at this level";
                    }

                    container function {
                        description "Enter the function context";

                        container end-dt4 {
                            presence "Enable the end-dt4 context";
                            description "Enable the end-dt4 context";

                            leaf value {
                                type uint32 {
                                    range "1..1048575";
                                }
                                description "SRv6 function value";
                            }

                        } // container end-dt4

                        container end-dt6 {
                            presence "Enable the end-dt6 context";
                            description "Enable the end-dt6 context";

                            leaf value {
                                type uint32 {
                                    range "1..1048575";
                                }
                                description "SRv6 function value";
                            }

                        } // container end-dt6

                        container end-dt46 {
                            presence "Enable the end-dt46 context";
                            description "Enable the end-dt46 context";

                            leaf value {
                                type uint32 {
                                    range "1..1048575";
                                }
                                description "SRv6 function value";
                            }

                        } // container end-dt46

                    } // container function

                } // list locator

                list micro-segment-locator {
                    key "locator-name";
                    description "Enter the micro-segment-locator list instance";

                    leaf locator-name {
                        type leafref {
                            path "../../../../../router/segment-routing/segment-routing-v6/micro-segment-locator/locator-name";
                        }
                        description "Micro-segment SRv6 locator name";
                    }

                    leaf-list apply-groups {
                        type leafref {
                            path "../../../../../groups/group/name";
                        }
                        max-elements 8;
                        ordered-by user;
                        description "Apply a configuration group at this level";
                    }

                    leaf-list apply-groups-exclude {
                        type leafref {
                            path "../../../../../groups/group/name";
                        }
                        max-elements 8;
                        ordered-by user;
                        description "Exclude a configuration group at this level";
                    }

                    container function {
                        description "Enter the function context";

                        container udt4 {
                            presence "Enable the udt4 context";
                            description "Enable the udt4 context";

                            leaf value {
                                type uint32 {
                                    range "1..1048575";
                                }
                                description "SRv6 function value";
                            }

                        } // container udt4

                        container udt6 {
                            presence "Enable the udt6 context";
                            description "Enable the udt6 context";

                            leaf value {
                                type uint32 {
                                    range "1..1048575";
                                }
                                description "SRv6 function value";
                            }

                        } // container udt6

                        container udt46 {
                            presence "Enable the udt46 context";
                            description "Enable the udt46 context";

                            leaf value {
                                type uint32 {
                                    range "1..1048575";
                                }
                                description "SRv6 function value";
                            }

                        } // container udt46

                    } // container function

                } // list micro-segment-locator

            } // list segment-routing-v6

            container bgp-evpn {
                description "Enter the bgp-evpn context";

                list mpls {
                    key "bgp-instance";
                    description "Enter the mpls list instance";

                    leaf bgp-instance {
                        type int32 {
                            range "1";
                        }
                        description "BGP instance ID";
                    }

                    leaf admin-state {
                        type types-sros:admin-state;
                        default "disable";
                        description "Administrative state of BGP-EVPN MPLS";
                    }

                    leaf route-distinguisher {
                        type types-services:vprn-bgp-evpn-mpls-rd;
                        description "Route distinguisher";
                    }

                    leaf default-route-tag {
                        type types-services:one-byte-value;
                        sros-ext:auto-restart-to-modify;
                        description "Default route tag";
                    }

                    leaf domain-id {
                        type types-services:domain-id;
                        sros-ext:auto-restart-to-modify;
                        description "Domain ID of received BGP route before readvertisement";
                    }

                    leaf dynamic-egress-label-limit {
                        type boolean;
                        default "false";
                        description "Enables dynamic egress label limit";
                    }

                    leaf evi {
                        type uint32 {
                            range "1..16777215";
                        }
                        sros-ext:auto-restart-to-modify;
                        description "EVPN instance ID";
                    }

                    leaf-list apply-groups {
                        type leafref {
                            path "../../../../../groups/group/name";
                        }
                        max-elements 8;
                        ordered-by user;
                        description "Apply a configuration group at this level";
                    }

                    leaf-list apply-groups-exclude {
                        type leafref {
                            path "../../../../../groups/group/name";
                        }
                        max-elements 8;
                        ordered-by user;
                        description "Exclude a configuration group at this level";
                    }

                    container send-tunnel-encap {
                        description "Enter the send-tunnel-encap context";

                        leaf mpls {
                            type boolean;
                            sros-ext:auto-restart-to-modify;
                            default "true";
                            description "Enable MPLS encapsulation";
                        }

                        leaf mpls-over-udp {
                            type boolean;
                            sros-ext:auto-restart-to-modify;
                            default "false";
                            description "Enable MPLS over UDP encapsulation";
                        }

                    } // container send-tunnel-encap

                    container vrf-export {
                        presence "Enable the vrf-export context";
                        description "Enable the vrf-export context";

                        leaf-list policy {
                            type union {
                                type types-sros:policy-expr-string;
                                type string;
                            }
                            min-elements 1;
                            max-elements 15;
                            ordered-by user;
                            description "Policy name";
                        }

                        leaf-list apply-groups {
                            type leafref {
                                path "../../../../../../groups/group/name";
                            }
                            max-elements 8;
                            ordered-by user;
                            description "Apply a configuration group at this level";
                        }

                        leaf-list apply-groups-exclude {
                            type leafref {
                                path "../../../../../../groups/group/name";
                            }
                            max-elements 8;
                            ordered-by user;
                            description "Exclude a configuration group at this level";
                        }

                    } // container vrf-export

                    container vrf-import {
                        presence "Enable the vrf-import context";
                        description "Enable the vrf-import context";

                        leaf-list policy {
                            type union {
                                type types-sros:policy-expr-string;
                                type string;
                            }
                            min-elements 1;
                            max-elements 15;
                            ordered-by user;
                            description "Policy name";
                        }

                        leaf-list apply-groups {
                            type leafref {
                                path "../../../../../../groups/group/name";
                            }
                            max-elements 8;
                            ordered-by user;
                            description "Apply a configuration group at this level";
                        }

                        leaf-list apply-groups-exclude {
                            type leafref {
                                path "../../../../../../groups/group/name";
                            }
                            max-elements 8;
                            ordered-by user;
                            description "Exclude a configuration group at this level";
                        }

                    } // container vrf-import

                    container vrf-target {
                        description "Enter the vrf-target context";

                        choice vrf-target {
                            case vrf-both-target {

                                leaf community {
                                    type types-services:route-target;
                                    description "Extended BGP community";
                                }

                            }
                            case vrf-ovr-target {

                                leaf import-community {
                                    type types-services:route-target;
                                    description "Communities accepted from remote PE neighbors";
                                }

                                leaf export-community {
                                    type types-services:route-target;
                                    description "Communities sent to remote PE neighbors";
                                }

                            }
                        }
                    } // container vrf-target

                    container auto-bind-tunnel {
                        description "Enter the auto-bind-tunnel context";

                        leaf resolution {
                            type types-services:resolve-status;
                            default "none";
                            description "Resolution method for tunnel selection";
                        }

                        leaf enforce-strict-tunnel-tagging {
                            type boolean;
                            default "false";
                            description "Allow enforcement of strict tunnel tagging";
                        }

                        leaf ecmp {
                            type types-router:mpls-ecmp;
                            default "1";
                            description "Maximum ECMP routes allowed";
                        }

                        leaf allow-flex-algo-fallback {
                            type boolean;
                            default "false";
                            description "Enable flexible algorithm fallback";
                        }

                        container resolution-filter {
                            description "Enter the resolution-filter context";

                            leaf bgp {
                                type boolean;
                                default "false";
                                description "Use BGP tunneling for next-hop resolution";
                            }

                            leaf ldp {
                                type boolean;
                                default "false";
                                description "Use LDP tunneling for next-hop resolution";
                            }

                            leaf rsvp {
                                type boolean;
                                default "false";
                                description "Use RSVP tunneling for next-hop resolution";
                            }

                            leaf sr-isis {
                                type boolean;
                                default "false";
                                description "Use IS-IS SR tunneling for next-hop resolution";
                            }

                            leaf sr-ospf {
                                type boolean;
                                default "false";
                                description "Use OSPF SR tunneling for next-hop resolution";
                            }

                            leaf sr-te {
                                type boolean;
                                default "false";
                                description "Use SR-TE tunneling for next-hop resolution";
                            }

                            leaf udp {
                                type boolean;
                                default "false";
                                description "Use MPLS over UDP tunneling for next-hop resolution";
                            }

                            leaf mpls-fwd-policy {
                                type boolean;
                                default "false";
                                description "Use MPLS forwarding policy for next-hop resolution";
                            }

                            leaf sr-policy {
                                type boolean;
                                default "false";
                                description "Use SR policies for next-hop resolution";
                            }

                            leaf rib-api {
                                type boolean;
                                default "false";
                                description "Use RIB API gRPC service for next-hop resolution";
                            }

                            leaf sr-ospf3 {
                                type boolean;
                                default "false";
                                description "Use OSPFv3 SR tunneling for next-hop resolution";
                            }

                        } // container resolution-filter

                    } // container auto-bind-tunnel

                    container evpn-link-bandwidth {
                        description "Enter the evpn-link-bandwidth context";

                        leaf weighted-ecmp {
                            type boolean;
                            default "false";
                            description "Enable weighted ECMP";
                        }

                        container advertise {
                            presence "Enable the advertise context";
                            description "Enable the advertise context";

                            leaf weight {
                                type union {
                                    type uint32 {
                                        range "1..128";
                                    }
                                    type enumeration {
                                        enum dynamic                        { value 0; }
                                    }
                                }
                                default "dynamic";
                                description "Weight of the route";
                            }

                            leaf max-dynamic-weight {
                                type uint32 {
                                    range "1..128";
                                }
                                default "128";
                                description "Maximum dynamic weight of the route";
                            }

                        } // container advertise

                    } // container evpn-link-bandwidth

                } // list mpls

                list segment-routing-v6 {
                    key "bgp-instance";
                    description "Enter the segment-routing-v6 list instance";

                    leaf bgp-instance {
                        type int32 {
                            range "1..2";
                        }
                        description "BGP instance";
                    }

                    leaf admin-state {
                        type types-sros:admin-state;
                        default "disable";
                        description "Administrative state of segment routing over IPv6";
                    }

                    leaf route-distinguisher {
                        type types-services:vpn-rd-or-auto-rd;
                        description "Route distinguisher";
                    }

                    leaf default-route-tag {
                        type types-services:one-byte-value;
                        description "Default route tag";
                    }

                    leaf source-address {
                        type types-sros:ipv6-unicast-address;
                        sros-ext:auto-restart-to-modify;
                        description "Source IPv6 address";
                    }

                    leaf domain-id {
                        type types-services:domain-id;
                        sros-ext:auto-restart-to-modify;
                        description "Domain ID of received BGP route before readvertisement";
                    }

                    leaf evi {
                        type uint32 {
                            range "1..16777215";
                        }
                        sros-ext:auto-restart-to-modify;
                        description "EVI information";
                    }

                    leaf resolution {
                        type types-sros:srv6-route-resolution;
                        default "route-table";
                        description "Resolution options for routes";
                    }

                    leaf-list apply-groups {
                        type leafref {
                            path "../../../../../groups/group/name";
                        }
                        max-elements 8;
                        ordered-by user;
                        description "Apply a configuration group at this level";
                    }

                    leaf-list apply-groups-exclude {
                        type leafref {
                            path "../../../../../groups/group/name";
                        }
                        max-elements 8;
                        ordered-by user;
                        description "Exclude a configuration group at this level";
                    }

                    container vrf-target {
                        description "Enter the vrf-target context";

                        choice vrf-target {
                            case vrf-both-target {

                                leaf community {
                                    type types-services:route-target;
                                    description "Extended BGP community";
                                }

                            }
                            case vrf-ovr-target {

                                leaf import-community {
                                    type types-services:route-target;
                                    description "Communities accepted from remote PE neighbors";
                                }

                                leaf export-community {
                                    type types-services:route-target;
                                    description "Communities sent to remote PE neighbors";
                                }

                            }
                        }
                    } // container vrf-target

                    container vrf-import {
                        presence "Enable the vrf-import context";
                        description "Enable the vrf-import context";

                        leaf-list policy {
                            type union {
                                type types-sros:policy-expr-string;
                                type string;
                            }
                            min-elements 1;
                            max-elements 15;
                            ordered-by user;
                            description "Policy name";
                        }

                        leaf-list apply-groups {
                            type leafref {
                                path "../../../../../../groups/group/name";
                            }
                            max-elements 8;
                            ordered-by user;
                            description "Apply a configuration group at this level";
                        }

                        leaf-list apply-groups-exclude {
                            type leafref {
                                path "../../../../../../groups/group/name";
                            }
                            max-elements 8;
                            ordered-by user;
                            description "Exclude a configuration group at this level";
                        }

                    } // container vrf-import

                    container vrf-export {
                        presence "Enable the vrf-export context";
                        description "Enable the vrf-export context";

                        leaf-list policy {
                            type union {
                                type types-sros:policy-expr-string;
                                type string;
                            }
                            min-elements 1;
                            max-elements 15;
                            ordered-by user;
                            description "Policy name";
                        }

                        leaf-list apply-groups {
                            type leafref {
                                path "../../../../../../groups/group/name";
                            }
                            max-elements 8;
                            ordered-by user;
                            description "Apply a configuration group at this level";
                        }

                        leaf-list apply-groups-exclude {
                            type leafref {
                                path "../../../../../../groups/group/name";
                            }
                            max-elements 8;
                            ordered-by user;
                            description "Exclude a configuration group at this level";
                        }

                    } // container vrf-export

                    container srv6 {
                        description "Enter the srv6 context";

                        leaf instance {
                            type leafref {
                                path "../../../../segment-routing-v6/instance";
                            }
                            sros-ext:immutable;
                            description "Segment Routing IPv6 instance";
                        }

                        leaf default-locator {
                            type string;
                            sros-ext:immutable;
                            description "Default route locator";
                        }

                    } // container srv6

                    container evpn-link-bandwidth {
                        description "Enter the evpn-link-bandwidth context";

                        leaf weighted-ecmp {
                            type boolean;
                            default "false";
                            description "Enable weighted ECMP";
                        }

                        container advertise {
                            presence "Enable the advertise context";
                            description "Enable the advertise context";

                            leaf weight {
                                type union {
                                    type uint32 {
                                        range "1..128";
                                    }
                                    type enumeration {
                                        enum dynamic                        { value 0; }
                                    }
                                }
                                default "dynamic";
                                description "Weight of the route";
                            }

                            leaf max-dynamic-weight {
                                type uint32 {
                                    range "1..128";
                                }
                                default "128";
                                description "Maximum dynamic weight of the route";
                            }

                        } // container advertise

                    } // container evpn-link-bandwidth

                } // list segment-routing-v6


            } // container bgp-evpn

            container bgp-ipvpn {
                description "Enter the bgp-ipvpn context";

                container mpls {
                    description "Enter the mpls context";

                    leaf admin-state {
                        type types-sros:admin-state;
                        default "disable";
                        description "Administrative state of BGP-IPVPN MPLS";
                    }

                    leaf route-distinguisher {
                        type types-services:vprn-bgp-evpn-mpls-rd;
                        description "Route distinguisher";
                    }

                    leaf domain-id {
                        type types-services:domain-id;
                        description "Domain ID of received BGP route before readvertisement";
                    }

                    leaf dynamic-egress-label-limit {
                        type boolean;
                        default "false";
                        description "Enables dynamic egress label limit";
                    }

                    container vrf-target {
                        description "Enter the vrf-target context";

                        choice vrf-target {
                            case vrf-both-target {

                                leaf community {
                                    type types-services:route-target;
                                    description "Extended BGP community";
                                }

                            }
                            case vrf-ovr-target {

                                leaf import-community {
                                    type types-services:route-target;
                                    description "Communities accepted from remote PE neighbors";
                                }

                                leaf export-community {
                                    type types-services:route-target;
                                    description "Communities sent to remote PE neighbors";
                                }

                            }
                        }
                    } // container vrf-target

                    container vrf-import {
                        presence "Enable the vrf-import context";
                        description "Enable the vrf-import context";

                        leaf-list policy {
                            type union {
                                type types-sros:policy-expr-string;
                                type string;
                            }
                            min-elements 1;
                            max-elements 15;
                            ordered-by user;
                            description "Policy name";
                        }

                        leaf-list apply-groups {
                            type leafref {
                                path "../../../../../../groups/group/name";
                            }
                            max-elements 8;
                            ordered-by user;
                            description "Apply a configuration group at this level";
                        }

                        leaf-list apply-groups-exclude {
                            type leafref {
                                path "../../../../../../groups/group/name";
                            }
                            max-elements 8;
                            ordered-by user;
                            description "Exclude a configuration group at this level";
                        }

                    } // container vrf-import

                    container vrf-export {
                        presence "Enable the vrf-export context";
                        description "Enable the vrf-export context";

                        leaf-list policy {
                            type union {
                                type types-sros:policy-expr-string;
                                type string;
                            }
                            min-elements 1;
                            max-elements 15;
                            ordered-by user;
                            description "Policy name";
                        }

                        leaf-list apply-groups {
                            type leafref {
                                path "../../../../../../groups/group/name";
                            }
                            max-elements 8;
                            ordered-by user;
                            description "Apply a configuration group at this level";
                        }

                        leaf-list apply-groups-exclude {
                            type leafref {
                                path "../../../../../../groups/group/name";
                            }
                            max-elements 8;
                            ordered-by user;
                            description "Exclude a configuration group at this level";
                        }

                    } // container vrf-export

                    container auto-bind-tunnel {
                        description "Enter the auto-bind-tunnel context";

                        leaf ecmp {
                            type types-router:mpls-ecmp;
                            default "1";
                            description "Maximum ECMP routes allowed";
                        }

                        leaf weighted-ecmp {
                            type boolean;
                            default "false";
                            description "Allow weighted load-balancing";
                        }

                        leaf resolution {
                            type types-services:resolve-status;
                            default "none";
                            description "Resolution method for tunnel selection";
                        }

                        leaf enforce-strict-tunnel-tagging {
                            type boolean;
                            default "false";
                            description "Allow enforcement of strict tunnel tagging";
                        }

                        leaf allow-flex-algo-fallback {
                            type boolean;
                            default "false";
                            description "Enable flexible algorithm fallback";
                        }

                        leaf-list apply-groups {
                            type leafref {
                                path "../../../../../../groups/group/name";
                            }
                            max-elements 8;
                            ordered-by user;
                            description "Apply a configuration group at this level";
                        }

                        leaf-list apply-groups-exclude {
                            type leafref {
                                path "../../../../../../groups/group/name";
                            }
                            max-elements 8;
                            ordered-by user;
                            description "Exclude a configuration group at this level";
                        }

                        container resolution-filter {
                            description "Enter the resolution-filter context";

                            leaf bgp {
                                type boolean;
                                default "true";
                                description "Use BGP tunneling for next-hop resolution";
                            }

                            leaf gre {
                                type boolean;
                                default "false";
                                description "Use GRE tunneling for next-hop resolution";
                            }

                            leaf ldp {
                                type boolean;
                                default "false";
                                description "Use LDP tunneling for next-hop resolution";
                            }

                            leaf rsvp {
                                type boolean;
                                default "false";
                                description "Use RSVP tunneling for next-hop resolution";
                            }

                            leaf sr-isis {
                                type boolean;
                                default "false";
                                description "Use IS-IS SR tunneling for next-hop resolution";
                            }

                            leaf sr-ospf {
                                type boolean;
                                default "false";
                                description "Use OSPF SR tunneling for next-hop resolution";
                            }

                            leaf sr-te {
                                type boolean;
                                default "false";
                                description "Use SR-TE tunneling for next-hop resolution";
                            }

                            leaf udp {
                                type boolean;
                                default "false";
                                description "Use MPLS over UDP tunneling for next-hop resolution";
                            }

                            leaf rib-api {
                                type boolean;
                                default "false";
                                description "Use RIB API gRPC service for next-hop resolution";
                            }

                            leaf mpls-fwd-policy {
                                type boolean;
                                default "false";
                                description "Use MPLS forwarding policy for next-hop resolution";
                            }

                            leaf sr-policy {
                                type boolean;
                                default "false";
                                description "Use SR policies for next-hop resolution";
                            }

                            leaf sr-ospf3 {
                                type boolean;
                                default "false";
                                description "Use OSPFv3 SR tunneling for next-hop resolution";
                            }

                        } // container resolution-filter

                    } // container auto-bind-tunnel

                } // container mpls

                list segment-routing-v6 {
                    key "bgp-instance";
                    description "Enter the segment-routing-v6 list instance";

                    leaf bgp-instance {
                        type int32 {
                            range "1..2";
                        }
                        description "BGP instance";
                    }

                    leaf admin-state {
                        type types-sros:admin-state;
                        default "disable";
                        description "Administrative state of segment routing over IPv6";
                    }

                    leaf route-distinguisher {
                        type types-services:vpn-rd-or-auto-rd;
                        description "Route distinguisher";
                    }

                    leaf default-route-tag {
                        type types-services:one-byte-value;
                        sros-ext:auto-restart-to-modify;
                        description "Default route tag";
                    }

                    leaf source-address {
                        type types-sros:ipv6-unicast-address;
                        sros-ext:auto-restart-to-modify;
                        description "Source IPv6 address";
                    }

                    leaf domain-id {
                        type types-services:domain-id;
                        sros-ext:auto-restart-to-modify;
                        description "Domain ID of received BGP route before readvertisement";
                    }

                    leaf resolution {
                        type types-sros:srv6-route-resolution;
                        default "route-table";
                        description "Resolution options for routes";
                    }

                    leaf-list apply-groups {
                        type leafref {
                            path "../../../../../groups/group/name";
                        }
                        max-elements 8;
                        ordered-by user;
                        description "Apply a configuration group at this level";
                    }

                    leaf-list apply-groups-exclude {
                        type leafref {
                            path "../../../../../groups/group/name";
                        }
                        max-elements 8;
                        ordered-by user;
                        description "Exclude a configuration group at this level";
                    }

                    container vrf-target {
                        description "Enter the vrf-target context";

                        choice vrf-target {
                            case vrf-both-target {

                                leaf community {
                                    type types-services:route-target;
                                    description "Extended BGP community";
                                }

                            }
                            case vrf-ovr-target {

                                leaf import-community {
                                    type types-services:route-target;
                                    description "Communities accepted from remote PE neighbors";
                                }

                                leaf export-community {
                                    type types-services:route-target;
                                    description "Communities sent to remote PE neighbors";
                                }

                            }
                        }
                    } // container vrf-target

                    container vrf-import {
                        presence "Enable the vrf-import context";
                        description "Enable the vrf-import context";

                        leaf-list policy {
                            type union {
                                type types-sros:policy-expr-string;
                                type string;
                            }
                            min-elements 1;
                            max-elements 15;
                            ordered-by user;
                            description "Policy name";
                        }

                        leaf-list apply-groups {
                            type leafref {
                                path "../../../../../../groups/group/name";
                            }
                            max-elements 8;
                            ordered-by user;
                            description "Apply a configuration group at this level";
                        }

                        leaf-list apply-groups-exclude {
                            type leafref {
                                path "../../../../../../groups/group/name";
                            }
                            max-elements 8;
                            ordered-by user;
                            description "Exclude a configuration group at this level";
                        }

                    } // container vrf-import

                    container vrf-export {
                        presence "Enable the vrf-export context";
                        description "Enable the vrf-export context";

                        leaf-list policy {
                            type union {
                                type types-sros:policy-expr-string;
                                type string;
                            }
                            min-elements 1;
                            max-elements 15;
                            ordered-by user;
                            description "Policy name";
                        }

                        leaf-list apply-groups {
                            type leafref {
                                path "../../../../../../groups/group/name";
                            }
                            max-elements 8;
                            ordered-by user;
                            description "Apply a configuration group at this level";
                        }

                        leaf-list apply-groups-exclude {
                            type leafref {
                                path "../../../../../../groups/group/name";
                            }
                            max-elements 8;
                            ordered-by user;
                            description "Exclude a configuration group at this level";
                        }

                    } // container vrf-export

                    container srv6 {
                        description "Enter the srv6 context";

                        leaf instance {
                            type leafref {
                                path "../../../../segment-routing-v6/instance";
                            }
                            sros-ext:immutable;
                            description "Segment Routing IPv6 instance";
                        }

                        leaf default-locator {
                            type string;
                            sros-ext:immutable;
                            description "Default route locator";
                        }

                    } // container srv6

                    container upa-trigger {
                        description "Enter the upa-trigger context";

                        leaf next-hop {
                            type types-bgp:upa-trigger-next-hop;
                            description "Action taken when an UPA is received for a next hop";
                        }

                    } // container upa-trigger

                } // list segment-routing-v6

                container attribute-set {
                    description "Enter the attribute-set context";

                    leaf import {
                        type types-sros:attribute-set-import;
                        default "ignore";
                        description "Reception behavior of ATTR_SET";
                    }

                    leaf export {
                        type boolean;
                        default "false";
                        description "Add ATTR_SET path attribute to exported VPN-IP routes";
                    }

                } // container attribute-set

            } // container bgp-ipvpn

            container aaa {
                description "Enter the aaa context";

                container remote-servers {
                    description "Enter the remote-servers context";

                    container tacplus {
                        presence "Enable the tacplus context";
                        description "Enable the tacplus context";

                        leaf interactive-authentication {
                            type boolean;
                            default "false";
                            description "Allows TACACS+ interactive authentication";
                        }

                        leaf admin-state {
                            type types-sros:admin-state;
                            default "enable";
                            description "Administrative state of the TACACS+ protocol";
                        }

                        leaf server-timeout {
                            type types-sros:time-duration {
                                range "1..90";
                            }
                            units "seconds";
                            default "3";
                            description "Time to wait for a response from the TACACS+ server";
                        }

                        leaf use-default-template {
                            type boolean;
                            default "true";
                            description "Apply TACACS+ default user-template to TACACS+ user";
                        }

                        leaf-list apply-groups {
                            type leafref {
                                path "../../../../../../groups/group/name";
                            }
                            max-elements 8;
                            ordered-by user;
                            description "Apply a configuration group at this level";
                        }

                        leaf-list apply-groups-exclude {
                            type leafref {
                                path "../../../../../../groups/group/name";
                            }
                            max-elements 8;
                            ordered-by user;
                            description "Exclude a configuration group at this level";
                        }

                        container accounting {
                            presence "Enable the accounting context";
                            description "Enable the accounting context";

                            leaf record-type {
                                type enumeration {
                                    enum start-stop                     { value 1; }
                                    enum stop-only                      { value 2; }
                                }
                                default "stop-only";
                                description "Type of accounting record packet sent to TACACS+ server";
                            }

                        } // container accounting

                        container authorization {
                            presence "Enable the authorization context";
                            description "Enable the authorization context";

                            leaf use-priv-lvl {
                                type boolean;
                                default "false";
                                description "Allow privilege level mapping";
                            }

                            container request-format {
                                description "Enter the request-format context";

                                leaf-list access-operation-cmd {
                                    type enumeration {
                                        enum delete                         { value 1; }
                                    }
                                    max-elements 1;
                                    description "Access operations sent in authorization requests";
                                }

                            } // container request-format

                        } // container authorization

                        container priv-lvl-map {
                            description "Enter the priv-lvl-map context";

                            list priv-lvl {
                                key "level";
                                description "Enter the priv-lvl list instance";

                                leaf level {
                                    type uint32 {
                                        range "0..15";
                                    }
                                    description "Privilege level for the mapping";
                                }

                                leaf user-profile-name {
                                    type leafref {
                                        path "../../../../../../../../system/security/aaa/local-profiles/profile/user-profile-name";
                                    }
                                    mandatory true;
                                    description "User profile for the mapping";
                                }

                                leaf-list apply-groups {
                                    type leafref {
                                        path "../../../../../../../../groups/group/name";
                                    }
                                    max-elements 8;
                                    ordered-by user;
                                    description "Apply a configuration group at this level";
                                }

                                leaf-list apply-groups-exclude {
                                    type leafref {
                                        path "../../../../../../../../groups/group/name";
                                    }
                                    max-elements 8;
                                    ordered-by user;
                                    description "Exclude a configuration group at this level";
                                }

                            } // list priv-lvl

                        } // container priv-lvl-map

                        list server {
                            key "index";
                            max-elements 5;
                            description "Enter the server list instance";

                            leaf index {
                                type uint32 {
                                    range "1..5";
                                }
                                description "TACACS+ server ID";
                            }

                            leaf address {
                                type types-sros:ip-unicast-address;
                                mandatory true;
                                description "IP address of the TACACS+ server";
                            }

                            leaf port {
                                type types-qos:tcp-udp-match-port;
                                default "49";
                                description "TCP port ID on which to contact TACACS+ server";
                            }

                            leaf secret {
                                type types-sros:encrypted-leaf {
                                    length "1..199";
                                }
                                mandatory true;
                                description "Secret key to access the TACACS+ server";
                            }

                            leaf-list apply-groups {
                                type leafref {
                                    path "../../../../../../../groups/group/name";
                                }
                                max-elements 8;
                                ordered-by user;
                                description "Apply a configuration group at this level";
                            }

                            leaf-list apply-groups-exclude {
                                type leafref {
                                    path "../../../../../../../groups/group/name";
                                }
                                max-elements 8;
                                ordered-by user;
                                description "Exclude a configuration group at this level";
                            }

                        } // list server

                    } // container tacplus

                    container radius {
                        presence "Enable the radius context";
                        description "Enable the radius context";

                        leaf admin-state {
                            type types-sros:admin-state;
                            default "enable";
                            description "Administrative state of the authentication server";
                        }

                        leaf accounting {
                            type boolean;
                            default "false";
                            description "Enable RADIUS command accounting";
                        }

                        leaf accounting-port {
                            type uint32 {
                                range "1..65535";
                            }
                            default "1813";
                            description "Port number on RADIUS server for accounting requests";
                        }

                        leaf authorization {
                            type boolean;
                            default "false";
                            description "Enable RADIUS authorization";
                        }

                        leaf interactive-authentication {
                            type boolean;
                            default "false";
                            description "Enable RADIUS interactive authentication";
                        }

                        leaf server-retry {
                            type uint32 {
                                range "1..10";
                            }
                            default "3";
                            description "Number of attempts to retry contacting RADIUS server";
                        }

                        leaf server-timeout {
                            type uint32 {
                                range "1..90";
                            }
                            units "seconds";
                            default "3";
                            description "Time to wait for a response from the RADIUS server";
                        }

                        leaf port {
                            type uint32 {
                                range "1..65535";
                            }
                            default "1812";
                            description "UDP port number on which to contact RADIUS server";
                        }

                        leaf use-default-template {
                            type boolean;
                            default "false";
                            description "Apply the RADIUS default user template to RADIUS user";
                        }

                        leaf access-algorithm {
                            type enumeration {
                                enum direct                         { value 1; }
                                enum round-robin                    { value 2; }
                            }
                            default "direct";
                            description "Algorithm used to access the set of RADIUS servers";
                        }

                        leaf-list apply-groups {
                            type leafref {
                                path "../../../../../../groups/group/name";
                            }
                            max-elements 8;
                            ordered-by user;
                            description "Apply a configuration group at this level";
                        }

                        leaf-list apply-groups-exclude {
                            type leafref {
                                path "../../../../../../groups/group/name";
                            }
                            max-elements 8;
                            ordered-by user;
                            description "Exclude a configuration group at this level";
                        }

                        list server {
                            key "index";
                            max-elements 5;
                            description "Enter the server list instance";

                            leaf index {
                                type uint32 {
                                    range "1..5";
                                }
                                description "RADIUS server ID";
                            }

                            leaf address {
                                type types-sros:ip-unicast-address;
                                mandatory true;
                                description "IP address of the RADIUS server";
                            }

                            leaf authenticator {
                                type enumeration {
                                    enum md5                            { value 1; }
                                    enum sm3                            { value 2; }
                                }
                                default "md5";
                                description "Authenticator hash algorithm for the RADIUS server";
                            }

                            leaf secret {
                                type types-sros:encrypted-leaf {
                                    length "1..115";
                                }
                                description "Secret key to access the RADIUS server";
                            }

                            leaf tls-client-profile {
                                type leafref {
                                    path "../../../../../../../system/security/tls/client-tls-profile/client-profile-name";
                                }
                                description "TLS client profile for the RADIUS server";
                            }

                            leaf-list apply-groups {
                                type leafref {
                                    path "../../../../../../../groups/group/name";
                                }
                                max-elements 8;
                                ordered-by user;
                                description "Apply a configuration group at this level";
                            }

                            leaf-list apply-groups-exclude {
                                type leafref {
                                    path "../../../../../../../groups/group/name";
                                }
                                max-elements 8;
                                ordered-by user;
                                description "Exclude a configuration group at this level";
                            }

                        } // list server

                    } // container radius

                } // container remote-servers

            } // container aaa

            container aggregates {
                description "Enter the aggregates context";

                leaf-list apply-groups {
                    type leafref {
                        path "../../../../groups/group/name";
                    }
                    max-elements 8;
                    ordered-by user;
                    description "Apply a configuration group at this level";
                }

                leaf-list apply-groups-exclude {
                    type leafref {
                        path "../../../../groups/group/name";
                    }
                    max-elements 8;
                    ordered-by user;
                    description "Exclude a configuration group at this level";
                }

                list aggregate {
                    key "ip-prefix";
                    description "Enter the aggregate list instance";

                    leaf ip-prefix {
                        type types-sros:ip-unicast-prefix;
                        description "Destination IP address prefix of the aggregate route";
                    }

                    leaf as-set {
                        type boolean;
                        default "false";
                        description "Use AS_SET path segment type for the aggregate route";
                    }

                    leaf-list community {
                        type types-sros:community;
                        max-elements 12;
                        ordered-by user;
                        description "Community name that is added to the aggregate route";
                    }

                    leaf description {
                        type types-sros:description;
                        description "Text description";
                    }

                    leaf summary-only {
                        type boolean;
                        default "false";
                        description "Advertise the aggregate route only";
                    }

                    leaf local-preference {
                        type int64 {
                            range "0..4294967295";
                        }
                        description "Local preference used when aggregate route is exported";
                    }

                    leaf discard-component-communities {
                        type boolean;
                        default "false";
                        description "Advertise aggregate with aggregate route community set";
                    }

                    leaf policy {
                        type leafref {
                            path "../../../../../policy-options/policy-statement/name";
                        }
                        description "Policy name for the aggregated route";
                    }

                    leaf tunnel-group {
                        type types-redundancy:tunnel-group-id;
                        description "Tunnel group from which to associate the MC IPSec state";
                    }

                    leaf-list apply-groups {
                        type leafref {
                            path "../../../../../groups/group/name";
                        }
                        max-elements 8;
                        ordered-by user;
                        description "Apply a configuration group at this level";
                    }

                    leaf-list apply-groups-exclude {
                        type leafref {
                            path "../../../../../groups/group/name";
                        }
                        max-elements 8;
                        ordered-by user;
                        description "Exclude a configuration group at this level";
                    }

                    choice next-hop {
                        case blackhole {

                            container blackhole {
                                presence "Enable the blackhole context";
                                description "Enable the blackhole context";

                                leaf generate-icmp {
                                    type boolean;
                                    default "false";
                                    description "Send ICMP unreachable messages for aggregate routes";
                                }

                            } // container blackhole

                        }
                        case indirect {

                            leaf indirect {
                                type types-sros:ip-unicast-address;
                                sros-ext:immutable;
                                description "Address of the indirect next hop";
                            }

                        }
                    }
                    container aggregator {
                        description "Enter the aggregator context";

                        leaf as-number {
                            type uint32 {
                                range "1..max";
                            }
                            description "Aggregator AS number";
                        }

                        leaf address {
                            type types-sros:ipv4-unicast-address;
                            description "Aggregator IP address";
                        }

                    } // container aggregator

                } // list aggregate

            } // container aggregates

            container subscriber-mgmt {
                description "Enter the subscriber-mgmt context";

                leaf multi-chassis-shunt-id {
                    type uint32 {
                        range "1..8191";
                    }
                    description "Shunt ID for a pair of resilient nodes";
                }

                leaf-list apply-groups {
                    type leafref {
                        path "../../../../groups/group/name";
                    }
                    max-elements 8;
                    ordered-by user;
                    description "Apply a configuration group at this level";
                }

                leaf-list apply-groups-exclude {
                    type leafref {
                        path "../../../../groups/group/name";
                    }
                    max-elements 8;
                    ordered-by user;
                    description "Exclude a configuration group at this level";
                }

                container up-resiliency {
                    description "Enter the up-resiliency context";

                    list monitor-oper-group {
                        key "oper-group";
                        max-elements 2;
                        description "Enter the monitor-oper-group list instance";

                        leaf oper-group {
                            type leafref {
                                path "../../../../../oper-group/name";
                            }
                            description "Operational group name";
                        }

                        leaf health-drop {
                            type uint32 {
                                range "1..100";
                            }
                            default "1";
                            description "Number subtracted from the health value per failure";
                        }

                        leaf-list apply-groups {
                            type leafref {
                                path "../../../../../../groups/group/name";
                            }
                            max-elements 8;
                            ordered-by user;
                            description "Apply a configuration group at this level";
                        }

                        leaf-list apply-groups-exclude {
                            type leafref {
                                path "../../../../../../groups/group/name";
                            }
                            max-elements 8;
                            ordered-by user;
                            description "Exclude a configuration group at this level";
                        }

                    } // list monitor-oper-group

                } // container up-resiliency

                container dhcpv4 {
                    description "Enter the dhcpv4 context";

                    leaf routed-subnet-transparent-forward {
                        type boolean;
                        default "false";
                        description "Transparently forward DHCPv4 from CPE LAN over IPoE";
                    }

                    leaf-list apply-groups {
                        type leafref {
                            path "../../../../../groups/group/name";
                        }
                        max-elements 8;
                        ordered-by user;
                        description "Apply a configuration group at this level";
                    }

                    leaf-list apply-groups-exclude {
                        type leafref {
                            path "../../../../../groups/group/name";
                        }
                        max-elements 8;
                        ordered-by user;
                        description "Exclude a configuration group at this level";
                    }

                } // container dhcpv4

            } // container subscriber-mgmt


            container wlan-gw {
                presence "Enable the wlan-gw context";
                description "Enable the wlan-gw context";

                leaf-list apply-groups {
                    type leafref {
                        path "../../../../groups/group/name";
                    }
                    max-elements 8;
                    ordered-by user;
                    description "Apply a configuration group at this level";
                }

                leaf-list apply-groups-exclude {
                    type leafref {
                        path "../../../../groups/group/name";
                    }
                    max-elements 8;
                    ordered-by user;
                    description "Exclude a configuration group at this level";
                }

                container mobility-triggered-accounting {
                    description "Enter the mobility-triggered-accounting context";

                    leaf admin-state {
                        type types-sros:admin-state;
                        default "disable";
                        description "Administrative state of mobility triggered accounting";
                    }

                    leaf include-counters {
                        type boolean;
                        default "false";
                        description "Include counters in interim updates";
                    }

                    leaf hold-down {
                        type types-sros:time-duration {
                            range "60..86400";
                        }
                        units "seconds";
                        description "Hold additional mobility-triggered update until this timer expires";
                    }

                } // container mobility-triggered-accounting

                container distributed-subscriber-mgmt {
                    description "Enter the distributed-subscriber-mgmt context";

                    leaf ipv6-tcp-mss-adjust {
                        type uint32 {
                            range "160..10240";
                        }
                        description "TCP-MSS adjustment value in upstream direction for DSM";
                    }

                    leaf-list apply-groups {
                        type leafref {
                            path "../../../../../groups/group/name";
                        }
                        max-elements 8;
                        ordered-by user;
                        description "Apply a configuration group at this level";
                    }

                    leaf-list apply-groups-exclude {
                        type leafref {
                            path "../../../../../groups/group/name";
                        }
                        max-elements 8;
                        ordered-by user;
                        description "Exclude a configuration group at this level";
                    }


                } // container distributed-subscriber-mgmt

                container xconnect {
                    description "Enter the xconnect context";

                    leaf admin-state {
                        type types-sros:admin-state;
                        default "disable";
                        description "Administrative state of the WLAN-GW cross-connect";
                    }

                    leaf tunnel-source-ip {
                        type types-sros:ipv6-prefix;
                        sros-ext:auto-restart-to-modify;
                        description "IPv6 address and prefix for the tunnel source";
                    }

                    leaf wlan-gw-group {
                        type leafref {
                            path "../../../../../isa/wlan-gw-group/id";
                        }
                        sros-ext:auto-restart-to-modify;
                        description "ISA WLAN-GW Group";
                    }

                    leaf-list apply-groups {
                        type leafref {
                            path "../../../../../groups/group/name";
                        }
                        max-elements 8;
                        ordered-by user;
                        description "Apply a configuration group at this level";
                    }

                    leaf-list apply-groups-exclude {
                        type leafref {
                            path "../../../../../groups/group/name";
                        }
                        max-elements 8;
                        ordered-by user;
                        description "Exclude a configuration group at this level";
                    }

                } // container xconnect

            } // container wlan-gw

            container auto-bind-tunnel {
                status obsolete;
                description "Enter the auto-bind-tunnel context";

                leaf ecmp {
                    status obsolete;
                    type types-router:mpls-ecmp;
                    default "1";
                    description "Maximum ECMP routes allowed";
                }

                leaf weighted-ecmp {
                    status obsolete;
                    type boolean;
                    default "false";
                    description "Allow weighted load-balancing";
                }

                leaf resolution {
                    status obsolete;
                    type types-services:resolve-status;
                    default "none";
                    description "Resolution method for tunnel selection";
                }

                leaf enforce-strict-tunnel-tagging {
                    status obsolete;
                    type boolean;
                    default "false";
                    description "Allow enforcement of strict tunnel tagging";
                }

                leaf allow-flex-algo-fallback {
                    status obsolete;
                    type boolean;
                    default "false";
                    description "Enable flexible algorithm fallback";
                }

                leaf-list apply-groups {
                    status obsolete;
                    type leafref {
                        path "../../../../groups/group/name";
                    }
                    max-elements 8;
                    ordered-by user;
                    description "Apply a configuration group at this level";
                }

                leaf-list apply-groups-exclude {
                    status obsolete;
                    type leafref {
                        path "../../../../groups/group/name";
                    }
                    max-elements 8;
                    ordered-by user;
                    description "Exclude a configuration group at this level";
                }

                container resolution-filter {
                    status obsolete;
                    description "Enter the resolution-filter context";

                    leaf bgp {
                        status obsolete;
                        type boolean;
                        default "true";
                        description "Use BGP tunneling for next-hop resolution";
                    }

                    leaf gre {
                        status obsolete;
                        type boolean;
                        default "false";
                        description "Use GRE tunneling for next-hop resolution";
                    }

                    leaf ldp {
                        status obsolete;
                        type boolean;
                        default "false";
                        description "Use LDP tunneling for next-hop resolution";
                    }

                    leaf rsvp {
                        status obsolete;
                        type boolean;
                        default "false";
                        description "Use RSVP tunneling for next-hop resolution";
                    }

                    leaf sr-isis {
                        status obsolete;
                        type boolean;
                        default "false";
                        description "Use IS-IS SR tunneling for next-hop resolution";
                    }

                    leaf sr-ospf {
                        status obsolete;
                        type boolean;
                        default "false";
                        description "Use OSPF SR tunneling for next-hop resolution";
                    }

                    leaf sr-te {
                        status obsolete;
                        type boolean;
                        default "false";
                        description "Use SR-TE tunneling for next-hop resolution";
                    }

                    leaf udp {
                        status obsolete;
                        type boolean;
                        default "false";
                        description "Use MPLS over UDP tunneling for next-hop resolution";
                    }

                    leaf rib-api {
                        status obsolete;
                        type boolean;
                        default "false";
                        description "Use RIB API gRPC service for next-hop resolution";
                    }

                    leaf mpls-fwd-policy {
                        status obsolete;
                        type boolean;
                        default "false";
                        description "Use MPLS forwarding policy for next-hop resolution";
                    }

                    leaf sr-policy {
                        status obsolete;
                        type boolean;
                        default "false";
                        description "Use SR policies for next-hop resolution";
                    }

                    leaf sr-ospf3 {
                        status obsolete;
                        type boolean;
                        default "false";
                        description "Use OSPFv3 SR tunneling for next-hop resolution";
                    }

                } // container resolution-filter

            } // container auto-bind-tunnel

            container dns {
                presence "Enable the dns context";
                description "Enable the dns context";

                leaf admin-state {
                    type types-sros:admin-state;
                    default "disable";
                    description "Administrative state of DNS";
                }

                leaf-list server {
                    type types-sros:ip-unicast-address;
                    max-elements 3;
                    ordered-by user;
                    description "DNS server used for DNS name resolution";
                }

                leaf ipv4-source-address {
                    type union {
                        type enumeration {
                            enum use-interface-ip               { value 0; }
                        }
                        type types-sros:ipv4-unicast-address;
                    }
                    default "use-interface-ip";
                    description "Source address to contact an IPv4 DNS server";
                }

                leaf ipv6-source-address {
                    type union {
                        type enumeration {
                            enum use-interface-ip               { value 0; }
                        }
                        type types-sros:ipv6-unicast-address;
                    }
                    default "use-interface-ip";
                    description "Source address to contact an IPv6 DNS server";
                }

                leaf default-domain {
                    type types-sros:fully-qualified-domain-name {
                        pattern "[a-z0-9\\-\\.]+";
                    }
                    description "Domain name added in DNS retries";
                }

                leaf-list apply-groups {
                    type leafref {
                        path "../../../../groups/group/name";
                    }
                    max-elements 8;
                    ordered-by user;
                    description "Apply a configuration group at this level";
                }

                leaf-list apply-groups-exclude {
                    type leafref {
                        path "../../../../groups/group/name";
                    }
                    max-elements 8;
                    ordered-by user;
                    description "Exclude a configuration group at this level";
                }

            } // container dns

            container bgp {
                presence "Enable the bgp context";
                description "Enable the bgp context";

                leaf description {
                    type types-sros:description;
                    description "Text description";
                }

                leaf connect-retry {
                    type int32 {
                        range "1..65535";
                    }
                    default "120";
                    description "BGP connect retry timer value";
                }

                leaf admin-state {
                    type types-sros:admin-state;
                    default "enable";
                    description "Administrative state of the BGP instance";
                }

                leaf keepalive {
                    type int32 {
                        range "0..21845";
                    }
                    default "30";
                    description "Time after which the BGP KEEPALIVE message is sent";
                }

                leaf damping {
                    type boolean;
                    default "false";
                    description "Use BGP route damping to reduce route flap";
                }

                leaf local-preference {
                    type uint32;
                    default "100";
                    description "Default local preference if not in incoming routes";
                }

                leaf loop-detect {
                    type types-bgp:loop-detect;
                    default "ignore-loop";
                    description "Strategy for loop detection in the AS path";
                }

                leaf loop-detect-threshold {
                    type uint32 {
                        range "0..15";
                    }
                    default "0";
                    description "Threshold for the global ASN in a received AS path";
                }

                leaf tcp-mss {
                    type uint32 {
                        range "384..9746";
                    }
                    description "TCP maximum segment size override";
                }

                leaf min-route-advertisement {
                    type int16 {
                        range "1..255";
                    }
                    default "30";
                    description "Minimum time before a prefix can be advertised to peer";
                }

                leaf aggregator-id-zero {
                    type boolean;
                    default "false";
                    description "Set router ID in the BGP AGGREGATOR attribute to 0";
                }

                leaf preference {
                    type uint32 {
                        range "1..255";
                    }
                    default "170";
                    description "Route preference for routes learned from all peers";
                }

                leaf multihop {
                    type int32 {
                        range "1..255";
                    }
                    description "TTL in IP packet headers for EBGP peers multi-hops away";
                }

                leaf med-out {
                    type union {
                        type uint32;
                        type enumeration {
                            enum igp-cost                       { value -1; }
                        }
                    }
                    description "Default MED attribute value to advertise to peers";
                }

                leaf authentication-key {
                    type types-sros:encrypted-leaf {
                        length "1..370";
                    }
                    description "BGP authentication key for all peers";
                }

                leaf client-reflect {
                    type boolean;
                    default "true";
                    description "Allow client reflection of routes by route reflector";
                }

                leaf asn-4-byte {
                    type boolean;
                    default "true";
                    description "Advertise support for 4-byte ASNs";
                }

                leaf eibgp-loadbalance {
                    type boolean;
                    default "false";
                    description "Use ECMP over BGP VPN and BGP routes";
                }

                leaf path-mtu-discovery {
                    type boolean;
                    default "false";
                    description "Enable Path MTU Discovery";
                }

                leaf enforce-first-as {
                    type boolean;
                    default "false";
                    description "Enforce the configured peer AS value in received routes";
                }

                leaf initial-send-delay-zero {
                    type boolean;
                    default "false";
                    description "Send BGP updates as soon as session comes up";
                }

                leaf router-id {
                    type types-sros:ipv4-address;
                    description "Router ID for the BGP instance in the AS";
                }

                leaf ibgp-multipath {
                    type boolean;
                    default "false";
                    description "Enable IBGP multipath load balancing";
                }

                leaf bfd-liveness {
                    type boolean;
                    default "false";
                    description "Enable BFD";
                }

                leaf fast-external-failover {
                    type boolean;
                    default "true";
                    description "Drop external BGP session immediately when link fails";
                }

                leaf advertise-inactive {
                    type boolean;
                    default "false";
                    description "Advertise inactive BGP routes to peers";
                }

                leaf authentication-keychain {
                    type leafref {
                        path "../../../../system/security/keychains/keychain/keychain-name";
                    }
                    description "TCP authentication keychain for the session";
                }

                leaf rapid-withdrawal {
                    type boolean;
                    default "false";
                    description "Send BGP withdrawal UPDATE messages immediately";
                }

                leaf peer-ip-tracking {
                    type boolean;
                    default "false";
                    description "Enable BGP peer tracking";
                }

                leaf split-horizon {
                    type boolean;
                    default "false";
                    description "Prevent routes being reflected back to best-route peer";
                }

                leaf third-party-nexthop {
                    type boolean;
                    default "false";
                    description "Apply third-party next-hop processing to EBGP peers";
                }

                leaf dynamic-neighbor-limit {
                    type uint32 {
                        range "1..8192";
                    }
                    description "Max dynamic BGP sessions to accept from remote peers";
                }

                leaf label-preference {
                    type uint32 {
                        range "1..255";
                    }
                    default "170";
                    description "Route preference for routes from labeled-unicast peers";
                }

                leaf peer-tracking-policy {
                    type leafref {
                        path "../../../../policy-options/policy-statement/name";
                    }
                    description "Policy for BGP peer tracking on router instance";
                }

                leaf domain-id {
                    type types-services:domain-id;
                    description "Domain ID of received BGP route before readvertisement";
                }

                leaf-list apply-groups {
                    type leafref {
                        path "../../../../groups/group/name";
                    }
                    max-elements 8;
                    ordered-by user;
                    description "Apply a configuration group at this level";
                }

                leaf-list apply-groups-exclude {
                    type leafref {
                        path "../../../../groups/group/name";
                    }
                    max-elements 8;
                    ordered-by user;
                    description "Exclude a configuration group at this level";
                }

                container hold-time {
                    description "Enter the hold-time context";

                    leaf seconds {
                        type int32 {
                            range "0|3..65535";
                        }
                        default "90";
                        description "Maximum time BGP waits between successive messages";
                    }

                    leaf minimum-hold-time {
                        type int32 {
                            range "0|3..65535";
                        }
                        default "0";
                        description "Minimum hold time between successive messages";
                    }

                } // container hold-time

                container family {
                    description "Enter the family context";

                    leaf ipv4 {
                        type boolean;
                        default "true";
                        description "Advertise MP-BGP support for the IPv4 address family";
                    }

                    leaf ipv6 {
                        type boolean;
                        default "false";
                        description "Advertise MP-BGP support for the IPv6 address family";
                    }

                    leaf mcast-ipv4 {
                        type boolean;
                        default "false";
                        description "Advertise support for the MCAST-IPv4 address family";
                    }

                    leaf flow-ipv4 {
                        type boolean;
                        default "false";
                        description "Advertise support for the FlowSpec-IPv4 address family";
                    }

                    leaf flow-ipv6 {
                        type boolean;
                        default "false";
                        description "Advertise support for the FlowSpec-IPv6 address family";
                    }

                    leaf mcast-ipv6 {
                        type boolean;
                        default "false";
                        description "Advertise support for the MCAST-IPv6 address family";
                    }

                    leaf label-ipv4 {
                        type boolean;
                        default "false";
                        description "Advertise support for the label-IPv4 address family";
                    }

                } // container family

                container send-default {
                    description "Enter the send-default context";

                    leaf ipv4 {
                        type boolean;
                        default "false";
                        description "Enable IPv4 family type";
                    }

                    leaf ipv6 {
                        type boolean;
                        default "false";
                        description "Enable IPv6 family type";
                    }

                    leaf export-policy {
                        type leafref {
                            path "../../../../../policy-options/policy-statement/name";
                        }
                        description "Export policy name";
                    }

                } // container send-default

                container default-preference {
                    description "Enter the default-preference context";

                    leaf ebgp {
                        type uint32 {
                            range "0..255";
                        }
                        default "0";
                        description "Default preference for EBGP";
                    }

                    leaf ibgp {
                        type uint32 {
                            range "0..255";
                        }
                        default "0";
                        description "Default preference for IBGP";
                    }

                } // container default-preference

                container default-label-preference {
                    description "Enter the default-label-preference context";

                    leaf ebgp {
                        type uint32 {
                            range "0..255";
                        }
                        default "0";
                        description "Default preference for EBGP";
                    }

                    leaf ibgp {
                        type uint32 {
                            range "0..255";
                        }
                        default "0";
                        description "Default preference for IBGP";
                    }

                } // container default-label-preference

                container remove-private {
                    presence "Enable the remove-private context";
                    description "Enable the remove-private context";

                    leaf limited {
                        type boolean;
                        default "false";
                        description "Remove private ASNs up to first public ASN encountered";
                    }

                    leaf skip-peer-as {
                        type boolean;
                        default "false";
                        description "Keep private ASN if AS-PATH contains eBGP peer's ASN";
                    }

                    leaf replace {
                        type boolean;
                        default "false";
                        description "Replace private ASN with global ASN before advertising";
                    }

                } // container remove-private

                container cluster {
                    description "Enter the cluster context";

                    leaf cluster-id {
                        type types-sros:ipv4-address;
                        description "Route reflector cluster ID";
                    }

                } // container cluster

                container ebgp-default-reject-policy {
                    description "Enter the ebgp-default-reject-policy context";

                    leaf import {
                        type boolean;
                        default "true";
                        description "Enable default reject import policy for external peers";
                    }

                    leaf export {
                        type boolean;
                        default "true";
                        description "Enable default reject export policy for external peers";
                    }

                } // container ebgp-default-reject-policy

                container bfd-strict-mode {
                    description "Enter the bfd-strict-mode context";

                    leaf next-hop-reachability {
                        type boolean;
                        default "false";
                        description "Consider next hop unreachable if BFD session is down";
                    }

                    container advertise {
                        presence "Enable the advertise context";
                        description "Enable the advertise context";

                        leaf holdtime {
                            type uint16 {
                                range "1..65535";
                            }
                            units "seconds";
                            default "30";
                            description "Maximum time BGP waits for the BFD session to come up";
                        }

                    } // container advertise

                } // container bfd-strict-mode

                container attribute-set {
                    description "Enter the attribute-set context";

                    leaf remove {
                        type boolean;
                        default "false";
                        description "Remove ATTR_SET in received BGP routes from PE-CE peers";
                    }

                } // container attribute-set

                container local-as {
                    description "Enter the local-as context";

                    leaf as-number {
                        type uint32 {
                            range "1..4294967295";
                        }
                        description "Local (or virtual) BGP AS number";
                    }

                    leaf private {
                        type boolean;
                        default "false";
                        description "Hide the local ASN in sent paths learned from peering";
                    }

                    leaf prepend-global-as {
                        type boolean;
                        default "true";
                        description "Prepend global AS when advertising routes to BGP peer";
                    }

                } // container local-as

                container best-path-selection {
                    description "Enter the best-path-selection context";

                    leaf compare-origin-validation-state {
                        type boolean;
                        default "false";
                        description "Allow comparison of origin validation states";
                    }

                    leaf deterministic-med {
                        type boolean;
                        default "false";
                        description "Group paths based on AS before MED attribute comparison";
                    }

                    leaf origin-invalid-unusable {
                        type boolean;
                        default "false";
                        description "Ignore routes with invalid origin validation state";
                    }

                    leaf ignore-nh-metric {
                        type boolean;
                        default "false";
                        description "Ignore next-hop distance in best path selection";
                    }

                    leaf d-path-length-ignore {
                        type boolean;
                        default "false";
                        description "Enable D-PATH length ignore";
                    }

                    container always-compare-med {
                        description "Enter the always-compare-med context";

                        leaf med-value {
                            type types-bgp:med-value;
                            default "off";
                            description "Action for a missing MED attribute";
                        }

                        leaf strict-as {
                            type boolean;
                            default "true";
                            description "Compare MED only for routes from same neighbor AS";
                        }

                    } // container always-compare-med

                    container as-path-ignore {
                        description "Enter the as-path-ignore context";

                        leaf ipv4 {
                            type boolean;
                            default "false";
                            description "Ignore AS path length for unlabeled unicast IPv4 routes";
                        }

                        leaf ipv6 {
                            type boolean;
                            default "false";
                            description "Ignore AS path length for unlabeled unicast IPv6 routes";
                        }

                        leaf label-ipv4 {
                            type boolean;
                            default "false";
                            description "Ignore AS path length for labeled-unicast IPv4 routes";
                        }

                        leaf label-ipv6 {
                            type boolean;
                            default "false";
                            description "Ignore AS path length for labeled unicast IPv6 routes";
                        }

                    } // container as-path-ignore

                    container ignore-router-id {
                        presence "Enable the ignore-router-id context";
                        description "Enable the ignore-router-id context";

                    } // container ignore-router-id

                    container ebgp-ibgp-equal {
                        description "Enter the ebgp-ibgp-equal context";

                        leaf ipv4 {
                            type boolean;
                            default "false";
                            description "Consider EBGP and IBGP IPv4 routes equal";
                        }

                        leaf ipv6 {
                            type boolean;
                            default "false";
                            description "Consider EBGP and IBGP IPv6 routes equal";
                        }

                        leaf label-ipv4 {
                            type boolean;
                            default "false";
                            description "Consider EBGP and IBGP label-IPv4 routes equal";
                        }

                        leaf label-ipv6 {
                            type boolean;
                            default "false";
                            description "Consider EBGP and IBGP label-IPv6 routes equal";
                        }

                    } // container ebgp-ibgp-equal

                } // container best-path-selection

                container send-communities {
                    description "Enter the send-communities context";

                    leaf standard {
                        type boolean;
                        default "true";
                        description "Advertise the Communities attribute to peers";
                    }

                    leaf extended {
                        type boolean;
                        default "true";
                        description "Advertise the Extended Communities attribute to peers";
                    }

                    leaf large {
                        type boolean;
                        default "true";
                        description "Advertise the Large Communities attribute to peers";
                    }

                } // container send-communities

                container error-handling {
                    description "Enter the error-handling context";

                    leaf update-fault-tolerance {
                        type boolean;
                        default "false";
                        description "Tolerate non-critical errors in UPDATE messages";
                    }

                    leaf legacy-mode {
                        type boolean;
                        default "false";
                        description "Enable legacy-mode of BGP error handling";
                    }

                } // container error-handling

                container damp-peer-oscillations {
                    presence "Enable the damp-peer-oscillations context";
                    description "Enable the damp-peer-oscillations context";

                    leaf error-interval {
                        type uint32 {
                            range "0..2048";
                        }
                        default "30";
                        description "Time after a reset that the session must be error-free";
                    }

                    container idle-hold-time {
                        description "Enter the idle-hold-time context";

                        leaf initial-wait {
                            type uint32 {
                                range "0..2048";
                            }
                            default "0";
                            description "Time session remains in idle state after stabilization";
                        }

                        leaf second-wait {
                            type uint32 {
                                range "1..2048";
                            }
                            default "5";
                            description "Time that doubles after each session failure";
                        }

                        leaf max-wait {
                            type uint32 {
                                range "1..2048";
                            }
                            default "60";
                            description "Maximum session idle time after repeated instability";
                        }

                    } // container idle-hold-time

                } // container damp-peer-oscillations

                container backup-path {
                    description "Enter the backup-path context";

                    leaf ipv4 {
                        type boolean;
                        default "false";
                        description "Enable support for unlabeled unicast IPv4 routes";
                    }

                    leaf ipv6 {
                        type boolean;
                        default "false";
                        description "Enable support for unlabeled unicast IPv6 routes";
                    }

                    leaf label-ipv4 {
                        type boolean;
                        default "false";
                        description "Enable support for labeled-unicast IPv4 routes";
                    }

                    leaf label-ipv6 {
                        type boolean;
                        default "false";
                        description "Enable support for labeled unicast IPv6 routes";
                    }

                } // container backup-path

                container flowspec {
                    description "Enter the flowspec context";

                    leaf validate-dest-prefix {
                        type boolean;
                        default "false";
                        description "Validate destination prefix in FlowSpec-IPv4/IPv6 route";
                    }

                    leaf validate-redirect-ip {
                        type boolean;
                        default "false";
                        description "Validate the redirect-to-IPv4 action in FlowSpec route";
                    }

                } // container flowspec

                container convergence {
                    description "Enter the convergence context";

                    leaf min-wait-to-advertise {
                        type uint32 {
                            range "0..3600";
                        }
                        default "0";
                        description "Minimum wait time before advertising routes";
                    }

                    list family {
                        key "family-type";
                        description "Enter the family list instance";

                        leaf family-type {
                            type enumeration {
                                enum ipv4                           { value 1; }
                                enum ipv6                           { value 3; }
                            }
                            description "Address family for which convergence selection applies";
                        }

                        leaf max-wait-to-advertise {
                            type uint32 {
                                range "0..3600";
                            }
                            default "0";
                            description "Maximum wait time before advertising routes";
                        }

                        leaf-list apply-groups {
                            type leafref {
                                path "../../../../../../groups/group/name";
                            }
                            max-elements 8;
                            ordered-by user;
                            description "Apply a configuration group at this level";
                        }

                        leaf-list apply-groups-exclude {
                            type leafref {
                                path "../../../../../../groups/group/name";
                            }
                            max-elements 8;
                            ordered-by user;
                            description "Exclude a configuration group at this level";
                        }

                    } // list family

                } // container convergence

                container import {
                    presence "Enable the import context";
                    description "Enable the import context";

                    leaf-list policy {
                        type union {
                            type types-sros:policy-expr-string;
                            type string;
                        }
                        min-elements 1;
                        max-elements 15;
                        ordered-by user;
                        description "Import policy name";
                    }

                    leaf-list apply-groups {
                        type leafref {
                            path "../../../../../groups/group/name";
                        }
                        max-elements 8;
                        ordered-by user;
                        description "Apply a configuration group at this level";
                    }

                    leaf-list apply-groups-exclude {
                        type leafref {
                            path "../../../../../groups/group/name";
                        }
                        max-elements 8;
                        ordered-by user;
                        description "Exclude a configuration group at this level";
                    }

                } // container import

                container export {
                    presence "Enable the export context";
                    description "Enable the export context";

                    leaf-list policy {
                        type union {
                            type types-sros:policy-expr-string;
                            type string;
                        }
                        min-elements 1;
                        max-elements 15;
                        ordered-by user;
                        description "Export policy name";
                    }

                    leaf-list apply-groups {
                        type leafref {
                            path "../../../../../groups/group/name";
                        }
                        max-elements 8;
                        ordered-by user;
                        description "Apply a configuration group at this level";
                    }

                    leaf-list apply-groups-exclude {
                        type leafref {
                            path "../../../../../groups/group/name";
                        }
                        max-elements 8;
                        ordered-by user;
                        description "Exclude a configuration group at this level";
                    }

                } // container export

                container extended-nh-encoding {
                    description "Enter the extended-nh-encoding context";

                    leaf ipv4 {
                        type boolean;
                        default "false";
                        description "Enable IPv4 family type";
                    }

                } // container extended-nh-encoding

                container advertise-ipv6-next-hops {
                    description "Enter the advertise-ipv6-next-hops context";

                    leaf ipv4 {
                        type boolean;
                        default "false";
                        description "Enable IPv4 routes to be advertised";
                    }

                } // container advertise-ipv6-next-hops

                container graceful-restart {
                    presence "Enable the graceful-restart context";
                    description "Enable the graceful-restart context";

                    leaf restart-time {
                        type uint32 {
                            range "0..4095";
                        }
                        default "120";
                        description "Restart time advertised by GR capability";
                    }

                    leaf stale-routes-time {
                        type uint32 {
                            range "1..3600";
                        }
                        default "360";
                        description "Maximum time to maintain routes after graceful restart";
                    }

                    leaf gr-notification {
                        type boolean;
                        default "false";
                        description "Perform Graceful Restart procedures";
                    }

                    container long-lived {
                        presence "Enable the long-lived context";
                        description "Enable the long-lived context";

                        leaf advertised-stale-time {
                            type uint32 {
                                range "0..16777215";
                            }
                            default "86400";
                            description "LLGR stale routes time";
                        }

                        leaf helper-override-stale-time {
                            type uint32 {
                                range "0..16777215";
                            }
                            description "Locally-configured stale routes override time";
                        }

                        leaf helper-override-restart-time {
                            type uint32 {
                                range "0..4095";
                            }
                            description "Locally-configured override for restart time";
                        }

                        leaf forwarding-bits-set {
                            type enumeration {
                                enum none                           { value 0; }
                                enum all                            { value 1; }
                                enum non-fwd                        { value 2; }
                            }
                            default "none";
                            description "BGP LLGR forwarding-bit behavior for address family";
                        }

                        leaf advertise-stale-to-all-neighbors {
                            type boolean;
                            default "false";
                            description "Advertise stale routes to all BGP peers";
                        }

                        leaf without-no-export {
                            type boolean;
                            default "false";
                            description "Advertise LLGR stale routes to non-LLGR peers";
                        }

                        list family {
                            key "family-type";
                            description "Enter the family list instance";

                            leaf family-type {
                                type types-bgp:vprn-bgp-llgr-family-identifiers;
                                description "Address family type for LLGR";
                            }

                            leaf advertised-stale-time {
                                type uint32 {
                                    range "0..16777215";
                                }
                                default "86400";
                                description "LLGR stale routes time for family override";
                            }

                            leaf helper-override-stale-time {
                                type uint32 {
                                    range "0..16777215";
                                }
                                description "Locally-configured stale routes override time";
                            }

                            leaf-list apply-groups {
                                type leafref {
                                    path "../../../../../../../groups/group/name";
                                }
                                max-elements 8;
                                ordered-by user;
                                description "Apply a configuration group at this level";
                            }

                            leaf-list apply-groups-exclude {
                                type leafref {
                                    path "../../../../../../../groups/group/name";
                                }
                                max-elements 8;
                                ordered-by user;
                                description "Exclude a configuration group at this level";
                            }

                        } // list family

                    } // container long-lived

                } // container graceful-restart

                container next-hop-resolution {
                    description "Enter the next-hop-resolution context";

                    leaf use-bgp-routes {
                        type boolean;
                        default "false";
                        description "Use BGP routes to resolve BGP next hops";
                    }

                    leaf policy {
                        type leafref {
                            path "../../../../../policy-options/policy-statement/name";
                        }
                        description "Policy that filters routes for BGP next-hop resolution";
                    }

                    container use-leaked-routes {
                        description "Enter the use-leaked-routes context";

                        leaf static {
                            type boolean;
                            default "false";
                            description "Use leaked static routes to resolve BGP next hop";
                        }

                    } // container use-leaked-routes

                } // container next-hop-resolution

                container multipath {
                    description "Enter the multipath context";

                    leaf max-paths {
                        type types-router:ip-ecmp;
                        default "1";
                        description "Maximum multipaths per prefix";
                    }

                    leaf ebgp {
                        type types-router:ip-ecmp;
                        description "Maximum multipaths per prefix for EBGP learned routes";
                    }

                    leaf ibgp {
                        type types-router:ip-ecmp;
                        description "Maximum multipaths per prefix for IBGP learned routes";
                    }

                    leaf restrict {
                        type types-bgp:restrict;
                        default "same-as-path-length";
                        description "AS path restriction for the non-best path";
                    }

                    leaf unequal-cost {
                        type boolean;
                        default "false";
                        description "Ignore differences in the next-hop cost for multipath";
                    }

                    list family {
                        key "family-type";
                        description "Enter the family list instance";

                        leaf family-type {
                            type enumeration {
                                enum ipv4                           { value 1; }
                                enum ipv6                           { value 3; }
                                enum label-ipv4                     { value 17; }
                                enum label-ipv6                     { value 18; }
                            }
                            description "Address family type for the multipath selection";
                        }

                        leaf max-paths {
                            type types-router:ip-ecmp;
                            description "Maximum number of multipaths per prefix or NLRI";
                        }

                        leaf ebgp {
                            type types-router:ip-ecmp;
                            description "Maximum multipaths when best path is EBGP learned route";
                        }

                        leaf ibgp {
                            type types-router:ip-ecmp;
                            description "Maximum multipaths when best path is IBGP learned route";
                        }

                        leaf restrict {
                            type types-bgp:restrict;
                            default "same-as-path-length";
                            description "AS path restriction for the non-best path";
                        }

                        leaf unequal-cost {
                            type boolean;
                            default "false";
                            description "Ignore differences in the next-hop cost for multipath";
                        }

                        leaf-list apply-groups {
                            type leafref {
                                path "../../../../../../groups/group/name";
                            }
                            max-elements 8;
                            ordered-by user;
                            description "Apply a configuration group at this level";
                        }

                        leaf-list apply-groups-exclude {
                            type leafref {
                                path "../../../../../../groups/group/name";
                            }
                            max-elements 8;
                            ordered-by user;
                            description "Exclude a configuration group at this level";
                        }

                    } // list family

                } // container multipath

                container monitor {
                    presence "Enable the monitor context";
                    description "Enable the monitor context";

                    leaf all-stations {
                        type boolean;
                        default "false";
                        description "Send BMP messages to all configured stations";
                    }

                    leaf admin-state {
                        type types-sros:admin-state;
                        default "disable";
                        description "Administrative state of BMP monitoring";
                    }

                    leaf-list apply-groups {
                        type leafref {
                            path "../../../../../groups/group/name";
                        }
                        max-elements 8;
                        ordered-by user;
                        description "Apply a configuration group at this level";
                    }

                    leaf-list apply-groups-exclude {
                        type leafref {
                            path "../../../../../groups/group/name";
                        }
                        max-elements 8;
                        ordered-by user;
                        description "Exclude a configuration group at this level";
                    }

                    container route-monitoring {
                        description "Enter the route-monitoring context";

                        leaf pre-policy {
                            type boolean;
                            default "false";
                            description "Allow pre-policy route-monitoring messages to be sent";
                        }

                        leaf post-policy {
                            type boolean;
                            default "false";
                            description "Allow post-policy route-monitoring messages to be sent";
                        }

                    } // container route-monitoring

                    list station {
                        key "station-name";
                        max-elements 8;
                        description "Add a list entry for station";

                        leaf station-name {
                            type leafref {
                                path "../../../../../../bmp/station/name";
                            }
                            description "BMP monitoring station";
                        }

                    } // list station

                } // container monitor

                container rib-management {
                    description "Enter the rib-management context";

                    container ipv4 {
                        description "Enter the ipv4 context";

                        container route-table-import {
                            description "Enter the route-table-import context";

                            leaf policy-name {
                                type leafref {
                                    path "../../../../../../../policy-options/policy-statement/name";
                                }
                                description "Name of policy that controls route importation into RIB";
                            }

                            leaf-list apply-groups {
                                type leafref {
                                    path "../../../../../../../groups/group/name";
                                }
                                max-elements 8;
                                ordered-by user;
                                description "Apply a configuration group at this level";
                            }

                            leaf-list apply-groups-exclude {
                                type leafref {
                                    path "../../../../../../../groups/group/name";
                                }
                                max-elements 8;
                                ordered-by user;
                                description "Exclude a configuration group at this level";
                            }

                        } // container route-table-import

                        container leak-import {
                            description "Enter the leak-import context";

                            leaf-list policy {
                                type union {
                                    type types-sros:policy-expr-string;
                                    type string;
                                }
                                max-elements 15;
                                ordered-by user;
                                description "Leak import policy name";
                            }

                            leaf-list apply-groups {
                                type leafref {
                                    path "../../../../../../../groups/group/name";
                                }
                                max-elements 8;
                                ordered-by user;
                                description "Apply a configuration group at this level";
                            }

                            leaf-list apply-groups-exclude {
                                type leafref {
                                    path "../../../../../../../groups/group/name";
                                }
                                max-elements 8;
                                ordered-by user;
                                description "Exclude a configuration group at this level";
                            }

                        } // container leak-import

                    } // container ipv4

                    container ipv6 {
                        description "Enter the ipv6 context";

                        container route-table-import {
                            description "Enter the route-table-import context";

                            leaf policy-name {
                                type leafref {
                                    path "../../../../../../../policy-options/policy-statement/name";
                                }
                                description "Name of policy that controls route importation into RIB";
                            }

                            leaf-list apply-groups {
                                type leafref {
                                    path "../../../../../../../groups/group/name";
                                }
                                max-elements 8;
                                ordered-by user;
                                description "Apply a configuration group at this level";
                            }

                            leaf-list apply-groups-exclude {
                                type leafref {
                                    path "../../../../../../../groups/group/name";
                                }
                                max-elements 8;
                                ordered-by user;
                                description "Exclude a configuration group at this level";
                            }

                        } // container route-table-import

                        container leak-import {
                            description "Enter the leak-import context";

                            leaf-list policy {
                                type union {
                                    type types-sros:policy-expr-string;
                                    type string;
                                }
                                max-elements 15;
                                ordered-by user;
                                description "Leak import policy name";
                            }

                            leaf-list apply-groups {
                                type leafref {
                                    path "../../../../../../../groups/group/name";
                                }
                                max-elements 8;
                                ordered-by user;
                                description "Apply a configuration group at this level";
                            }

                            leaf-list apply-groups-exclude {
                                type leafref {
                                    path "../../../../../../../groups/group/name";
                                }
                                max-elements 8;
                                ordered-by user;
                                description "Exclude a configuration group at this level";
                            }

                        } // container leak-import

                    } // container ipv6

                    container label-ipv4 {
                        description "Enter the label-ipv4 context";

                        container route-table-import {
                            description "Enter the route-table-import context";

                            leaf policy-name {
                                type leafref {
                                    path "../../../../../../../policy-options/policy-statement/name";
                                }
                                description "Name of policy that controls route importation into RIB";
                            }

                            leaf-list apply-groups {
                                type leafref {
                                    path "../../../../../../../groups/group/name";
                                }
                                max-elements 8;
                                ordered-by user;
                                description "Apply a configuration group at this level";
                            }

                            leaf-list apply-groups-exclude {
                                type leafref {
                                    path "../../../../../../../groups/group/name";
                                }
                                max-elements 8;
                                ordered-by user;
                                description "Exclude a configuration group at this level";
                            }

                        } // container route-table-import

                        container leak-import {
                            description "Enter the leak-import context";

                            leaf-list policy {
                                type union {
                                    type types-sros:policy-expr-string;
                                    type string;
                                }
                                max-elements 15;
                                ordered-by user;
                                description "Leak import policy name";
                            }

                            leaf-list apply-groups {
                                type leafref {
                                    path "../../../../../../../groups/group/name";
                                }
                                max-elements 8;
                                ordered-by user;
                                description "Apply a configuration group at this level";
                            }

                            leaf-list apply-groups-exclude {
                                type leafref {
                                    path "../../../../../../../groups/group/name";
                                }
                                max-elements 8;
                                ordered-by user;
                                description "Exclude a configuration group at this level";
                            }

                        } // container leak-import

                    } // container label-ipv4

                    container label-ipv6 {
                        description "Enter the label-ipv6 context";

                        container leak-import {
                            description "Enter the leak-import context";

                            leaf-list policy {
                                type union {
                                    type types-sros:policy-expr-string;
                                    type string;
                                }
                                max-elements 15;
                                ordered-by user;
                                description "Leak import policy name";
                            }

                            leaf-list apply-groups {
                                type leafref {
                                    path "../../../../../../../groups/group/name";
                                }
                                max-elements 8;
                                ordered-by user;
                                description "Apply a configuration group at this level";
                            }

                            leaf-list apply-groups-exclude {
                                type leafref {
                                    path "../../../../../../../groups/group/name";
                                }
                                max-elements 8;
                                ordered-by user;
                                description "Exclude a configuration group at this level";
                            }

                        } // container leak-import

                    } // container label-ipv6

                } // container rib-management

                list group {
                    key "group-name";
                    description "Enter the group list instance";

                    leaf group-name {
                        type types-sros:named-item-64;
                        description "BGP peer group name";
                    }

                    leaf description {
                        type types-sros:description;
                        description "Text description";
                    }

                    leaf connect-retry {
                        type int32 {
                            range "1..65535";
                        }
                        description "BGP connect retry timer value";
                    }

                    leaf admin-state {
                        type types-sros:admin-state;
                        default "enable";
                        description "Administrative state of the BGP group";
                    }

                    leaf static-group {
                        type boolean;
                        default "true";
                        description "Use group for static peers";
                    }

                    leaf keepalive {
                        type int32 {
                            range "0..21845";
                        }
                        description "Time after which the BGP KEEPALIVE message is sent";
                    }

                    leaf damping {
                        type boolean;
                        description "Use BGP route damping to reduce route flap";
                    }

                    leaf local-preference {
                        type int64 {
                            range "0..4294967295";
                        }
                        description "Default local preference if not in incoming routes";
                    }

                    leaf loop-detect {
                        type types-bgp:loop-detect;
                        description "Strategy for loop detection in the AS path";
                    }

                    leaf loop-detect-threshold {
                        type uint32 {
                            range "0..15";
                        }
                        description "Threshold for the global ASN in a received AS path";
                    }

                    leaf tcp-mss {
                        type union {
                            type uint32 {
                                range "384..9746";
                            }
                            type enumeration {
                                enum ip-stack                       { value 0; }
                            }
                        }
                        description "TCP maximum segment size override";
                    }

                    leaf min-route-advertisement {
                        type int16 {
                            range "1..255";
                        }
                        description "Minimum time before a prefix can be advertised to peer";
                    }

                    leaf aggregator-id-zero {
                        type boolean;
                        description "Set router ID in the BGP AGGREGATOR attribute to zero";
                    }

                    leaf preference {
                        type uint32 {
                            range "1..255";
                        }
                        description "Route preference for routes learned from all peers";
                    }

                    leaf multihop {
                        type int32 {
                            range "1..255";
                        }
                        description "TTL in IP packet headers for EBGP peers multi-hops away";
                    }

                    leaf med-out {
                        type union {
                            type uint32;
                            type enumeration {
                                enum igp-cost                       { value -1; }
                            }
                        }
                        description "Default MED attribute value to advertise to peers";
                    }

                    leaf authentication-key {
                        type types-sros:encrypted-leaf {
                            length "1..370";
                        }
                        description "BGP authentication key for peers in the group";
                    }

                    leaf client-reflect {
                        type boolean;
                        description "Allow cluster RR to advertise routes to its clients";
                    }

                    leaf as-override {
                        type boolean;
                        default "false";
                        description "Replace the peer's ASN with the local ASN in AS Path";
                    }

                    leaf asn-4-byte {
                        type boolean;
                        description "Advertise the use of 4-byte ASNs";
                    }

                    leaf path-mtu-discovery {
                        type boolean;
                        description "Enable Path MTU Discovery";
                    }

                    leaf next-hop-self {
                        type boolean;
                        default "false";
                        description "Advertise routes with local address as next-hop address";
                    }

                    leaf passive {
                        type boolean;
                        default "false";
                        description "Enable passive mode for BGP communication";
                    }

                    leaf type {
                        type types-bgp:peer-type;
                        default "no-type";
                        description "BGP peer type";
                    }

                    leaf peer-as {
                        type uint32 {
                            range "1..4294967295";
                        }
                        description "Peer AS number";
                    }

                    leaf capability-negotiation {
                        type boolean;
                        default "true";
                        description "Enable capability negotiation";
                    }

                    leaf enforce-first-as {
                        type boolean;
                        description "Enforce the configured peer AS value in received routes";
                    }

                    leaf initial-send-delay-zero {
                        type boolean;
                        description "Send BGP updates as soon as the session comes up";
                    }

                    leaf local-address {
                        type types-bgp:local-address;
                        description "Local IP address used when communicating with BGP peers";
                    }

                    leaf ttl-security {
                        type uint32 {
                            range "1..255";
                        }
                        description "Minimum TTL value for an incoming BGP packet";
                    }

                    leaf advertise-inactive {
                        type boolean;
                        description "Advertise an inactive BGP route to peers";
                    }

                    leaf authentication-keychain {
                        type leafref {
                            path "../../../../../system/security/keychains/keychain/keychain-name";
                        }
                        description "TCP authentication keychain for the session";
                    }

                    leaf bfd-liveness {
                        type boolean;
                        description "Enable BFD";
                    }

                    leaf fast-external-failover {
                        type boolean;
                        description "Drop external BGP session immediately when link fails";
                    }

                    leaf peer-ip-tracking {
                        type boolean;
                        description "Enable BGP peer tracking";
                    }

                    leaf dynamic-neighbor-limit {
                        type uint32 {
                            range "1..8192";
                        }
                        description "Maximum dynamic BGP sessions to accept from remote peer";
                    }

                    leaf split-horizon {
                        type boolean;
                        description "Prevent routes being reflected back to best-route peer";
                    }

                    leaf third-party-nexthop {
                        type boolean;
                        description "Apply third-party next-hop processing to EBGP peers";
                    }

                    leaf label-preference {
                        type uint32 {
                            range "1..255";
                        }
                        description "Route preference for routes from labeled-unicast peers";
                    }

                    leaf multipath-eligible {
                        type boolean;
                        default "false";
                        description "Allow routes from group peers in multipath eligibility";
                    }

                    leaf-list apply-groups {
                        type leafref {
                            path "../../../../../groups/group/name";
                        }
                        max-elements 8;
                        ordered-by user;
                        description "Apply a configuration group at this level";
                    }

                    leaf-list apply-groups-exclude {
                        type leafref {
                            path "../../../../../groups/group/name";
                        }
                        max-elements 8;
                        ordered-by user;
                        description "Exclude a configuration group at this level";
                    }

                    container hold-time {
                        description "Enter the hold-time context";

                        leaf seconds {
                            type int32 {
                                range "0|3..65535";
                            }
                            description "Maximum time BGP waits between successive messages";
                        }

                        leaf minimum-hold-time {
                            type int32 {
                                range "0|3..65536";
                            }
                            default "0";
                            description "Minimum hold time between successive messages";
                        }

                    } // container hold-time

                    container family {
                        presence "Enable the family context";
                        description "Enable the family context";

                        leaf ipv4 {
                            type boolean;
                            default "false";
                            description "Add support for the IPv4 address family";
                        }

                        leaf ipv6 {
                            type boolean;
                            default "false";
                            description "Advertise MP-BGP support for the IPv6 address family";
                        }

                        leaf mcast-ipv4 {
                            type boolean;
                            default "false";
                            description "Advertise support for the MCAST-IPv4 address family";
                        }

                        leaf flow-ipv4 {
                            type boolean;
                            default "false";
                            description "Advertise support for the FlowSpec-IPv4 address family";
                        }

                        leaf flow-ipv6 {
                            type boolean;
                            default "false";
                            description "Advertise support for the FlowSpec-IPv6 address family";
                        }

                        leaf mcast-ipv6 {
                            type boolean;
                            default "false";
                            description "Advertise support for the MCAST-IPv6 address family";
                        }

                        leaf label-ipv4 {
                            type boolean;
                            default "false";
                            description "Advertise support for the label-IPv4 address family";
                        }

                    } // container family

                    container send-default {
                        presence "Enable the send-default context";
                        description "Enable the send-default context";

                        leaf ipv4 {
                            type boolean;
                            default "false";
                            description "Generate and advertise an IPv4 default route (0/0)";
                        }

                        leaf ipv6 {
                            type boolean;
                            default "false";
                            description "Generate and advertise an IPv6 default route (::/0)";
                        }

                        leaf export-policy {
                            type leafref {
                                path "../../../../../../policy-options/policy-statement/name";
                            }
                            description "Export policy name";
                        }

                    } // container send-default

                    container default-preference {
                        description "Enter the default-preference context";

                        leaf ebgp {
                            type uint32 {
                                range "0..255";
                            }
                            description "Default preference for EBGP";
                        }

                        leaf ibgp {
                            type uint32 {
                                range "0..255";
                            }
                            description "Default preference for IBGP";
                        }

                    } // container default-preference

                    container default-label-preference {
                        description "Enter the default-label-preference context";

                        leaf ebgp {
                            type uint32 {
                                range "0..255";
                            }
                            description "Default preference for EBGP";
                        }

                        leaf ibgp {
                            type uint32 {
                                range "0..255";
                            }
                            description "Default preference for IBGP";
                        }

                    } // container default-label-preference

                    container remove-private {
                        presence "Enable the remove-private context";
                        description "Enable the remove-private context";

                        leaf limited {
                            type boolean;
                            default "false";
                            description "Remove private ASNs up to first public ASN encountered";
                        }

                        leaf skip-peer-as {
                            type boolean;
                            default "false";
                            description "Keep private ASN if it is the same as the BGP peer ASN";
                        }

                        leaf replace {
                            type boolean;
                            default "false";
                            description "Replace private ASN with global ASN before advertising";
                        }

                    } // container remove-private

                    container cluster {
                        description "Enter the cluster context";

                        leaf cluster-id {
                            type types-sros:ipv4-address;
                            description "Route reflector cluster ID";
                        }

                    } // container cluster

                    container ebgp-default-reject-policy {
                        presence "Enable the ebgp-default-reject-policy context";
                        description "Enable the ebgp-default-reject-policy context";

                        leaf import {
                            type boolean;
                            default "true";
                            description "Enable default reject import policy for external peers";
                        }

                        leaf export {
                            type boolean;
                            default "true";
                            description "Enable default reject export policy for external peers";
                        }

                    } // container ebgp-default-reject-policy

                    container local-as {
                        description "Enter the local-as context";

                        leaf as-number {
                            type uint32 {
                                range "1..4294967295";
                            }
                            description "Local (or virtual) BGP AS number";
                        }

                        leaf private {
                            type boolean;
                            default "false";
                            description "Hide the local ASN in sent paths learned from peering";
                        }

                        leaf prepend-global-as {
                            type boolean;
                            default "true";
                            description "Prepend global ASN when advertising routes to BGP peer";
                        }

                    } // container local-as

                    container origin-validation {
                        description "Enter the origin-validation context";

                        leaf ipv4 {
                            type boolean;
                            default "false";
                            description "Enable support for unlabeled unicast IPv4 routes";
                        }

                        leaf ipv6 {
                            type boolean;
                            default "false";
                            description "Enable support for unlabeled unicast IPv6 routes";
                        }

                        leaf label-ipv4 {
                            type boolean;
                            default "false";
                            description "Enable support for labeled-unicast IPv4 routes";
                        }

                    } // container origin-validation

                    container link-bandwidth {
                        description "Enter the link-bandwidth context";

                        container accept-from-ebgp {
                            description "Enter the accept-from-ebgp context";

                            leaf ipv4 {
                                type boolean;
                                default "false";
                                description "Support Link Bandwidth EC in IPv4 routes";
                            }

                            leaf ipv6 {
                                type boolean;
                                default "false";
                                description "Support Link Bandwidth EC in IPv6 routes";
                            }

                            leaf label-ipv4 {
                                type boolean;
                                default "false";
                                description "Support Link Bandwidth EC in label-IPv4 routes";
                            }

                        } // container accept-from-ebgp

                        container add-to-received-ebgp {
                            description "Enter the add-to-received-ebgp context";

                            leaf ipv4 {
                                type boolean;
                                default "false";
                                description "Support Link Bandwidth EC in IPv4 routes";
                            }

                            leaf ipv6 {
                                type boolean;
                                default "false";
                                description "Support Link Bandwidth EC in IPv6 routes";
                            }

                            leaf label-ipv4 {
                                type boolean;
                                default "false";
                                description "Support Link Bandwidth EC in label-IPv4 routes";
                            }

                        } // container add-to-received-ebgp

                        container aggregate-used-paths {
                            description "Enter the aggregate-used-paths context";

                            leaf ipv4 {
                                type boolean;
                                default "false";
                                description "Support Link Bandwidth EC in IPv4 routes";
                            }

                            leaf ipv6 {
                                type boolean;
                                default "false";
                                description "Support Link Bandwidth EC in IPv6 routes";
                            }

                            leaf label-ipv4 {
                                type boolean;
                                default "false";
                                description "Support Link Bandwidth EC in label-IPv4 routes";
                            }

                        } // container aggregate-used-paths

                        container send-to-ebgp {
                            description "Enter the send-to-ebgp context";

                            leaf ipv4 {
                                type boolean;
                                default "false";
                                description "Support Link Bandwidth EC in IPv4 routes";
                            }

                            leaf ipv6 {
                                type boolean;
                                default "false";
                                description "Support Link Bandwidth EC in IPv6 routes";
                            }

                            leaf label-ipv4 {
                                type boolean;
                                default "false";
                                description "Support Link Bandwidth EC in label-IPv4 routes";
                            }

                        } // container send-to-ebgp

                    } // container link-bandwidth

                    container send-communities {
                        description "Enter the send-communities context";

                        leaf standard {
                            type boolean;
                            description "Advertise the Communities attribute to peers";
                        }

                        leaf extended {
                            type boolean;
                            description "Advertise the Extended Communities attribute to peers";
                        }

                        leaf large {
                            type boolean;
                            description "Advertise the Large Communities attribute to peers";
                        }

                    } // container send-communities

                    container error-handling {
                        description "Enter the error-handling context";

                        leaf update-fault-tolerance {
                            type boolean;
                            description "Tolerate non-critical errors in UPDATE messages";
                        }

                    } // container error-handling

                    container damp-peer-oscillations {
                        presence "Enable the damp-peer-oscillations context";
                        description "Enable the damp-peer-oscillations context";

                        leaf error-interval {
                            type uint32 {
                                range "0..2048";
                            }
                            default "30";
                            description "Time after a reset that the session must be error-free";
                        }

                        container idle-hold-time {
                            description "Enter the idle-hold-time context";

                            leaf initial-wait {
                                type uint32 {
                                    range "0..2048";
                                }
                                default "0";
                                description "Time session remains in idle state after stabilization";
                            }

                            leaf second-wait {
                                type uint32 {
                                    range "1..2048";
                                }
                                default "5";
                                description "Time that doubles after each repeated session failure";
                            }

                            leaf max-wait {
                                type uint32 {
                                    range "1..2048";
                                }
                                default "60";
                                description "Maximum session idle time after repeated instability";
                            }

                        } // container idle-hold-time

                    } // container damp-peer-oscillations

                    container bfd-strict-mode {
                        description "Enter the bfd-strict-mode context";

                        leaf next-hop-reachability {
                            type boolean;
                            description "Consider next hop unreachable if BFD session is down";
                        }

                        container advertise {
                            presence "Enable the advertise context";
                            description "Enable the advertise context";

                            leaf holdtime {
                                type uint16 {
                                    range "1..65535";
                                }
                                units "seconds";
                                default "30";
                                description "Maximum time BGP waits for the BFD session to come up";
                            }

                        } // container advertise

                    } // container bfd-strict-mode

                    container import {
                        presence "Enable the import context";
                        description "Enable the import context";

                        leaf-list policy {
                            type union {
                                type types-sros:policy-expr-string;
                                type string;
                            }
                            min-elements 1;
                            max-elements 15;
                            ordered-by user;
                            description "Route policy name";
                        }

                        leaf-list apply-groups {
                            type leafref {
                                path "../../../../../../groups/group/name";
                            }
                            max-elements 8;
                            ordered-by user;
                            description "Apply a configuration group at this level";
                        }

                        leaf-list apply-groups-exclude {
                            type leafref {
                                path "../../../../../../groups/group/name";
                            }
                            max-elements 8;
                            ordered-by user;
                            description "Exclude a configuration group at this level";
                        }

                    } // container import

                    container export {
                        presence "Enable the export context";
                        description "Enable the export context";

                        leaf-list policy {
                            type union {
                                type types-sros:policy-expr-string;
                                type string;
                            }
                            min-elements 1;
                            max-elements 15;
                            ordered-by user;
                            description "Export policy name";
                        }

                        leaf-list apply-groups {
                            type leafref {
                                path "../../../../../../groups/group/name";
                            }
                            max-elements 8;
                            ordered-by user;
                            description "Apply a configuration group at this level";
                        }

                        leaf-list apply-groups-exclude {
                            type leafref {
                                path "../../../../../../groups/group/name";
                            }
                            max-elements 8;
                            ordered-by user;
                            description "Exclude a configuration group at this level";
                        }

                    } // container export

                    container extended-nh-encoding {
                        presence "Enable the extended-nh-encoding context";
                        description "Enable the extended-nh-encoding context";

                        leaf ipv4 {
                            type boolean;
                            default "false";
                            description "Enable IPv4 family type";
                        }

                    } // container extended-nh-encoding

                    container advertise-ipv6-next-hops {
                        presence "Enable the advertise-ipv6-next-hops context";
                        description "Enable the advertise-ipv6-next-hops context";

                        leaf ipv4 {
                            type boolean;
                            default "false";
                            description "Enable IPv4 routes to be advertised";
                        }

                    } // container advertise-ipv6-next-hops

                    container graceful-restart {
                        presence "Enable the graceful-restart context";
                        description "Enable the graceful-restart context";

                        leaf restart-time {
                            type uint32 {
                                range "0..4095";
                            }
                            default "300";
                            description "Restart time advertised by GR capability";
                        }

                        leaf stale-routes-time {
                            type uint32 {
                                range "1..3600";
                            }
                            default "360";
                            description "Maximum time to maintain routes after graceful restart";
                        }

                        leaf gr-notification {
                            type boolean;
                            default "false";
                            description "Perform graceful restart procedures after NOTIFICATION";
                        }

                        container long-lived {
                            presence "Enable the long-lived context";
                            description "Enable the long-lived context";

                            leaf advertised-stale-time {
                                type uint32 {
                                    range "0..16777215";
                                }
                                default "86400";
                                description "Advertised long-lived stale time for LLGR routes";
                            }

                            leaf helper-override-stale-time {
                                type uint32 {
                                    range "0..16777215";
                                }
                                description "Locally-configured stale routes override time";
                            }

                            leaf helper-override-restart-time {
                                type uint32 {
                                    range "0..4095";
                                }
                                description "Locally-configured override for restart time";
                            }

                            leaf forwarding-bits-set {
                                type enumeration {
                                    enum none                           { value 0; }
                                    enum all                            { value 1; }
                                    enum non-fwd                        { value 2; }
                                }
                                default "none";
                                description "BGP LLGR forwarding-bit behavior for address family";
                            }

                            leaf advertise-stale-to-all-neighbors {
                                type boolean;
                                default "false";
                                description "Advertise stale routes to all BGP peers";
                            }

                            leaf without-no-export {
                                type boolean;
                                default "false";
                                description "Advertise LLGR stale routes to non-LLGR peers";
                            }

                            list family {
                                key "family-type";
                                description "Enter the family list instance";

                                leaf family-type {
                                    type types-bgp:vprn-bgp-llgr-family-identifiers;
                                    description "Address family type for LLGR";
                                }

                                leaf advertised-stale-time {
                                    type uint32 {
                                        range "0..16777215";
                                    }
                                    default "86400";
                                    description "LLGR stale routes time for family override";
                                }

                                leaf helper-override-stale-time {
                                    type uint32 {
                                        range "0..16777216";
                                    }
                                    default "16777216";
                                    description "Locally-configured stale routes override time";
                                }

                                leaf-list apply-groups {
                                    type leafref {
                                        path "../../../../../../../../groups/group/name";
                                    }
                                    max-elements 8;
                                    ordered-by user;
                                    description "Apply a configuration group at this level";
                                }

                                leaf-list apply-groups-exclude {
                                    type leafref {
                                        path "../../../../../../../../groups/group/name";
                                    }
                                    max-elements 8;
                                    ordered-by user;
                                    description "Exclude a configuration group at this level";
                                }

                            } // list family

                        } // container long-lived

                    } // container graceful-restart

                    list prefix-limit {
                        key "family";
                        description "Enter the prefix-limit list instance";

                        leaf family {
                            type enumeration {
                                enum ipv4                           { value 1; }
                                enum ipv6                           { value 3; }
                                enum mcast-ipv4                     { value 4; }
                                enum flow-ipv4                      { value 10; }
                                enum flow-ipv6                      { value 14; }
                                enum mcast-ipv6                     { value 16; }
                                enum label-ipv4                     { value 17; }
                            }
                            description "Address family to which the limit applies";
                        }

                        leaf maximum {
                            type uint32 {
                                range "1..4294967295";
                            }
                            mandatory true;
                            description "Maximum number of routes to be learned from a peer";
                        }

                        leaf log-only {
                            type boolean;
                            default "false";
                            description "Send warning message at threshold instead of take-down";
                        }

                        leaf threshold {
                            type uint32 {
                                range "1..100";
                            }
                            default "90";
                            description "Percentage threshold that triggers a warning message";
                        }

                        leaf idle-timeout {
                            type int32 {
                                range "1..1024";
                            }
                            description "Time BGP peering remains idle before reconnecting";
                        }

                        leaf post-import {
                            type boolean;
                            default "false";
                            description "Apply limit only to routes accepted by import policies";
                        }

                        leaf hold-excess {
                            type int32 {
                                range "1..100";
                            }
                            description "Percentage of maximum routes to install in route table";
                        }

                        leaf-list apply-groups {
                            type leafref {
                                path "../../../../../../groups/group/name";
                            }
                            max-elements 8;
                            ordered-by user;
                            description "Apply a configuration group at this level";
                        }

                        leaf-list apply-groups-exclude {
                            type leafref {
                                path "../../../../../../groups/group/name";
                            }
                            max-elements 8;
                            ordered-by user;
                            description "Exclude a configuration group at this level";
                        }

                    } // list prefix-limit

                    container dynamic-neighbor {
                        description "Enter the dynamic-neighbor context";

                        container match {
                            description "Enter the match context";

                            list prefix {
                                key "ip-prefix";
                                description "Enter the prefix list instance";

                                leaf ip-prefix {
                                    type types-sros:ip-prefix;
                                    description "Dynamic peer prefix for the group";
                                }

                                leaf-list allowed-peer-as {
                                    type string {
                                        pattern "(([1-9]|[1-9][0-9]{1,8}|[1-3][0-9]{9}|4[0-1][0-9]{8}|42[0-8][0-9]{7}|429[0-3][0-9]{6}|4294[0-8][0-9]{5}|42949[0-5][0-9]{4}|429496[0-6][0-9]{3}|4294967[0-1][0-9]{2}|42949672[0-8][0-9]|429496729[0-5]))|(([1-9]|[1-9][0-9]{1,8}|[1-3][0-9]{9}|4[0-1][0-9]{8}|42[0-8][0-9]{7}|429[0-3][0-9]{6}|4294[0-8][0-9]{5}|42949[0-5][0-9]{4}|429496[0-6][0-9]{3}|4294967[0-1][0-9]{2}|42949672[0-8][0-9]|429496729[0-5])\\.\\.([1-9]|[1-9][0-9]{1,8}|[1-3][0-9]{9}|4[0-1][0-9]{8}|42[0-8][0-9]{7}|429[0-3][0-9]{6}|4294[0-8][0-9]{5}|42949[0-5][0-9]{4}|429496[0-6][0-9]{3}|4294967[0-1][0-9]{2}|42949672[0-8][0-9]|429496729[0-5]))";
                                    }
                                    max-elements 32;
                                    ordered-by user;
                                    description "Allowed peer AS value or range of acceptable values";
                                }

                                leaf-list apply-groups {
                                    type leafref {
                                        path "../../../../../../../../groups/group/name";
                                    }
                                    max-elements 8;
                                    ordered-by user;
                                    description "Apply a configuration group at this level";
                                }

                                leaf-list apply-groups-exclude {
                                    type leafref {
                                        path "../../../../../../../../groups/group/name";
                                    }
                                    max-elements 8;
                                    ordered-by user;
                                    description "Exclude a configuration group at this level";
                                }

                            } // list prefix

                        } // container match

                        list interface {
                            key "interface-name";
                            description "Enter the interface list instance";

                            leaf interface-name {
                                type leafref {
                                    path "../../../../../../vprn/interface/interface-name";
                                }
                                description "Name of the dynamic neighbor interface";
                            }

                            leaf-list allowed-peer-as {
                                type string {
                                    pattern "(([1-9]|[1-9][0-9]{1,8}|[1-3][0-9]{9}|4[0-1][0-9]{8}|42[0-8][0-9]{7}|429[0-3][0-9]{6}|4294[0-8][0-9]{5}|42949[0-5][0-9]{4}|429496[0-6][0-9]{3}|4294967[0-1][0-9]{2}|42949672[0-8][0-9]|429496729[0-5]))|(([1-9]|[1-9][0-9]{1,8}|[1-3][0-9]{9}|4[0-1][0-9]{8}|42[0-8][0-9]{7}|429[0-3][0-9]{6}|4294[0-8][0-9]{5}|42949[0-5][0-9]{4}|429496[0-6][0-9]{3}|4294967[0-1][0-9]{2}|42949672[0-8][0-9]|429496729[0-5])\\.\\.([1-9]|[1-9][0-9]{1,8}|[1-3][0-9]{9}|4[0-1][0-9]{8}|42[0-8][0-9]{7}|429[0-3][0-9]{6}|4294[0-8][0-9]{5}|42949[0-5][0-9]{4}|429496[0-6][0-9]{3}|4294967[0-1][0-9]{2}|42949672[0-8][0-9]|429496729[0-5]))";
                                }
                                max-elements 32;
                                ordered-by user;
                                description "Allowed peer AS value or range of acceptable values";
                            }

                            leaf max-sessions {
                                type uint32 {
                                    range "1..255";
                                }
                                default "1";
                                description "Maximum number of dynamic sessions allowed";
                            }

                            leaf-list apply-groups {
                                type leafref {
                                    path "../../../../../../../groups/group/name";
                                }
                                max-elements 8;
                                ordered-by user;
                                description "Apply a configuration group at this level";
                            }

                            leaf-list apply-groups-exclude {
                                type leafref {
                                    path "../../../../../../../groups/group/name";
                                }
                                max-elements 8;
                                ordered-by user;
                                description "Exclude a configuration group at this level";
                            }

                        } // list interface

                    } // container dynamic-neighbor

                    container monitor {
                        presence "Enable the monitor context";
                        description "Enable the monitor context";

                        leaf all-stations {
                            type boolean;
                            default "false";
                            description "Send BMP messages to all configured stations";
                        }

                        leaf admin-state {
                            type types-sros:admin-state;
                            default "disable";
                            description "Administrative state of BMP monitoring";
                        }

                        leaf-list apply-groups {
                            type leafref {
                                path "../../../../../../groups/group/name";
                            }
                            max-elements 8;
                            ordered-by user;
                            description "Apply a configuration group at this level";
                        }

                        leaf-list apply-groups-exclude {
                            type leafref {
                                path "../../../../../../groups/group/name";
                            }
                            max-elements 8;
                            ordered-by user;
                            description "Exclude a configuration group at this level";
                        }

                        container route-monitoring {
                            description "Enter the route-monitoring context";

                            leaf pre-policy {
                                type boolean;
                                default "false";
                                description "Allow pre-policy route-monitoring messages to be sent";
                            }

                            leaf post-policy {
                                type boolean;
                                default "false";
                                description "Allow post-policy route-monitoring messages to be sent";
                            }

                        } // container route-monitoring

                        list station {
                            key "station-name";
                            max-elements 8;
                            description "Add a list entry for station";

                            leaf station-name {
                                type leafref {
                                    path "../../../../../../../bmp/station/name";
                                }
                                description "BMP monitoring station";
                            }

                        } // list station

                    } // container monitor

                    container evpn-link-bandwidth {
                        description "Enter the evpn-link-bandwidth context";

                        leaf add-to-received-bgp {
                            type union {
                                type int32 {
                                    range "1..128";
                                }
                            }
                            description "Weight added to received PE-CE BGP routes";
                        }

                    } // container evpn-link-bandwidth

                } // list group

                list neighbor {
                    key "ip-address";
                    description "Enter the neighbor list instance";

                    leaf ip-address {
                        type types-sros:ip-address-with-zone;
                        description "IP address of the BGP peer router";
                    }

                    leaf ttl-security {
                        type uint32 {
                            range "1..255";
                        }
                        description "Minimum TTL value for an incoming BGP packet";
                    }

                    leaf advertise-inactive {
                        type boolean;
                        description "Advertise an inactive BGP route to peers";
                    }

                    leaf authentication-keychain {
                        type leafref {
                            path "../../../../../system/security/keychains/keychain/keychain-name";
                        }
                        description "TCP authentication keychain for the session";
                    }

                    leaf bfd-liveness {
                        type boolean;
                        description "Enable BFD";
                    }

                    leaf fast-external-failover {
                        type boolean;
                        description "Drop external BGP session immediately when link fails";
                    }

                    leaf peer-ip-tracking {
                        type boolean;
                        description "Enable BGP peer tracking";
                    }

                    leaf split-horizon {
                        type boolean;
                        description "Prevent routes being reflected back to best-route peer";
                    }

                    leaf third-party-nexthop {
                        type boolean;
                        description "Apply third-party next-hop processing to EBGP peers";
                    }

                    leaf label-preference {
                        type uint32 {
                            range "1..255";
                        }
                        description "Route preference for routes from labeled-unicast peers";
                    }

                    leaf multipath-eligible {
                        type boolean;
                        description "Allow routes from this peer in multipath eligibility";
                    }

                    leaf group {
                        type leafref {
                            path "../../group/group-name";
                        }
                        sros-ext:immutable;
                        mandatory true;
                        description "Neighbor to group";
                    }

                    leaf peer-creation-type {
                        type types-bgp:peer-creation-type;
                        default "static";
                        description "Peer creation type";
                    }

                    leaf connect-retry {
                        type int32 {
                            range "1..65535";
                        }
                        description "BGP connect retry timer value";
                    }

                    leaf description {
                        type types-sros:description;
                        description "Text description";
                    }

                    leaf admin-state {
                        type types-sros:admin-state;
                        default "enable";
                        description "Administrative state of the BGP neighbor";
                    }

                    leaf keepalive {
                        type int32 {
                            range "0..21845";
                        }
                        description "Time after which the BGP KEEPALIVE message is sent";
                    }

                    leaf damping {
                        type boolean;
                        description "Use BGP route damping to reduce route flap";
                    }

                    leaf local-preference {
                        type int64 {
                            range "0..4294967295";
                        }
                        description "Default local preference if not in incoming routes";
                    }

                    leaf loop-detect {
                        type types-bgp:loop-detect;
                        description "Strategy for loop detection in the AS path";
                    }

                    leaf loop-detect-threshold {
                        type uint32 {
                            range "0..15";
                        }
                        description "Threshold for the global ASN in a received AS path";
                    }

                    leaf tcp-mss {
                        type union {
                            type uint32 {
                                range "384..9746";
                            }
                            type enumeration {
                                enum ip-stack                       { value 0; }
                            }
                        }
                        description "TCP maximum segment size override";
                    }

                    leaf min-route-advertisement {
                        type int16 {
                            range "1..255";
                        }
                        description "Minimum interval between successive prefix updates";
                    }

                    leaf aggregator-id-zero {
                        type boolean;
                        description "Set router ID in the BGP AGGREGATOR attribute to zero";
                    }

                    leaf preference {
                        type uint32 {
                            range "1..255";
                        }
                        description "Route preference for routes learned from all peers";
                    }

                    leaf multihop {
                        type int32 {
                            range "1..255";
                        }
                        description "TTL in IP packet headers for EBGP peers multi-hops away";
                    }

                    leaf med-out {
                        type union {
                            type uint32;
                            type enumeration {
                                enum igp-cost                       { value -1; }
                            }
                        }
                        description "Default MED attribute value to advertise to peers";
                    }

                    leaf authentication-key {
                        type types-sros:encrypted-leaf {
                            length "1..370";
                        }
                        description "BGP authentication key";
                    }

                    leaf client-reflect {
                        type boolean;
                        description "Allow cluster RR to advertise routes to its clients";
                    }

                    leaf as-override {
                        type boolean;
                        description "Replace the peer ASN with the local ASN in AS Path";
                    }

                    leaf asn-4-byte {
                        type boolean;
                        description "Advertise the use of 4-byte ASNs";
                    }

                    leaf path-mtu-discovery {
                        type boolean;
                        description "Enable path MTU discovery";
                    }

                    leaf local-address {
                        type types-bgp:local-address;
                        description "Local IP address used when communicating with BGP peers";
                    }

                    leaf next-hop-self {
                        type boolean;
                        description "Advertise routes with local address as next-hop address";
                    }

                    leaf passive {
                        type boolean;
                        description "Use passive mode for BGP communication";
                    }

                    leaf type {
                        type types-bgp:peer-type;
                        description "BGP peer type";
                    }

                    leaf peer-as {
                        type uint32 {
                            range "1..4294967295";
                        }
                        description "Peer AS number";
                    }

                    leaf capability-negotiation {
                        type boolean;
                        description "Enable capability negotiation";
                    }

                    leaf enforce-first-as {
                        type boolean;
                        description "Enforce the configured peer AS value in received routes";
                    }

                    leaf initial-send-delay-zero {
                        type boolean;
                        description "Send BGP updates as soon as the session comes up";
                    }

                    leaf-list apply-groups {
                        type leafref {
                            path "../../../../../groups/group/name";
                        }
                        max-elements 8;
                        ordered-by user;
                        description "Apply a configuration group at this level";
                    }

                    leaf-list apply-groups-exclude {
                        type leafref {
                            path "../../../../../groups/group/name";
                        }
                        max-elements 8;
                        ordered-by user;
                        description "Exclude a configuration group at this level";
                    }

                    container origin-validation {
                        presence "Enable the origin-validation context";
                        description "Enable the origin-validation context";

                        leaf ipv4 {
                            type boolean;
                            default "false";
                            description "Enable support for unlabeled unicast IPv4 routes";
                        }

                        leaf ipv6 {
                            type boolean;
                            default "false";
                            description "Enable support for unlabeled unicast IPv6 routes";
                        }

                        leaf label-ipv4 {
                            type boolean;
                            default "false";
                            description "Enable support for labeled-unicast IPv4 routes";
                        }

                    } // container origin-validation

                    container link-bandwidth {
                        description "Enter the link-bandwidth context";

                        container accept-from-ebgp {
                            presence "Enable the accept-from-ebgp context";
                            description "Enable the accept-from-ebgp context";

                            leaf ipv4 {
                                type boolean;
                                default "false";
                                description "Support Link Bandwidth EC in IPv4 routes";
                            }

                            leaf ipv6 {
                                type boolean;
                                default "false";
                                description "Support Link Bandwidth EC in IPv6 routes";
                            }

                            leaf label-ipv4 {
                                type boolean;
                                default "false";
                                description "Support Link Bandwidth EC in label-IPv4 routes";
                            }

                        } // container accept-from-ebgp

                        container add-to-received-ebgp {
                            presence "Enable the add-to-received-ebgp context";
                            description "Enable the add-to-received-ebgp context";

                            leaf ipv4 {
                                type boolean;
                                default "false";
                                description "Support Link Bandwidth EC in IPv4 routes";
                            }

                            leaf ipv6 {
                                type boolean;
                                default "false";
                                description "Support Link Bandwidth EC in IPv6 routes";
                            }

                            leaf label-ipv4 {
                                type boolean;
                                default "false";
                                description "Support Link Bandwidth EC in label-IPv4 routes";
                            }

                        } // container add-to-received-ebgp

                        container aggregate-used-paths {
                            presence "Enable the aggregate-used-paths context";
                            description "Enable the aggregate-used-paths context";

                            leaf ipv4 {
                                type boolean;
                                default "false";
                                description "Support Link Bandwidth EC in IPv4 routes";
                            }

                            leaf ipv6 {
                                type boolean;
                                default "false";
                                description "Support Link Bandwidth EC in IPv6 routes";
                            }

                            leaf label-ipv4 {
                                type boolean;
                                default "false";
                                description "Support Link Bandwidth EC in label-IPv4 routes";
                            }

                        } // container aggregate-used-paths

                        container send-to-ebgp {
                            presence "Enable the send-to-ebgp context";
                            description "Enable the send-to-ebgp context";

                            leaf ipv4 {
                                type boolean;
                                default "false";
                                description "Support Link Bandwidth EC in IPv4 routes";
                            }

                            leaf ipv6 {
                                type boolean;
                                default "false";
                                description "Support Link Bandwidth EC in IPv6 routes";
                            }

                            leaf label-ipv4 {
                                type boolean;
                                default "false";
                                description "Support Link Bandwidth EC in label-IPv4 routes";
                            }

                        } // container send-to-ebgp

                    } // container link-bandwidth

                    container send-communities {
                        description "Enter the send-communities context";

                        leaf standard {
                            type boolean;
                            description "Advertise the Communities attribute to peers";
                        }

                        leaf extended {
                            type boolean;
                            description "Advertise the Extended Communities attribute to peers";
                        }

                        leaf large {
                            type boolean;
                            description "Advertise the Large Communities attribute to peers";
                        }

                    } // container send-communities

                    container error-handling {
                        description "Enter the error-handling context";

                        leaf update-fault-tolerance {
                            type boolean;
                            description "Tolerate non-critical errors in UPDATE messages";
                        }

                    } // container error-handling

                    container damp-peer-oscillations {
                        presence "Enable the damp-peer-oscillations context";
                        description "Enable the damp-peer-oscillations context";

                        leaf error-interval {
                            type uint32 {
                                range "0..2048";
                            }
                            default "30";
                            description "Time after a reset that the session must be error-free";
                        }

                        container idle-hold-time {
                            description "Enter the idle-hold-time context";

                            leaf initial-wait {
                                type uint32 {
                                    range "0..2048";
                                }
                                default "0";
                                description "Time session remains in idle state after stabilization";
                            }

                            leaf second-wait {
                                type uint32 {
                                    range "1..2048";
                                }
                                default "5";
                                description "Time that doubles after each repeated session failure";
                            }

                            leaf max-wait {
                                type uint32 {
                                    range "1..2048";
                                }
                                default "60";
                                description "Maximum session idle time after repeated instability";
                            }

                        } // container idle-hold-time

                    } // container damp-peer-oscillations

                    container bfd-strict-mode {
                        description "Enter the bfd-strict-mode context";

                        leaf next-hop-reachability {
                            type boolean;
                            description "Consider next hop unreachable if BFD session is down";
                        }

                        container advertise {
                            presence "Enable the advertise context";
                            description "Enable the advertise context";

                            leaf holdtime {
                                type uint16 {
                                    range "1..65535";
                                }
                                units "seconds";
                                default "30";
                                description "Maximum time BGP waits for the BFD session to come up";
                            }

                        } // container advertise

                    } // container bfd-strict-mode

                    container hold-time {
                        description "Enter the hold-time context";

                        leaf seconds {
                            type int32 {
                                range "0|3..65535";
                            }
                            description "Maximum hold time between successive messages";
                        }

                        leaf minimum-hold-time {
                            type int32 {
                                range "0|3..65536";
                            }
                            default "0";
                            description "Minimum time BGP waits between successive messages";
                        }

                    } // container hold-time

                    container family {
                        presence "Enable the family context";
                        description "Enable the family context";

                        leaf ipv4 {
                            type boolean;
                            default "false";
                            description "Add support for the IPv4 address family";
                        }

                        leaf ipv6 {
                            type boolean;
                            default "false";
                            description "Advertise MP-BGP support for the IPv6 address family";
                        }

                        leaf mcast-ipv4 {
                            type boolean;
                            default "false";
                            description "Advertise support for the MCAST-IPv4 address family";
                        }

                        leaf flow-ipv4 {
                            type boolean;
                            default "false";
                            description "Advertise support for the FlowSpec-IPv4 address family";
                        }

                        leaf flow-ipv6 {
                            type boolean;
                            default "false";
                            description "Advertise support for the FlowSpec-IPv6 address family";
                        }

                        leaf mcast-ipv6 {
                            type boolean;
                            default "false";
                            description "Advertise support for the MCAST-IPv6 address family";
                        }

                        leaf label-ipv4 {
                            type boolean;
                            default "false";
                            description "Advertise support for the label-IPv4 address family";
                        }

                    } // container family

                    container send-default {
                        presence "Enable the send-default context";
                        description "Enable the send-default context";

                        leaf ipv4 {
                            type boolean;
                            default "false";
                            description "Enable IPv4 family type";
                        }

                        leaf ipv6 {
                            type boolean;
                            default "false";
                            description "Enable IPv6 family type";
                        }

                        leaf export-policy {
                            type leafref {
                                path "../../../../../../policy-options/policy-statement/name";
                            }
                            description "Export policy name";
                        }

                    } // container send-default

                    container default-preference {
                        description "Enter the default-preference context";

                        leaf ebgp {
                            type uint32 {
                                range "0..255";
                            }
                            description "Default preference for EBGP";
                        }

                        leaf ibgp {
                            type uint32 {
                                range "0..255";
                            }
                            description "Default preference for IBGP";
                        }

                    } // container default-preference

                    container default-label-preference {
                        description "Enter the default-label-preference context";

                        leaf ebgp {
                            type uint32 {
                                range "0..255";
                            }
                            description "Default preference for EBGP";
                        }

                        leaf ibgp {
                            type uint32 {
                                range "0..255";
                            }
                            description "Default preference for IBGP";
                        }

                    } // container default-label-preference

                    container remove-private {
                        presence "Enable the remove-private context";
                        description "Enable the remove-private context";

                        leaf limited {
                            type boolean;
                            default "false";
                            description "Remove private ASNs up to first public ASN encountered";
                        }

                        leaf skip-peer-as {
                            type boolean;
                            default "false";
                            description "Keep private ASN if it is the same as the BGP peer ASN";
                        }

                        leaf replace {
                            type boolean;
                            default "false";
                            description "Replace private ASN with global ASN before advertising";
                        }

                    } // container remove-private

                    container cluster {
                        description "Enter the cluster context";

                        leaf cluster-id {
                            type types-sros:ipv4-address;
                            description "Route reflector cluster ID";
                        }

                    } // container cluster

                    container ebgp-default-reject-policy {
                        presence "Enable the ebgp-default-reject-policy context";
                        description "Enable the ebgp-default-reject-policy context";

                        leaf import {
                            type boolean;
                            default "true";
                            description "Enable default reject import policy for external peers";
                        }

                        leaf export {
                            type boolean;
                            default "true";
                            description "Enable default reject export policy for external peers";
                        }

                    } // container ebgp-default-reject-policy

                    container local-as {
                        description "Enter the local-as context";

                        leaf as-number {
                            type uint32 {
                                range "1..4294967295";
                            }
                            description "Local (or virtual) BGP AS number";
                        }

                        leaf private {
                            type boolean;
                            default "false";
                            description "Hide the local ASN in sent paths learned from peering";
                        }

                        leaf prepend-global-as {
                            type boolean;
                            default "true";
                            description "Prepend global ASN when advertising routes to BGP peer";
                        }

                    } // container local-as

                    container import {
                        presence "Enable the import context";
                        description "Enable the import context";

                        leaf-list policy {
                            type union {
                                type types-sros:policy-expr-string;
                                type string;
                            }
                            min-elements 1;
                            max-elements 15;
                            ordered-by user;
                            description "Route policy name";
                        }

                        leaf-list apply-groups {
                            type leafref {
                                path "../../../../../../groups/group/name";
                            }
                            max-elements 8;
                            ordered-by user;
                            description "Apply a configuration group at this level";
                        }

                        leaf-list apply-groups-exclude {
                            type leafref {
                                path "../../../../../../groups/group/name";
                            }
                            max-elements 8;
                            ordered-by user;
                            description "Exclude a configuration group at this level";
                        }

                    } // container import

                    container export {
                        presence "Enable the export context";
                        description "Enable the export context";

                        leaf-list policy {
                            type union {
                                type types-sros:policy-expr-string;
                                type string;
                            }
                            min-elements 1;
                            max-elements 15;
                            ordered-by user;
                            description "Export policy name";
                        }

                        leaf-list apply-groups {
                            type leafref {
                                path "../../../../../../groups/group/name";
                            }
                            max-elements 8;
                            ordered-by user;
                            description "Apply a configuration group at this level";
                        }

                        leaf-list apply-groups-exclude {
                            type leafref {
                                path "../../../../../../groups/group/name";
                            }
                            max-elements 8;
                            ordered-by user;
                            description "Exclude a configuration group at this level";
                        }

                    } // container export

                    container extended-nh-encoding {
                        presence "Enable the extended-nh-encoding context";
                        description "Enable the extended-nh-encoding context";

                        leaf ipv4 {
                            type boolean;
                            default "false";
                            description "Enable IPv4 family type";
                        }

                    } // container extended-nh-encoding

                    container advertise-ipv6-next-hops {
                        presence "Enable the advertise-ipv6-next-hops context";
                        description "Enable the advertise-ipv6-next-hops context";

                        leaf ipv4 {
                            type boolean;
                            default "false";
                            description "Enable IPv4 routes to be advertised";
                        }

                    } // container advertise-ipv6-next-hops

                    container graceful-restart {
                        presence "Enable the graceful-restart context";
                        description "Enable the graceful-restart context";

                        leaf restart-time {
                            type uint32 {
                                range "0..4095";
                            }
                            default "300";
                            description "Restart time advertised by GR capability";
                        }

                        leaf stale-routes-time {
                            type uint32 {
                                range "1..3600";
                            }
                            default "360";
                            description "Maximum time to maintain routes after graceful restart";
                        }

                        leaf gr-notification {
                            type boolean;
                            default "false";
                            description "Perform graceful restart procedures after NOTIFICATION";
                        }

                        container long-lived {
                            presence "Enable the long-lived context";
                            description "Enable the long-lived context";

                            leaf advertised-stale-time {
                                type uint32 {
                                    range "0..16777215";
                                }
                                default "86400";
                                description "Advertised long-lived stale time for LLGR routes";
                            }

                            leaf helper-override-stale-time {
                                type uint32 {
                                    range "0..16777215";
                                }
                                description "Locally-configured stale routes override time";
                            }

                            leaf helper-override-restart-time {
                                type uint32 {
                                    range "0..4095";
                                }
                                description "Locally-configured override for restart time";
                            }

                            leaf forwarding-bits-set {
                                type enumeration {
                                    enum none                           { value 0; }
                                    enum all                            { value 1; }
                                    enum non-fwd                        { value 2; }
                                }
                                default "none";
                                description "BGP LLGR forwarding-bit behavior for address family";
                            }

                            leaf advertise-stale-to-all-neighbors {
                                type boolean;
                                default "false";
                                description "Advertise stale routes to all BGP peers";
                            }

                            leaf without-no-export {
                                type boolean;
                                default "false";
                                description "Advertise LLGR stale routes to non-LLGR peers";
                            }

                            list family {
                                key "family-type";
                                description "Enter the family list instance";

                                leaf family-type {
                                    type types-bgp:vprn-bgp-llgr-family-identifiers;
                                    description "Address family type for LLGR";
                                }

                                leaf advertised-stale-time {
                                    type uint32 {
                                        range "0..16777215";
                                    }
                                    default "86400";
                                    description "LLGR stale routes time for family override";
                                }

                                leaf helper-override-stale-time {
                                    type uint32 {
                                        range "0..16777216";
                                    }
                                    default "16777216";
                                    description "Locally-configured stale routes override time";
                                }

                                leaf-list apply-groups {
                                    type leafref {
                                        path "../../../../../../../../groups/group/name";
                                    }
                                    max-elements 8;
                                    ordered-by user;
                                    description "Apply a configuration group at this level";
                                }

                                leaf-list apply-groups-exclude {
                                    type leafref {
                                        path "../../../../../../../../groups/group/name";
                                    }
                                    max-elements 8;
                                    ordered-by user;
                                    description "Exclude a configuration group at this level";
                                }

                            } // list family

                        } // container long-lived

                    } // container graceful-restart

                    list prefix-limit {
                        key "family";
                        description "Enter the prefix-limit list instance";

                        leaf family {
                            type enumeration {
                                enum ipv4                           { value 1; }
                                enum ipv6                           { value 3; }
                                enum mcast-ipv4                     { value 4; }
                                enum flow-ipv4                      { value 10; }
                                enum flow-ipv6                      { value 14; }
                                enum mcast-ipv6                     { value 16; }
                                enum label-ipv4                     { value 17; }
                            }
                            description "Address family to which the limit applies";
                        }

                        leaf maximum {
                            type uint32 {
                                range "1..4294967295";
                            }
                            mandatory true;
                            description "Maximum number of routes to be learned from a peer";
                        }

                        leaf log-only {
                            type boolean;
                            default "false";
                            description "Send warning message at threshold instead of take-down";
                        }

                        leaf threshold {
                            type uint32 {
                                range "1..100";
                            }
                            default "90";
                            description "Percentage threshold that triggers a warning message";
                        }

                        leaf idle-timeout {
                            type int32 {
                                range "1..1024";
                            }
                            description "Time which BGP peering remains idle before reconnecting";
                        }

                        leaf post-import {
                            type boolean;
                            default "false";
                            description "Apply limit only to routes accepted by import policies";
                        }

                        leaf hold-excess {
                            type int32 {
                                range "1..100";
                            }
                            description "Percentage of maximum routes to install in route table";
                        }

                        leaf-list apply-groups {
                            type leafref {
                                path "../../../../../../groups/group/name";
                            }
                            max-elements 8;
                            ordered-by user;
                            description "Apply a configuration group at this level";
                        }

                        leaf-list apply-groups-exclude {
                            type leafref {
                                path "../../../../../../groups/group/name";
                            }
                            max-elements 8;
                            ordered-by user;
                            description "Exclude a configuration group at this level";
                        }

                    } // list prefix-limit

                    container monitor {
                        presence "Enable the monitor context";
                        description "Enable the monitor context";

                        leaf all-stations {
                            type boolean;
                            default "false";
                            description "Send BMP messages to all configured stations";
                        }

                        leaf admin-state {
                            type types-sros:admin-state;
                            default "disable";
                            description "Administrative state of BMP monitoring";
                        }

                        leaf-list apply-groups {
                            type leafref {
                                path "../../../../../../groups/group/name";
                            }
                            max-elements 8;
                            ordered-by user;
                            description "Apply a configuration group at this level";
                        }

                        leaf-list apply-groups-exclude {
                            type leafref {
                                path "../../../../../../groups/group/name";
                            }
                            max-elements 8;
                            ordered-by user;
                            description "Exclude a configuration group at this level";
                        }

                        container route-monitoring {
                            description "Enter the route-monitoring context";

                            leaf pre-policy {
                                type boolean;
                                default "false";
                                description "Allow pre-policy route-monitoring messages to be sent";
                            }

                            leaf post-policy {
                                type boolean;
                                default "false";
                                description "Allow post-policy route-monitoring messages to be sent";
                            }

                        } // container route-monitoring

                        list station {
                            key "station-name";
                            max-elements 8;
                            description "Add a list entry for station";

                            leaf station-name {
                                type leafref {
                                    path "../../../../../../../bmp/station/name";
                                }
                                description "BMP monitoring station";
                            }

                        } // list station

                    } // container monitor

                    container evpn-link-bandwidth {
                        description "Enter the evpn-link-bandwidth context";

                        leaf add-to-received-bgp {
                            type union {
                                type int32 {
                                    range "1..128";
                                }
                            }
                            description "Weight added to received PE-CE BGP routes";
                        }

                    } // container evpn-link-bandwidth

                } // list neighbor

            } // container bgp

            container confederation {
                description "Enter the confederation context";

                leaf confed-as-num {
                    type inet:as-number {
                        range "1..4294967295";
                    }
                    description "Confederation number within an autonomous system";
                }

                list members {
                    key "as-number";
                    max-elements 256;
                    description "Add a list entry for members";

                    leaf as-number {
                        type inet:as-number {
                            range "1..4294967295";
                        }
                        description "Confederation AS number";
                    }

                } // list members

            } // container confederation

            container eth-cfm {
                description "Enter the eth-cfm context";

                leaf-list apply-groups {
                    type leafref {
                        path "../../../../groups/group/name";
                    }
                    max-elements 8;
                    ordered-by user;
                    description "Apply a configuration group at this level";
                }

                leaf-list apply-groups-exclude {
                    type leafref {
                        path "../../../../groups/group/name";
                    }
                    max-elements 8;
                    ordered-by user;
                    description "Exclude a configuration group at this level";
                }

            } // container eth-cfm

            container maximum-ipv4-routes {
                description "Enter the maximum-ipv4-routes context";

                leaf value {
                    type int32 {
                        range "1..2147483647";
                    }
                    sros-ext:auto-restart-to-modify;
                    description "Maximum number of routes that are configured on this virtual router";
                }

                leaf log-only {
                    type boolean;
                    default "false";
                    description "Action when the maximum number of routes, held within a VRF context, is reached";
                }

                leaf threshold {
                    type uint32 {
                        range "1..100";
                    }
                    units "percent";
                    description "Mid-level water marker for the number of routes which this VRF holds";
                }

            } // container maximum-ipv4-routes

            container maximum-ipv6-routes {
                description "Enter the maximum-ipv6-routes context";

                leaf value {
                    type int32 {
                        range "1..2147483647";
                    }
                    sros-ext:auto-restart-to-modify;
                    description "Maximum number of routes that are configured on this virtual router";
                }

                leaf log-only {
                    type boolean;
                    default "false";
                    description "Action when the maximum number of routes, held within a VRF context, is reached";
                }

                leaf threshold {
                    type uint32 {
                        range "1..100";
                    }
                    units "percent";
                    description "Mid-level water marker for the number of routes which this VRF holds";
                }

            } // container maximum-ipv6-routes

            container mc-maximum-routes {
                description "Enter the mc-maximum-routes context";

                leaf value {
                    type int32 {
                        range "1..2147483647";
                    }
                    description "Maximum multicast routes configured on virtual router";
                }

                leaf log-only {
                    type boolean;
                    default "false";
                    description "Log and allow learning of new multicast routes";
                }

                leaf threshold {
                    type uint32 {
                        range "1..100";
                    }
                    units "percent";
                    description "Maximum multicast routes which the VRF holds";
                }

            } // container mc-maximum-routes

            container mss-adjust {
                presence "Enable the mss-adjust context";
                description "Enable the mss-adjust context";

                leaf nat-group {
                    type uint32;
                    sros-ext:immutable;
                    mandatory true;
                    description "NAT group used for TCP-MSS adjustment";
                }

                leaf segment-size {
                    type uint32 {
                        range "160..10240";
                    }
                    mandatory true;
                    description "TCP-MSS option value in transmitted TCP SYN requests";
                }

                leaf-list apply-groups {
                    type leafref {
                        path "../../../../groups/group/name";
                    }
                    max-elements 8;
                    ordered-by user;
                    description "Apply a configuration group at this level";
                }

                leaf-list apply-groups-exclude {
                    type leafref {
                        path "../../../../groups/group/name";
                    }
                    max-elements 8;
                    ordered-by user;
                    description "Exclude a configuration group at this level";
                }

            } // container mss-adjust

            container reassembly {
                presence "Enable the reassembly context";
                description "Enable the reassembly context";

                leaf nat-group {
                    type uint32;
                    sros-ext:immutable;
                    description "NAT group (including WLAN Gateway group) that executes the reassembly";
                }

                leaf to-base-network {
                    type boolean;
                    default "false";
                    description "Allow reassembled traffic sent to network interface";
                }

                leaf-list apply-groups {
                    type leafref {
                        path "../../../../groups/group/name";
                    }
                    max-elements 8;
                    ordered-by user;
                    description "Apply a configuration group at this level";
                }

                leaf-list apply-groups-exclude {
                    type leafref {
                        path "../../../../groups/group/name";
                    }
                    max-elements 8;
                    ordered-by user;
                    description "Exclude a configuration group at this level";
                }

            } // container reassembly

            container sfm-overload {
                presence "Enable the sfm-overload context";
                description "Enable the sfm-overload context";

                leaf holdoff-time {
                    type uint32 {
                        range "1..600";
                    }
                    units "seconds";
                    description "Delay in detecting SFM failures and setting overload";
                }

            } // container sfm-overload

            container mtrace2 {
                description "Enter the mtrace2 context";

                leaf admin-state {
                    type types-sros:admin-state;
                    default "disable";
                    description "Administrative state of multicast path tracing";
                }

                leaf udp-port {
                    type uint32 {
                        range "1024..49151";
                    }
                    default "5000";
                    description "Destination and listening port for the mtrace2 command";
                }

            } // container mtrace2

            list aa-interface {
                key "interface-name";
                description "Enter the aa-interface list instance";

                leaf interface-name {
                    type types-sros:interface-name;
                    description "Interface name";
                }

                leaf description {
                    type types-sros:very-long-description;
                    description "Text description";
                }

                leaf admin-state {
                    type types-sros:admin-state;
                    default "enable";
                    description "Administrative state of the interface";
                }

                leaf ip-mtu {
                    type types-router:ip-mtu-ext;
                    units "bytes";
                    description "IP MTU applied to outgoing packets";
                }

                leaf-list apply-groups {
                    type leafref {
                        path "../../../../groups/group/name";
                    }
                    max-elements 8;
                    ordered-by user;
                    description "Apply a configuration group at this level";
                }

                leaf-list apply-groups-exclude {
                    type leafref {
                        path "../../../../groups/group/name";
                    }
                    max-elements 8;
                    ordered-by user;
                    description "Exclude a configuration group at this level";
                }

                list sap {
                    key "sap-id";
                    max-elements 1;
                    description "Enter the sap list instance";

                    leaf sap-id {
                        type types-sros:sap;
                        description "SAP ID";
                    }

                    leaf description {
                        type types-sros:long-description;
                        description "Text description";
                    }

                    leaf admin-state {
                        type types-sros:admin-state;
                        default "enable";
                        description "Administrative state of the SAP";
                    }

                    leaf-list apply-groups {
                        type leafref {
                            path "../../../../../groups/group/name";
                        }
                        max-elements 8;
                        ordered-by user;
                        description "Apply a configuration group at this level";
                    }

                    leaf-list apply-groups-exclude {
                        type leafref {
                            path "../../../../../groups/group/name";
                        }
                        max-elements 8;
                        ordered-by user;
                        description "Exclude a configuration group at this level";
                    }

                    container ingress {
                        description "Enter the ingress context";

                        container qos {
                            description "Enter the qos context";

                            container sap-ingress {
                                description "Enter the sap-ingress context";

                                leaf policy-name {
                                    type leafref {
                                        path "../../../../../../../../qos/sap-ingress/sap-ingress-policy-name";
                                    }
                                    description "Policy ID";
                                }

                                container overrides {
                                    description "Enter the overrides context";

                                } // container overrides

                            } // container sap-ingress

                        } // container qos

                    } // container ingress

                    container egress {
                        description "Enter the egress context";

                        container qos {
                            description "Enter the qos context";

                            container sap-egress {
                                description "Enter the sap-egress context";

                                leaf policy-name {
                                    type leafref {
                                        path "../../../../../../../../qos/sap-egress/sap-egress-policy-name";
                                    }
                                    description "Policy ID to associate with SAP for mirrored service";
                                }

                            } // container sap-egress

                        } // container qos

                        container filter {
                            description "Enter the filter context";

                            leaf ip {
                                type leafref {
                                    path "../../../../../../../filter/ip-filter/filter-name";
                                }
                                description "IPv4 filter policy name";
                            }

                        } // container filter

                        container virtual-port {
                            description "Enter the virtual-port context";

                            leaf vport-name {
                                type leafref {
                                    path "../../../../../../../port/ethernet/access/egress/virtual-port/vport-name";
                                }
                                description "Virtual port assigned to the SAP";
                            }

                        } // container virtual-port

                    } // container egress

                    container lag {
                        description "Enter the lag context";

                    } // container lag

                    container fwd-wholesale {
                        description "Enter the fwd-wholesale context";

                        leaf pppoe-service {
                            type leafref {
                                path "../../../../../epipe/service-name";
                            }
                            description "PPPoE service name";
                        }

                    } // container fwd-wholesale

                } // list sap

                container ipv4 {
                    description "Enter the ipv4 context";

                    container primary {
                        presence "Enable the primary context";
                        description "Enable the primary context";

                        leaf address {
                            type types-sros:ipv4-unicast-address;
                            mandatory true;
                            description "Primary IPv4 address assigned to the interface";
                        }

                        leaf prefix-length {
                            type uint32 {
                                range "0..32";
                            }
                            mandatory true;
                            description "IPv4 address prefix length";
                        }

                        leaf-list apply-groups {
                            type leafref {
                                path "../../../../../../groups/group/name";
                            }
                            max-elements 8;
                            ordered-by user;
                            description "Apply a configuration group at this level";
                        }

                        leaf-list apply-groups-exclude {
                            type leafref {
                                path "../../../../../../groups/group/name";
                            }
                            max-elements 8;
                            ordered-by user;
                            description "Exclude a configuration group at this level";
                        }

                    } // container primary

                } // container ipv4

            } // list aa-interface

            list dms-interface {
                key "interface-name";
                description "Enter the dms-interface list instance";

                leaf interface-name {
                    type types-sros:interface-name;
                    description "Interface name";
                }

                leaf description {
                    type types-sros:very-long-description;
                    description "Text description";
                }

                leaf admin-state {
                    type types-sros:admin-state;
                    default "enable";
                    description "Administrative state of the interface";
                }

                leaf ip-mtu {
                    type types-router:ip-mtu-ext;
                    units "bytes";
                    description "IP MTU applied to outgoing packets";
                }

                leaf-list apply-groups {
                    type leafref {
                        path "../../../../groups/group/name";
                    }
                    max-elements 8;
                    ordered-by user;
                    description "Apply a configuration group at this level";
                }

                leaf-list apply-groups-exclude {
                    type leafref {
                        path "../../../../groups/group/name";
                    }
                    max-elements 8;
                    ordered-by user;
                    description "Exclude a configuration group at this level";
                }

                list sap {
                    key "sap-id";
                    max-elements 1;
                    description "Enter the sap list instance";

                    leaf sap-id {
                        type types-sros:sap;
                        description "SAP identifier";
                    }

                    leaf description {
                        type types-sros:long-description;
                        description "Text description";
                    }

                    leaf admin-state {
                        type types-sros:admin-state;
                        default "enable";
                        description "Administrative state of the SAP";
                    }

                    leaf-list apply-groups {
                        type leafref {
                            path "../../../../../groups/group/name";
                        }
                        max-elements 8;
                        ordered-by user;
                        description "Apply a configuration group at this level";
                    }

                    leaf-list apply-groups-exclude {
                        type leafref {
                            path "../../../../../groups/group/name";
                        }
                        max-elements 8;
                        ordered-by user;
                        description "Exclude a configuration group at this level";
                    }

                    container ingress {
                        description "Enter the ingress context";

                        container qos {
                            description "Enter the qos context";

                            container sap-ingress {
                                description "Enter the sap-ingress context";

                                leaf policy-name {
                                    type leafref {
                                        path "../../../../../../../../qos/sap-ingress/sap-ingress-policy-name";
                                    }
                                    description "Policy ID";
                                }

                                container overrides {
                                    description "Enter the overrides context";

                                } // container overrides

                            } // container sap-ingress

                        } // container qos

                    } // container ingress

                    container egress {
                        description "Enter the egress context";

                        container qos {
                            description "Enter the qos context";

                            container sap-egress {
                                description "Enter the sap-egress context";

                                leaf policy-name {
                                    type leafref {
                                        path "../../../../../../../../qos/sap-egress/sap-egress-policy-name";
                                    }
                                    description "Policy ID to associate with SAP for mirrored service";
                                }

                            } // container sap-egress

                        } // container qos

                        container filter {
                            description "Enter the filter context";

                            leaf ip {
                                type leafref {
                                    path "../../../../../../../filter/ip-filter/filter-name";
                                }
                                description "IPv4 filter policy name";
                            }

                        } // container filter

                        container virtual-port {
                            description "Enter the virtual-port context";

                            leaf vport-name {
                                type leafref {
                                    path "../../../../../../../port/ethernet/access/egress/virtual-port/vport-name";
                                }
                                description "Virtual port assigned to the SAP";
                            }

                        } // container virtual-port

                    } // container egress

                    container lag {
                        description "Enter the lag context";

                    } // container lag

                    container fwd-wholesale {
                        description "Enter the fwd-wholesale context";

                        leaf pppoe-service {
                            type leafref {
                                path "../../../../../epipe/service-name";
                            }
                            description "PPPoE service name";
                        }

                    } // container fwd-wholesale

                } // list sap

                container ipv4 {
                    description "Enter the ipv4 context";

                    container primary {
                        presence "Enable the primary context";
                        description "Enable the primary context";

                        leaf address {
                            type types-sros:ipv4-unicast-address;
                            mandatory true;
                            description "Primary IPv4 address assigned to the interface";
                        }

                        leaf prefix-length {
                            type uint32 {
                                range "0..32";
                            }
                            mandatory true;
                            description "IPv4 address prefix length";
                        }

                        leaf-list apply-groups {
                            type leafref {
                                path "../../../../../../groups/group/name";
                            }
                            max-elements 8;
                            ordered-by user;
                            description "Apply a configuration group at this level";
                        }

                        leaf-list apply-groups-exclude {
                            type leafref {
                                path "../../../../../../groups/group/name";
                            }
                            max-elements 8;
                            ordered-by user;
                            description "Exclude a configuration group at this level";
                        }

                    } // container primary

                } // container ipv4

            } // list dms-interface

            list interface {
                key "interface-name";
                description "Enter the interface list instance";

                leaf interface-name {
                    type types-sros:interface-name;
                    description "Interface name";
                }

                leaf description {
                    type types-sros:very-long-description;
                    description "Text description";
                }

                leaf admin-state {
                    type types-sros:admin-state;
                    default "enable";
                    description "Administrative state of the interface";
                }

                leaf radius-auth-policy {
                    type leafref {
                        path "../../../../subscriber-mgmt/radius-authentication-policy/name";
                    }
                    description "Authentication policy";
                }

                leaf tunnel {
                    type boolean;
                    sros-ext:immutable;
                    default "false";
                    description "Enable/disable tunnel interface";
                }

                leaf loopback {
                    type boolean;
                    default "false";
                    description "Use interface as a loopback interface";
                }

                leaf monitor-oper-group {
                    type leafref {
                        path "../../../oper-group/name";
                    }
                    description "Operational group to monitor";
                }

                leaf shcv-policy-ipv4 {
                    when "not(../tunnel = 'true')" {
                        description "shcv-policy can't be used in a tunnel interface";
                    }
                    type leafref {
                        path "../../../../subscriber-mgmt/shcv-policy/name";
                    }
                    description "Host connectivity IPv4 policy";
                }

                leaf cpu-protection {
                    type leafref {
                        path "../../../../system/security/cpu-protection/policy/policy-id";
                    }
                    description "CPU protection policy";
                }

                leaf ip-mtu-profile {
                    type boolean;
                    default "false";
                    description "Enable the interface IP MTU profile";
                }

                leaf ip-mtu {
                    type types-router:ip-mtu-ext;
                    units "bytes";
                    description "IP MTU applied to outgoing packets";
                }

                leaf mac {
                    type types-sros:mac-unicast-address;
                    description "MAC address for the interface";
                }

                leaf tos-marking-state {
                    type types-router:tos-marking-state;
                    default "trusted";
                    description "TOS marking state";
                }

                leaf ingress-stats {
                    type boolean;
                    default "false";
                    description "Collect ingress statistics";
                }

                leaf mac-accounting {
                    type boolean;
                    default "false";
                    description "Enable MAC accounting functionality";
                }

                leaf vas-if-type {
                    when "../tunnel = 'false'" {
                        description "not allowed in a tunnel interface";
                    }
                    type types-router:vas-if-type;
                    description "VAS interface type";
                }

                leaf-list apply-groups {
                    type leafref {
                        path "../../../../groups/group/name";
                    }
                    max-elements 8;
                    ordered-by user;
                    description "Apply a configuration group at this level";
                }

                leaf-list apply-groups-exclude {
                    type leafref {
                        path "../../../../groups/group/name";
                    }
                    max-elements 8;
                    ordered-by user;
                    description "Exclude a configuration group at this level";
                }

                choice shunting {
                    description "shunting options";
                    case shunting-profile {

                        leaf multi-chassis-shunting-profile {
                            type leafref {
                                path "../../ipsec/multi-chassis-shunting-profile/name";
                            }
                            description "Multi-chassis shunting profile name";
                        }

                    }
                    case nexthop {

                        leaf static-tunnel-redundant-nexthop {
                            type types-sros:ipv4-unicast-address;
                            description "Address for the static ISA tunnel redundant next-hop";
                        }

                        leaf dynamic-tunnel-redundant-nexthop {
                            type types-sros:ipv4-unicast-address;
                            description "Redundant next-hop address for the dynamic IPsec tunnel";
                        }

                    }
                }
                container ptp-hw-assist {
                    description "Enter the ptp-hw-assist context";

                    leaf admin-state {
                        type types-sros:admin-state;
                        default "disable";
                        description "Administrative state of the PTP timestamping assist";
                    }

                    leaf-list apply-groups {
                        type leafref {
                            path "../../../../../groups/group/name";
                        }
                        max-elements 8;
                        ordered-by user;
                        description "Apply a configuration group at this level";
                    }

                    leaf-list apply-groups-exclude {
                        type leafref {
                            path "../../../../../groups/group/name";
                        }
                        max-elements 8;
                        ordered-by user;
                        description "Exclude a configuration group at this level";
                    }

                } // container ptp-hw-assist

                container ingress {
                    description "Enter the ingress context";

                    leaf policy-accounting {
                        type leafref {
                            path "../../../../../routing-options/policy-accounting/policy-acct-template/name";
                        }
                        description "Ingress policy accounting template name";
                    }

                    leaf destination-class-lookup {
                        type boolean;
                        default "false";
                        description "Enable BGP destination class lookup";
                    }

                } // container ingress

                container load-balancing {
                    description "Enter the load-balancing context";

                    leaf ip-load-balancing {
                        type types-router:ip-load-balancing;
                        default "both";
                        description "IP load-balancing algorithm";
                    }

                    leaf spi-load-balancing {
                        type boolean;
                        default "false";
                        description "Enable SPI use in hashing";
                    }

                    leaf teid-load-balancing {
                        type boolean;
                        default "false";
                        description "Enable use of TEID in hashing";
                    }

                    leaf flow-label-load-balancing {
                        type boolean;
                        default "false";
                        description "Enable flow label load balancing";
                    }

                } // container load-balancing

                container hold-time {
                    when "../tunnel = 'false' or not(../loopback = 'false')" {
                        description "not allowed in a tunnel interface unless it is a loopback interface";
                    }
                    description "Enter the hold-time context";

                    container ipv4 {
                        description "Enter the ipv4 context";

                        container up {
                            description "Enter the up context";

                            leaf seconds {
                                type types-router:hold-time-seconds;
                                units "seconds";
                                description "Up hold time for the IP interface";
                            }

                        } // container up

                        container down {
                            description "Enter the down context";

                            leaf seconds {
                                type types-router:hold-time-seconds;
                                units "seconds";
                                description "Down hold time for the IP interface";
                            }

                            leaf init-only {
                                type boolean;
                                default "false";
                                description "Apply delay only at interface configuration or reboot";
                            }

                        } // container down

                    } // container ipv4

                    container ipv6 {
                        description "Enter the ipv6 context";

                        container up {
                            description "Enter the up context";

                            leaf seconds {
                                type types-router:hold-time-seconds;
                                units "seconds";
                                description "Up hold time for the IP interface";
                            }

                        } // container up

                        container down {
                            description "Enter the down context";

                            leaf seconds {
                                type types-router:hold-time-seconds;
                                units "seconds";
                                description "Down hold time for the IP interface";
                            }

                            leaf init-only {
                                type boolean;
                                default "false";
                                description "Apply delay only at interface configuration or reboot";
                            }

                        } // container down

                    } // container ipv6

                } // container hold-time

                container ping-template {
                    presence "Enable the ping-template context";
                    description "Enable the ping-template context";

                    leaf name {
                        type leafref {
                            path "../../../../../test-oam/icmp/ping-template/name";
                        }
                        sros-ext:immutable;
                        mandatory true;
                        description "Ping template name";
                    }

                    leaf admin-state {
                        type types-sros:admin-state;
                        default "disable";
                        description "Administrative state of the ping template";
                    }

                    leaf destination-address {
                        type types-sros:ipv4-unicast-address;
                        sros-ext:auto-restart-to-modify;
                        description "Ping template destination address";
                    }

                    leaf-list apply-groups {
                        type leafref {
                            path "../../../../../groups/group/name";
                        }
                        max-elements 8;
                        ordered-by user;
                        description "Apply a configuration group at this level";
                    }

                    leaf-list apply-groups-exclude {
                        type leafref {
                            path "../../../../../groups/group/name";
                        }
                        max-elements 8;
                        ordered-by user;
                        description "Exclude a configuration group at this level";
                    }

                } // container ping-template

                container ipsec {
                    presence "Enable the ipsec context";
                    description "Enable the ipsec context";

                    leaf admin-state {
                        type types-sros:admin-state;
                        default "disable";
                        description "Administrative state of IPsec secured interface";
                    }

                    leaf tunnel-group {
                        type leafref {
                            path "../../../../../isa/tunnel-group/id";
                        }
                        sros-ext:immutable;
                        mandatory true;
                        description "Tunnel group ID";
                    }

                    leaf public-sap {
                        type uint32 {
                            range "0..4094";
                        }
                        sros-ext:immutable;
                        mandatory true;
                        description "Public SAP ID";
                    }

                    leaf ip-exception {
                        type leafref {
                            path "../../../../../filter/ip-exception/filter-name";
                        }
                        description "IP exception filter";
                    }

                    leaf ipv6-exception {
                        type leafref {
                            path "../../../../../filter/ipv6-exception/filter-name";
                        }
                        description "IPv6 filter exception used to bypass encryption";
                    }

                    leaf-list apply-groups {
                        type leafref {
                            path "../../../../../groups/group/name";
                        }
                        max-elements 8;
                        ordered-by user;
                        description "Apply a configuration group at this level";
                    }

                    leaf-list apply-groups-exclude {
                        type leafref {
                            path "../../../../../groups/group/name";
                        }
                        max-elements 8;
                        ordered-by user;
                        description "Exclude a configuration group at this level";
                    }

                    list ipsec-tunnel {
                        key "name";
                        description "Enter the ipsec-tunnel list instance";

                        leaf name {
                            type types-sros:named-item {
                                pattern "[a-zA-Z]+.*" {
                                    error-message "IPSec tunnel name cannot start with a number";
                                }
                            }
                            description "IPsec tunnel name";
                        }

                        leaf private-sap {
                            type uint32 {
                                range "0..4094";
                            }
                            sros-ext:immutable;
                            sros-ext:auto-restart-to-modify;
                            mandatory true;
                            description "Private SAP ID";
                        }

                        leaf admin-state {
                            type types-sros:admin-state;
                            default "disable";
                            description "Administrative state of the IPsec tunnel";
                        }

                        leaf description {
                            type types-sros:description;
                            description "Text description";
                        }

                        leaf clear-df-bit {
                            type boolean;
                            sros-ext:auto-restart-to-modify;
                            default "false";
                            description "Reset the DF bit to 0 in all payload IP packets";
                        }

                        leaf copy-traffic-class-upon-decapsulation {
                            type boolean;
                            sros-ext:auto-restart-to-modify;
                            default "false";
                            description "Enable traffic class copy upon decapsulation";
                        }

                        leaf encapsulated-ip-mtu {
                            type uint32 {
                                range "512..9000";
                            }
                            units "bytes";
                            sros-ext:auto-restart-to-modify;
                            description "Maximum size of the encapsulated tunnel packet";
                        }

                        leaf ip-mtu {
                            type uint32 {
                                range "512..9000";
                            }
                            units "bytes";
                            sros-ext:auto-restart-to-modify;
                            description "Private MTU of the IPsec tunnel";
                        }

                        leaf replay-window {
                            type uint32 {
                                range "32|64|128|256|512";
                            }
                            units "packets";
                            sros-ext:auto-restart-to-modify;
                            description "Anti-replay window size";
                        }

                        leaf public-tcp-mss-adjust {
                            type union {
                                type uint32 {
                                    range "512..9000";
                                }
                                type enumeration {
                                    enum auto                           { value 0; }
                                }
                            }
                            units "bytes";
                            sros-ext:auto-restart-to-modify;
                            description "TCP maximum segment size (MSS) on the public network";
                        }

                        leaf private-tcp-mss-adjust {
                            type int32 {
                                range "512..9000";
                            }
                            units "bytes";
                            sros-ext:auto-restart-to-modify;
                            description "TCP maximum segment size (MSS) adjustment";
                        }

                        leaf local-gateway-address-override {
                            type types-sros:ip-address;
                            sros-ext:auto-restart-to-modify;
                            description "Local IPsec tunnel endpoint address";
                        }

                        leaf remote-gateway-address {
                            type types-sros:ip-address;
                            sros-ext:auto-restart-to-modify;
                            description "Remote IPsec tunnel endpoint address";
                        }

                        leaf private-service {
                            type types-services:service-name;
                            sros-ext:immutable;
                            sros-ext:auto-restart-to-modify;
                            description "Private service name";
                        }

                        leaf propagate-pmtu-v4 {
                            type boolean;
                            sros-ext:auto-restart-to-modify;
                            default "true";
                            description "Enable propagation of the path MTU to IPv4 hosts";
                        }

                        leaf propagate-pmtu-v6 {
                            type boolean;
                            sros-ext:auto-restart-to-modify;
                            default "true";
                            description "Enable propagation of the path MTU to IPv6 hosts";
                        }

                        leaf pmtu-discovery-aging {
                            type uint32 {
                                range "900..3600";
                            }
                            units "seconds";
                            sros-ext:auto-restart-to-modify;
                            default "900";
                            description "Aging out time of the learned path MTU";
                        }

                        leaf-list apply-groups {
                            type leafref {
                                path "../../../../../../groups/group/name";
                            }
                            max-elements 8;
                            ordered-by user;
                            sros-ext:auto-restart-to-modify;
                            description "Apply a configuration group at this level";
                        }

                        leaf-list apply-groups-exclude {
                            type leafref {
                                path "../../../../../../groups/group/name";
                            }
                            max-elements 8;
                            ordered-by user;
                            sros-ext:auto-restart-to-modify;
                            description "Exclude a configuration group at this level";
                        }

                        container bfd {
                            sros-ext:auto-restart-to-modify;
                            description "Enter the bfd context";

                            leaf bfd-designate {
                                type boolean;
                                sros-ext:auto-restart-to-modify;
                                default "false";
                                description "Designate IPsec tunnel to carry BFD traffic";
                            }

                            container bfd-liveness {
                                presence "Enable the bfd-liveness context";
                                sros-ext:auto-restart-to-modify;
                                description "Enable the bfd-liveness context";

                                leaf dest-ip {
                                    type types-sros:ipv4-unicast-address;
                                    sros-ext:auto-restart-to-modify;
                                    mandatory true;
                                    description "Destination address used for the BFD session";
                                }

                                leaf interface {
                                    type types-sros:interface-name;
                                    sros-ext:auto-restart-to-modify;
                                    mandatory true;
                                    description "Name of the interface used by the BFD session";
                                }

                                leaf service-name {
                                    type types-services:service-name;
                                    sros-ext:auto-restart-to-modify;
                                    mandatory true;
                                    description "Administrative service name";
                                }

                            } // container bfd-liveness

                        } // container bfd

                        container icmp6-generation {
                            sros-ext:auto-restart-to-modify;
                            description "Enter the icmp6-generation context";

                            container packet-too-big {
                                sros-ext:auto-restart-to-modify;
                                description "Enter the packet-too-big context";

                                leaf admin-state {
                                    type types-sros:admin-state;
                                    sros-ext:auto-restart-to-modify;
                                    default "enable";
                                    description "Administrative state of Packet Too Big message sends";
                                }

                                leaf message-count {
                                    type uint32 {
                                        range "10..1000";
                                    }
                                    sros-ext:auto-restart-to-modify;
                                    default "100";
                                    description "Maximum number of ICMPv6 PTB messages that can be sent";
                                }

                                leaf interval {
                                    type uint32 {
                                        range "1..60";
                                    }
                                    units "seconds";
                                    sros-ext:auto-restart-to-modify;
                                    default "10";
                                    description "Interval for sending Packet Too Big messages";
                                }

                            } // container packet-too-big

                        } // container icmp6-generation

                        container key-exchange {
                            sros-ext:auto-restart-to-modify;
                            description "Enter the key-exchange context";

                            choice type {
                                case dynamic {

                                    container dynamic {
                                        presence "Enable the dynamic context";
                                        sros-ext:auto-restart-to-modify;
                                        description "Enable the dynamic context";

                                        leaf auto-establish {
                                            type boolean;
                                            sros-ext:auto-restart-to-modify;
                                            default "false";
                                            description "Attempt to establish a phase 1 exchange automatically";
                                        }

                                        leaf ike-policy {
                                            type leafref {
                                                path "../../../../../../../../ipsec/ike-policy/id";
                                            }
                                            sros-ext:auto-restart-to-modify;
                                            description "IKE policy ID";
                                        }

                                        leaf-list ipsec-transform {
                                            type leafref {
                                                path "../../../../../../../../ipsec/ipsec-transform/id";
                                            }
                                            max-elements 4;
                                            sros-ext:auto-restart-to-modify;
                                            description "IPsec transform IDs used by the dynamic key";
                                        }

                                        leaf pre-shared-key {
                                            type types-sros:encrypted-leaf {
                                                length "1..115";
                                            }
                                            sros-ext:auto-restart-to-modify;
                                            description "Pre-shared key for authentication";
                                        }

                                        container cert {
                                            sros-ext:auto-restart-to-modify;
                                            description "Enter the cert context";

                                            leaf cert-profile {
                                                type leafref {
                                                    path "../../../../../../../../../ipsec/cert-profile/name";
                                                }
                                                description "Certificate profile name";
                                            }

                                            leaf trust-anchor-profile {
                                                type leafref {
                                                    path "../../../../../../../../../ipsec/trust-anchor-profile/name";
                                                }
                                                description "Trust anchor profile name";
                                            }

                                            container status-verify {
                                                sros-ext:auto-restart-to-modify;
                                                description "Enter the status-verify context";

                                                leaf default-result {
                                                    type enumeration {
                                                        enum revoked                        { value 0; }
                                                        enum good                           { value 1; }
                                                    }
                                                    default "revoked";
                                                    description "Default result for Certificate Status Verification";
                                                }

                                                leaf primary {
                                                    type types-ipsec:cert-revocation-status;
                                                    default "crl";
                                                    description "Primary method of CSV to verify the revocation status";
                                                }

                                                leaf secondary {
                                                    type types-ipsec:cert-revocation-status-with-none;
                                                    default "none";
                                                    description "Secondary method used to verify certificate revocation";
                                                }

                                            } // container status-verify

                                        } // container cert

                                        container id {
                                            sros-ext:auto-restart-to-modify;
                                            description "Enter the id context";

                                            choice id {
                                                case ipv4 {

                                                    leaf ipv4 {
                                                        type types-sros:ipv4-unicast-address;
                                                        sros-ext:auto-restart-to-modify;
                                                        description "IPv4 as the local ID type";
                                                    }

                                                }
                                                case ipv6 {

                                                    leaf ipv6 {
                                                        type types-sros:ip-address;
                                                        sros-ext:auto-restart-to-modify;
                                                        description "IPv6 used as the local IKE ID type";
                                                    }

                                                }
                                                case fqdn {

                                                    leaf fqdn {
                                                        type types-sros:fully-qualified-domain-name;
                                                        sros-ext:auto-restart-to-modify;
                                                        description "FQDN used as the local ID IKE type";
                                                    }

                                                }
                                            }
                                        } // container id


                                    } // container dynamic

                                }
                                case manual {

                                    container manual {
                                        presence "Enable the manual context";
                                        sros-ext:auto-restart-to-modify;
                                        description "Enable the manual context";

                                        list keys {
                                            key "security-association direction";
                                            description "Enter the keys list instance";

                                            leaf security-association {
                                                type uint32 {
                                                    range "1..16";
                                                }
                                                description "SA entry ID";
                                            }

                                            leaf direction {
                                                type enumeration {
                                                    enum inbound                        { value 1; }
                                                    enum outbound                       { value 2; }
                                                }
                                                description "Direction of the IPsec tunnel";
                                            }

                                            leaf ipsec-transform {
                                                type leafref {
                                                    path "../../../../../../../../../ipsec/ipsec-transform/id";
                                                }
                                                sros-ext:immutable;
                                                mandatory true;
                                                description "Transform entry used by manual SAs";
                                            }

                                            leaf spi {
                                                type uint32 {
                                                    range "256..16383";
                                                }
                                                sros-ext:immutable;
                                                mandatory true;
                                                description "SPI of inbound and outbound packets";
                                            }

                                            leaf authentication-key {
                                                type types-sros:hex-string {
                                                    length "1..130";
                                                }
                                                sros-ext:immutable;
                                                description "Key used for the authentication algorithm";
                                            }

                                            leaf encryption-key {
                                                type types-sros:hex-string {
                                                    length "1..66";
                                                }
                                                sros-ext:immutable;
                                                description "Key used for the encryption algorithm";
                                            }

                                            leaf-list apply-groups {
                                                type leafref {
                                                    path "../../../../../../../../../groups/group/name";
                                                }
                                                max-elements 8;
                                                ordered-by user;
                                                description "Apply a configuration group at this level";
                                            }

                                            leaf-list apply-groups-exclude {
                                                type leafref {
                                                    path "../../../../../../../../../groups/group/name";
                                                }
                                                max-elements 8;
                                                ordered-by user;
                                                description "Exclude a configuration group at this level";
                                            }

                                        } // list keys

                                    } // container manual

                                }
                            }
                        } // container key-exchange

                        container max-history-key-records {
                            sros-ext:auto-restart-to-modify;
                            description "Enter the max-history-key-records context";

                            leaf ike {
                                type uint32 {
                                    range "1..3";
                                }
                                sros-ext:auto-restart-to-modify;
                                description "Maximum number of historical IKE key records";
                            }

                            leaf esp {
                                type uint32 {
                                    range "1..48";
                                }
                                sros-ext:auto-restart-to-modify;
                                description "Maximum number of recent records";
                            }

                        } // container max-history-key-records

                        container icmp-generation {
                            sros-ext:auto-restart-to-modify;
                            description "Enter the icmp-generation context";

                            container frag-required {
                                sros-ext:auto-restart-to-modify;
                                description "Enter the frag-required context";

                                leaf admin-state {
                                    type types-sros:admin-state;
                                    sros-ext:auto-restart-to-modify;
                                    default "enable";
                                    description "Administrative state of sending ICMP messages";
                                }

                                leaf message-count {
                                    type uint32 {
                                        range "10..1000";
                                    }
                                    sros-ext:auto-restart-to-modify;
                                    default "100";
                                    description "Maximum number of ICMP messages that can be sent";
                                }

                                leaf interval {
                                    type uint32 {
                                        range "1..60";
                                    }
                                    units "seconds";
                                    sros-ext:auto-restart-to-modify;
                                    default "10";
                                    description "Interval for sending ICMP messages";
                                }

                            } // container frag-required

                        } // container icmp-generation


                        container security-policy {
                            sros-ext:auto-restart-to-modify;
                            description "Enter the security-policy context";

                            leaf id {
                                type uint32;
                                sros-ext:auto-restart-to-modify;
                                description "Security policy ID for use by the tunnel";
                            }

                            leaf strict-match {
                                type boolean;
                                sros-ext:auto-restart-to-modify;
                                default "false";
                                description "Enable strict match of the security policy entry";
                            }

                        } // container security-policy

                    } // list ipsec-tunnel

                } // container ipsec

                container cflowd-parameters {
                    description "Enter the cflowd-parameters context";

                    list sampling {
                        key "sampling-type";
                        description "Enter the sampling list instance";

                        leaf sampling-type {
                            type types-router:cflowd-sampling;
                            description "Traffic sampling type";
                        }

                        leaf type {
                            when "not(../sampling-type = 'both')";
                            type enumeration {
                                enum acl                            { value 1; }
                                enum interface                      { value 2; }
                            }
                            mandatory true;
                            description "Type of cflowd analysis";
                        }

                        leaf direction {
                            type enumeration {
                                enum ingress-only                   { value 1; }
                                enum egress-only                    { value 2; }
                                enum both                           { value 3; }
                            }
                            default "ingress-only";
                            description "Direction of traffic for cflowd sampling";
                        }

                        leaf sample-profile {
                            type union {
                                type enumeration {
                                    enum 1                              { value 1; }
                                }
                                type uint32;
                            }
                            description "Sample profile ID";
                        }

                        leaf-list apply-groups {
                            type leafref {
                                path "../../../../../../groups/group/name";
                            }
                            max-elements 8;
                            ordered-by user;
                            description "Apply a configuration group at this level";
                        }

                        leaf-list apply-groups-exclude {
                            type leafref {
                                path "../../../../../../groups/group/name";
                            }
                            max-elements 8;
                            ordered-by user;
                            description "Exclude a configuration group at this level";
                        }

                    } // list sampling

                } // container cflowd-parameters

                container ipv4 {
                    description "Enter the ipv4 context";

                    leaf tcp-mss {
                        type types-router:ipv4-tcp-mss-ext;
                        description "TCP maximum segment size for the interface";
                    }

                    leaf allow-directed-broadcasts {
                        type boolean;
                        default "false";
                        description "Forward directed broadcasts";
                    }

                    leaf local-dhcp-server {
                        when "../../tunnel = 'false'" {
                            description "not allowed in a tunnel interface";
                        }
                        type leafref {
                            path "../../../dhcp-server/dhcpv4/name";
                        }
                        description "DHCP server for the interface";
                    }

                    leaf qos-route-lookup {
                        type types-router:qos-route-lookup;
                        description "IP address for QoS route lookup for ingress IP packets";
                    }

                    leaf ip-helper-address {
                        type types-sros:ipv4-unicast-address;
                        description "Gateway address";
                    }

                    container icmp {
                        description "Enter the icmp context";

                        leaf mask-reply {
                            type boolean;
                            default "true";
                            description "Allow responses to ICMP mask requests on the interface";
                        }

                        container redirects {
                            description "Enter the redirects context";

                            leaf admin-state {
                                type types-sros:admin-state;
                                default "enable";
                                description "Administrative state of sending ICMP redirect messages";
                            }

                            leaf number {
                                type uint16 {
                                    range "10..1000";
                                }
                                default "100";
                                description "Maximum number of ICMP redirect messages to send";
                            }

                            leaf seconds {
                                type uint16 {
                                    range "1..60";
                                }
                                units "seconds";
                                default "10";
                                description "Time used to limit the number of ICMP redirect messages";
                            }

                        } // container redirects

                        container ttl-expired {
                            description "Enter the ttl-expired context";

                            leaf admin-state {
                                type types-sros:admin-state;
                                default "enable";
                                description "Administrative state of sending TTL expired messages";
                            }

                            leaf number {
                                type uint16 {
                                    range "10..2000";
                                }
                                default "100";
                                description "Maximum number of TTL expired messages to send";
                            }

                            leaf seconds {
                                type uint16 {
                                    range "1..60";
                                }
                                units "seconds";
                                default "10";
                                description "Time used to limit the number of TTL expired messages";
                            }

                        } // container ttl-expired

                        container unreachables {
                            description "Enter the unreachables context";

                            leaf admin-state {
                                type types-sros:admin-state;
                                default "enable";
                                description "Administrative state of sending unreachable messages";
                            }

                            leaf number {
                                type uint16 {
                                    range "10..2000";
                                }
                                default "100";
                                description "Maximum number of unreachable messages to send";
                            }

                            leaf seconds {
                                type uint16 {
                                    range "1..60";
                                }
                                units "seconds";
                                default "10";
                                description "Time to limit the number of ICMP unreachable messages";
                            }

                        } // container unreachables

                        container param-problem {
                            description "Enter the param-problem context";

                            leaf admin-state {
                                type types-sros:admin-state;
                                default "enable";
                                description "Administrative state of sent Parameter Problem messages";
                            }

                            leaf number {
                                type uint32 {
                                    range "10..1000";
                                }
                                default "100";
                                description "Maximum number of Parameter Problem messages to send";
                            }

                            leaf seconds {
                                type uint32 {
                                    range "1..60";
                                }
                                units "seconds";
                                default "10";
                                description "Time used to limit number of Parameter Problem messages";
                            }

                        } // container param-problem

                    } // container icmp

                    container unnumbered {
                        description "Enter the unnumbered context";

                        choice source {
                            case ip-address {

                                leaf ip-address {
                                    type types-sros:ipv4-unicast-address;
                                    description "IP address for the interface";
                                }

                            }
                            case ip-int-name {

                                leaf ip-int-name {
                                    type types-sros:interface-name;
                                    description "IP interface name";
                                }

                            }
                        }
                    } // container unnumbered

                    container urpf-check {
                        presence "Enable the urpf-check context";
                        description "Enable the urpf-check context";

                        leaf ignore-default {
                            type boolean;
                            default "false";
                            description "Ignore default route when performing a uRPF check";
                        }

                        leaf mode {
                            type types-router:urpf-check-mode;
                            default "strict";
                            description "Unicast RPF check mode";
                        }

                    } // container urpf-check

                    container bfd {
                        description "Enter the bfd context";

                        leaf admin-state {
                            type types-sros:admin-state;
                            default "disable";
                            description "Administrative state of BFD sessions";
                        }

                        leaf transmit-interval {
                            type uint32 {
                                range "10..100000";
                            }
                            units "milliseconds";
                            default "100";
                            description "BFD transmit interval over this interface";
                        }

                        leaf receive {
                            type uint32 {
                                range "10..100000";
                            }
                            units "milliseconds";
                            default "100";
                            description "BFD receive interval over this interface";
                        }

                        leaf multiplier {
                            type uint32 {
                                range "1..20";
                            }
                            default "3";
                            description "Number of consecutive BFD messages missed from the peer";
                        }

                        leaf echo-receive {
                            type uint32 {
                                range "100..100000";
                            }
                            units "milliseconds";
                            description "Minimum echo interval over this interface";
                        }

                        leaf type {
                            type enumeration {
                                enum cpm-np                         { value 1; }
                                enum auto                           { value 2; }
                                enum fp                             { value 3; }
                            }
                            default "auto";
                            description "Local termination point for the BFD session";
                        }

                    } // container bfd

                    container primary {
                        presence "Enable the primary context";
                        description "Enable the primary context";

                        leaf address {
                            type types-sros:ipv4-unicast-address;
                            mandatory true;
                            description "Primary IPv4 address assigned to the interface";
                        }

                        leaf prefix-length {
                            type uint32 {
                                range "0..32";
                            }
                            mandatory true;
                            description "IPv4 address prefix length";
                        }

                        leaf broadcast {
                            type types-services:broadcast-address-format;
                            default "host-ones";
                            description "Broadcast address format";
                        }

                        leaf track-srrp {
                            type uint32 {
                                range "1..4294967295";
                            }
                            description "SRRP instance whose state is tracked on the IP address";
                        }

                        leaf-list apply-groups {
                            type leafref {
                                path "../../../../../../groups/group/name";
                            }
                            max-elements 8;
                            ordered-by user;
                            description "Apply a configuration group at this level";
                        }

                        leaf-list apply-groups-exclude {
                            type leafref {
                                path "../../../../../../groups/group/name";
                            }
                            max-elements 8;
                            ordered-by user;
                            description "Exclude a configuration group at this level";
                        }

                    } // container primary

                    list secondary {
                        key "address";
                        description "Enter the secondary list instance";

                        leaf address {
                            type types-sros:ipv4-unicast-address;
                            description "Secondary IPv4 address assigned to the interface";
                        }

                        leaf prefix-length {
                            type uint32 {
                                range "0..32";
                            }
                            mandatory true;
                            description "IPv4 address prefix length";
                        }

                        leaf igp-inhibit {
                            type boolean;
                            default "false";
                            description "Disable the running IGP from recognizing secondary IP";
                        }

                        leaf broadcast {
                            type types-services:broadcast-address-format;
                            default "host-ones";
                            description "Broadcast address format";
                        }

                        leaf track-srrp {
                            type uint32 {
                                range "1..4294967295";
                            }
                            description "SRRP instance whose state is tracked on the IP address";
                        }

                        leaf-list apply-groups {
                            type leafref {
                                path "../../../../../../groups/group/name";
                            }
                            max-elements 8;
                            ordered-by user;
                            description "Apply a configuration group at this level";
                        }

                        leaf-list apply-groups-exclude {
                            type leafref {
                                path "../../../../../../groups/group/name";
                            }
                            max-elements 8;
                            ordered-by user;
                            description "Exclude a configuration group at this level";
                        }

                    } // list secondary

                    container addresses {
                        description "Enter the addresses context";

                        list address {
                            key "ipv4-address";
                            description "Enter the address list instance";

                            leaf ipv4-address {
                                type types-sros:ipv4-unicast-address;
                                description "IPv4 address for the interface";
                            }

                            leaf prefix-length {
                                type uint32 {
                                    range "0..32";
                                }
                                mandatory true;
                                description "IPv4 address prefix length";
                            }

                            leaf-list apply-groups {
                                type leafref {
                                    path "../../../../../../../groups/group/name";
                                }
                                max-elements 8;
                                ordered-by user;
                                description "Apply a configuration group at this level";
                            }

                            leaf-list apply-groups-exclude {
                                type leafref {
                                    path "../../../../../../../groups/group/name";
                                }
                                max-elements 8;
                                ordered-by user;
                                description "Exclude a configuration group at this level";
                            }

                        } // list address

                    } // container addresses

                    container neighbor-discovery {
                        when "../../tunnel = 'false'" {
                            description "not allowed in a tunnel interface";
                        }
                        description "Enter the neighbor-discovery context";

                        leaf timeout {
                            type uint32 {
                                range "0..65535";
                            }
                            units "seconds";
                            default "14400";
                            description "Timeout for an ARP entry learned on the interface";
                        }

                        leaf retry-timer {
                            type uint32 {
                                range "1..300";
                            }
                            units "deciseconds";
                            default "50";
                            description "ARP retry interval";
                        }

                        leaf learn-unsolicited {
                            type boolean;
                            default "false";
                            description "Learn new entries from any received NA message";
                        }

                        leaf proactive-refresh {
                            type boolean;
                            default "false";
                            description "Send a single refresh message before entry timeout";
                        }

                        leaf populate {
                            type boolean;
                            default "false";
                            description "Allow static and dynamic hosts to be populated in system ARP cache";
                        }

                        leaf populate-host {
                            status obsolete;
                            type boolean;
                            default "false";
                            description "Allow addition or deletion of host routes in route table derived from ARP entries in ARP cache";
                        }

                        leaf route-tag {
                            status obsolete;
                            type types-router:route-tag;
                            description "ARP route tag";
                        }

                        leaf local-proxy-arp {
                            type boolean;
                            description "Enable local proxy ARP on interface";
                        }

                        leaf remote-proxy-arp {
                            type boolean;
                            default "false";
                            description "Enable remote proxy ARP on the interface";
                        }

                        leaf-list proxy-arp-policy {
                            type leafref {
                                path "../../../../../../policy-options/policy-statement/name";
                            }
                            max-elements 5;
                            ordered-by user;
                            description "Proxy ARP policy name";
                        }

                        container host-route {
                            description "Enter the host-route context";

                            list populate {
                                key "route-type";
                                description "Enter the populate list instance";

                                leaf route-type {
                                    type enumeration {
                                        enum static                         { value 1; }
                                        enum dynamic                        { value 2; }
                                        enum evpn                           { value 3; }
                                    }
                                    description "Type of ARP or ND entries that generate host routes";
                                }

                                leaf route-tag {
                                    type uint32 {
                                        range "1..255";
                                    }
                                    sros-ext:immutable;
                                    description "Tag value used with the host route from an ARP/ND entry";
                                }

                                leaf-list apply-groups {
                                    type leafref {
                                        path "../../../../../../../../groups/group/name";
                                    }
                                    max-elements 8;
                                    ordered-by user;
                                    description "Apply a configuration group at this level";
                                }

                                leaf-list apply-groups-exclude {
                                    type leafref {
                                        path "../../../../../../../../groups/group/name";
                                    }
                                    max-elements 8;
                                    ordered-by user;
                                    description "Exclude a configuration group at this level";
                                }

                            } // list populate

                        } // container host-route

                        container limit {
                            description "Enter the limit context";

                            leaf max-entries {
                                type types-router:ipv4-neighbor-limit;
                                description "Maximum number of entries learned on an IP interface";
                            }

                            leaf log-only {
                                type boolean;
                                default "false";
                                description "Generate log entries only if limit is reached";
                            }

                            leaf threshold {
                                type uint32 {
                                    range "1..100";
                                }
                                units "percent";
                                default "90";
                                description "Threshold value that triggers a warning message";
                            }

                        } // container limit

                        container static-neighbor-unnumbered {
                            when "../../unnumbered/ip-address or ../../unnumbered/ip-int-name" {
                                description "only allowed in unnumbered interfaces";
                            }
                            presence "Enable the static-neighbor-unnumbered context";
                            description "Enable the static-neighbor-unnumbered context";

                            leaf mac-address {
                                type yang:mac-address;
                                mandatory true;
                                description "MAC address for the static neighbor";
                            }

                        } // container static-neighbor-unnumbered

                        list static-neighbor {
                            when "not(../../unnumbered/ip-address) and not(../../unnumbered/ip-int-name)" {
                                description "not allowed in unnumbered interfaces";
                            }
                            key "ipv4-address";
                            description "Enter the static-neighbor list instance";

                            leaf ipv4-address {
                                type types-sros:ipv4-address;
                                description "IPv4 address that corresponds to the physical address";
                            }

                            leaf mac-address {
                                type yang:mac-address;
                                mandatory true;
                                description "MAC address for the static neighbor";
                            }

                            leaf-list apply-groups {
                                type leafref {
                                    path "../../../../../../../groups/group/name";
                                }
                                max-elements 8;
                                ordered-by user;
                                description "Apply a configuration group at this level";
                            }

                            leaf-list apply-groups-exclude {
                                type leafref {
                                    path "../../../../../../../groups/group/name";
                                }
                                max-elements 8;
                                ordered-by user;
                                description "Exclude a configuration group at this level";
                            }

                        } // list static-neighbor

                    } // container neighbor-discovery

                    container dhcp {
                        description "Enter the dhcp context";

                        leaf admin-state {
                            type types-sros:admin-state;
                            description "Administrative state of DHCP";
                        }

                        leaf description {
                            type types-sros:description;
                            description "Text description";
                        }

                        leaf python-policy {
                            when "../../../tunnel = 'false'" {
                                description "not allowed in a tunnel interface";
                            }
                            type leafref {
                                path "../../../../../../python/python-policy/name";
                            }
                            description "Python policy";
                        }

                        leaf-list server {
                            type types-sros:ipv4-unicast-address;
                            max-elements 8;
                            ordered-by user;
                            description "IP addresses for DHCP server requests";
                        }

                        leaf trusted {
                            type boolean;
                            default "false";
                            description "Relay untrusted packets";
                        }

                        leaf gi-address {
                            type types-sros:ipv4-unicast-address;
                            description "GI address for the DHCP relay";
                        }

                        leaf release-include-gi-address {
                            type boolean;
                            default "false";
                            description "Include gateway IP address in DHCP Release messages";
                        }

                        leaf src-ip-addr {
                            type enumeration {
                                enum auto                           { value 0; }
                                enum gi-address                     { value 1; }
                            }
                            default "auto";
                            description "Type of source address to use for DHCP relay";
                        }

                        leaf relay-plain-bootp {
                            when "../../../tunnel = 'false'" {
                                description "not allowed in a tunnel interface";
                            }
                            type boolean;
                            default "false";
                            description "Enable relaying of plain BOOTP packets";
                        }

                        leaf use-arp {
                            when "../../../tunnel = 'false'" {
                                description "not allowed in a tunnel interface";
                            }
                            type boolean;
                            default "false";
                            description "Use ARP to determine the destination hardware address";
                        }

                        leaf-list apply-groups {
                            type leafref {
                                path "../../../../../../groups/group/name";
                            }
                            max-elements 8;
                            ordered-by user;
                            description "Apply a configuration group at this level";
                        }

                        leaf-list apply-groups-exclude {
                            type leafref {
                                path "../../../../../../groups/group/name";
                            }
                            max-elements 8;
                            ordered-by user;
                            description "Exclude a configuration group at this level";
                        }

                        container proxy-server {
                            description "Enter the proxy-server context";

                            leaf admin-state {
                                type types-sros:admin-state;
                                default "disable";
                                description "Administrative state of the DHCP proxy server";
                            }

                            leaf emulated-server {
                                type types-sros:ipv4-unicast-address;
                                description "IP address used as the DHCP server address for the SAP";
                            }

                            container lease-time {
                                description "Enter the lease-time context";

                                leaf value {
                                    type types-sros:time-duration {
                                        range "300..315446399";
                                    }
                                    units "seconds";
                                    description "DHCP lease time";
                                }

                                leaf radius-override {
                                    type boolean;
                                    default "false";
                                    description "Use lease time information provided by RADIUS server";
                                }

                            } // container lease-time

                        } // container proxy-server

                        container option-82 {
                            description "Enter the option-82 context";

                            leaf action {
                                type enumeration {
                                    enum replace                        { value 1; }
                                    enum drop                           { value 2; }
                                    enum keep                           { value 3; }
                                }
                                default "keep";
                                description "Action to take with received DHCP Option 82";
                            }

                            container circuit-id {
                                description "Enter the circuit-id context";

                                choice circuit-id {
                                    default "ascii-tuple";
                                    case none {

                                        leaf none {
                                            type empty;
                                            description "Do not include the circuit ID";
                                        }

                                    }
                                    case ifindex {

                                        leaf ifindex {
                                            type empty;
                                            description "Use the interface index for the circuit ID";
                                        }

                                    }
                                    case ascii-tuple {

                                        leaf ascii-tuple {
                                            type empty;
                                            description "Use the ASCII-encoded tuple for the circuit ID";
                                        }

                                    }
                                    case sap-id {

                                        leaf sap-id {
                                            type empty;
                                            description "Use the SAP ID";
                                        }

                                    }
                                    case vlan-ascii-tuple {

                                        leaf vlan-ascii-tuple {
                                            type empty;
                                            description "Include the VLAN ID and dot1p bits in the ASCII tuple";
                                        }

                                    }
                                }
                            } // container circuit-id

                            container remote-id {
                                description "Enter the remote-id context";

                                choice remote-id {
                                    default "none";
                                    case none {

                                        leaf none {
                                            type empty;
                                            description "Do not include the remote ID";
                                        }

                                    }
                                    case mac {

                                        leaf mac {
                                            type empty;
                                            description "Use the MAC address for the remote ID";
                                        }

                                    }
                                    case ascii-string {

                                        leaf ascii-string {
                                            type types-sros:string-not-all-spaces {
                                                length "1..32";
                                            }
                                            description "User-defined ASCII string for the remote ID";
                                        }

                                    }
                                }
                            } // container remote-id

                            container vendor-specific-option {
                                description "Enter the vendor-specific-option context";

                                leaf system-id {
                                    type boolean;
                                    default "false";
                                    description "Send the system ID in the VSO";
                                }

                                leaf client-mac-address {
                                    type boolean;
                                    default "false";
                                    description "Send the MAC address in the VSO";
                                }

                                leaf pool-name {
                                    type boolean;
                                    default "false";
                                    description "Send the pool name in the VSO";
                                }

                                leaf service-id {
                                    type boolean;
                                    default "false";
                                    description "Send the service ID in the Vendor Specific Option";
                                }

                                leaf sap-id {
                                    type boolean;
                                    default "false";
                                    description "Send SAP ID in the sub-option of the DHCP relay packet";
                                }

                                leaf string {
                                    type types-sros:string-not-all-spaces {
                                        length "1..32";
                                    }
                                    description "User-defined ASCII string for the VSO";
                                }

                            } // container vendor-specific-option

                        } // container option-82

                        container lease-populate {
                            description "Enter the lease-populate context";

                            leaf max-leases {
                                type uint32 {
                                    range "0..511999";
                                }
                                description "Maximum number of DHCPv4 leases allowed";
                            }

                        } // container lease-populate

                        container relay-proxy {
                            presence "Enable the relay-proxy context";
                            description "Enable the relay-proxy context";

                            leaf release-update-src-ip {
                                type boolean;
                                default "false";
                                description "Update the source IP address of a DHCP RELEASE message";
                            }

                            leaf siaddr-override {
                                type types-sros:ipv4-unicast-address;
                                description "DHCP server IP address for address hiding function";
                            }

                        } // container relay-proxy

                    } // container dhcp

                    list vrrp {
                        key "virtual-router-id";
                        description "Enter the vrrp list instance";

                        leaf virtual-router-id {
                            type int32 {
                                range "1..255";
                            }
                            description "Virtual Router Identifier (VRID) for the IP interface";
                        }

                        leaf authentication-key {
                            type types-sros:encrypted-leaf {
                                length "1..38";
                            }
                            description "Password for simple text authentication";
                        }

                        leaf-list backup {
                            type types-sros:ipv4-unicast-address;
                            max-elements 16;
                            description "Virtual router IP addresses for the interface";
                        }

                        leaf message-interval {
                            type uint32 {
                                range "1..2559";
                            }
                            units "deciseconds";
                            default "10";
                            description "Interval for sending VRRP advertisement messages";
                        }

                        leaf owner {
                            type boolean;
                            sros-ext:immutable;
                            default "false";
                            description "Designate the virtual router instance as owner";
                        }

                        leaf passive {
                            type boolean;
                            sros-ext:immutable;
                            default "false";
                            description "Suppress the processing of VRRP advertisement messages";
                        }

                        leaf init-delay {
                            type uint32 {
                                range "1..65535";
                            }
                            units "seconds";
                            description "VRRP initialization delay timer";
                        }

                        leaf mac {
                            type types-sros:mac-unicast-address;
                            description "Virtual MAC address to use in ARP responses";
                        }

                        leaf priority {
                            type uint32 {
                                range "1..255";
                            }
                            description "Base priority for the VRRP";
                        }

                        leaf admin-state {
                            type types-sros:admin-state;
                            default "enable";
                            description "Administrative state of VRRP";
                        }

                        leaf master-int-inherit {
                            type boolean;
                            description "Allow master instance to dictate the master down timer";
                        }

                        leaf ping-reply {
                            type boolean;
                            default "false";
                            description "Allow non-owner master to reply to ICMP echo requests";
                        }

                        leaf policy {
                            type leafref {
                                path "../../../../../../vrrp/policy/policy-id";
                            }
                            description "VRRP priority control policy";
                        }

                        leaf preempt {
                            type boolean;
                            default "true";
                            description "Allow the VRRP to override an existing non-owner master";
                        }

                        leaf telnet-reply {
                            type boolean;
                            default "false";
                            description "Allow non-owner master to reply to Telnet requests";
                        }

                        leaf traceroute-reply {
                            type boolean;
                            default "false";
                            description "Allow non-owner master to reply to traceroute requests";
                        }

                        leaf standby-forwarding {
                            type boolean;
                            default "false";
                            description "Allow standby router to forward traffic";
                        }

                        leaf ssh-reply {
                            type boolean;
                            default "false";
                            description "Allow the non-owner master to reply to SSH requests";
                        }

                        leaf ntp-reply {
                            type boolean;
                            default "false";
                            description "Allow processing of NTP requests";
                        }

                        leaf oper-group {
                            type leafref {
                                path "../../../../../oper-group/name";
                            }
                            description "Operational group name associated with the VRRP";
                        }

                        leaf monitor-oper-group {
                            type leafref {
                                path "../../../../../oper-group/name";
                            }
                            sros-ext:immutable;
                            description "VRRP instance to follow a specified operational group";
                        }

                        leaf-list apply-groups {
                            type leafref {
                                path "../../../../../../groups/group/name";
                            }
                            max-elements 8;
                            ordered-by user;
                            description "Apply a configuration group at this level";
                        }

                        leaf-list apply-groups-exclude {
                            type leafref {
                                path "../../../../../../groups/group/name";
                            }
                            max-elements 8;
                            ordered-by user;
                            description "Exclude a configuration group at this level";
                        }

                        container bfd-liveness {
                            presence "Enable the bfd-liveness context";
                            description "Enable the bfd-liveness context";

                            leaf dest-ip {
                                type types-sros:ipv4-address;
                                sros-ext:immutable;
                                mandatory true;
                                description "Destination IP address to use for BFD session";
                            }

                            leaf service-name {
                                type types-services:service-name;
                                sros-ext:immutable;
                                description "Administrative service name";
                            }

                            leaf interface-name {
                                type types-sros:interface-name;
                                sros-ext:immutable;
                                mandatory true;
                                description "Name of the interface running BFD";
                            }

                            leaf-list apply-groups {
                                type leafref {
                                    path "../../../../../../../groups/group/name";
                                }
                                max-elements 8;
                                ordered-by user;
                                description "Apply a configuration group at this level";
                            }

                            leaf-list apply-groups-exclude {
                                type leafref {
                                    path "../../../../../../../groups/group/name";
                                }
                                max-elements 8;
                                ordered-by user;
                                description "Exclude a configuration group at this level";
                            }

                        } // container bfd-liveness

                    } // list vrrp

                } // container ipv4

                list spoke-sdp {
                    key "sdp-bind-id";
                    max-elements 1;
                    description "Enter the spoke-sdp list instance";

                    leaf sdp-bind-id {
                        type types-services:sdp-bind-id;
                        description "SDP binding ID";
                    }

                    leaf description {
                        type types-sros:description;
                        description "Text description";
                    }

                    leaf admin-state {
                        type types-sros:admin-state;
                        default "enable";
                        description "Administrative state of the SDP binding to the service";
                    }

                    leaf collect-stats {
                        type boolean;
                        default "false";
                        description "Allow agent to collect accounting statistics";
                    }

                    leaf accounting-policy {
                        type leafref {
                            path "../../../../../log/accounting-policy/policy-id";
                        }
                        description "Policy to collect accounting statistics";
                    }

                    leaf control-word {
                        type boolean;
                        default "false";
                        description "Use the control word as preferred";
                    }

                    leaf app-profile {
                        type leafref {
                            path "../../../../../application-assurance/group/partition/policy/app-profile/app-profile-name";
                        }
                        description "Application profile name for this SDP";
                    }

                    leaf bfd-template {
                        status obsolete;
                        type leafref {
                            path "../../../../../bfd/bfd-template/name";
                        }
                        description "BFD template associated with SDP binding";
                    }

                    leaf vc-type {
                        type types-services:ies-sdp-bind-vc-type;
                        sros-ext:immutable;
                        default "ether";
                        description "Type of virtual circuit (VC) associated with the SDP binding";
                    }

                    leaf-list apply-groups {
                        type leafref {
                            path "../../../../../groups/group/name";
                        }
                        max-elements 8;
                        ordered-by user;
                        description "Apply a configuration group at this level";
                    }

                    leaf-list apply-groups-exclude {
                        type leafref {
                            path "../../../../../groups/group/name";
                        }
                        max-elements 8;
                        ordered-by user;
                        description "Exclude a configuration group at this level";
                    }

                    choice label {
                        case entropy {

                            leaf entropy-label {
                                type empty;
                                description "Enable the use of entropy labels for spoke SDPs";
                            }

                        }
                        case hash {

                            container hash-label {
                                presence "Enable the hash-label context";
                                description "Enable the hash-label context";

                                leaf signal-capability {
                                    type empty;
                                    description "Signal hash label capability to the remote PE";
                                }

                            } // container hash-label

                        }
                    }
                    container ingress {
                        description "Enter the ingress context";

                        leaf vc-label {
                            type types-services:ingress-vc-label;
                            sros-ext:auto-restart-to-modify;
                            description "Ingress MPLS VC label to send packets to the far end";
                        }

                        container filter {
                            description "Enter the filter context";

                            leaf ip {
                                type leafref {
                                    path "../../../../../../../filter/ip-filter/filter-name";
                                }
                                description "IPv4 filter policy name";
                            }

                            leaf ipv6 {
                                type leafref {
                                    path "../../../../../../../filter/ipv6-filter/filter-name";
                                }
                                description "IPv6 filter policy name";
                            }

                        } // container filter

                        container qos {
                            description "Enter the qos context";

                            container network {
                                description "Enter the network context";

                                leaf policy-name {
                                    type leafref {
                                        path "../../../../../../../../qos/network/network-policy-name";
                                    }
                                    description "Network policy ID";
                                }

                                container fp-redirect-group {
                                    description "Enter the fp-redirect-group context";

                                    leaf group-name {
                                        type leafref {
                                            path "../../../../../../../../../qos/queue-group-templates/ingress/queue-group/ingress-queue-group-name";
                                        }
                                        description "Name of the forwarding plane queue group template";
                                    }

                                    leaf instance {
                                        type types-services:qos-qgrp-instance-id;
                                        description "Instance of FP ingress queue group for the SDP binding";
                                    }

                                } // container fp-redirect-group

                            } // container network

                        } // container qos

                    } // container ingress

                    container egress {
                        description "Enter the egress context";

                        leaf vc-label {
                            type types-services:egress-vc-label;
                            sros-ext:auto-restart-to-modify;
                            description "Egress MPLS VC label to send packets to the far end";
                        }

                        container filter {
                            description "Enter the filter context";

                            leaf ip {
                                type leafref {
                                    path "../../../../../../../filter/ip-filter/filter-name";
                                }
                                description "IPv4 filter policy name";
                            }

                            leaf ipv6 {
                                type leafref {
                                    path "../../../../../../../filter/ipv6-filter/filter-name";
                                }
                                description "IPv6 filter policy name";
                            }

                        } // container filter

                        container qos {
                            description "Enter the qos context";

                            container network {
                                description "Enter the network context";

                                leaf policy-name {
                                    type leafref {
                                        path "../../../../../../../../qos/network/network-policy-name";
                                    }
                                    description "Network policy ID";
                                }

                                container port-redirect-group {
                                    description "Enter the port-redirect-group context";

                                    leaf group-name {
                                        type leafref {
                                            path "../../../../../../../../../qos/queue-group-templates/egress/queue-group/egress-queue-group-name";
                                        }
                                        description "Name of the egress port queue group";
                                    }

                                    leaf instance {
                                        type types-services:qos-qgrp-instance-id;
                                        description "Queue-group instance ID";
                                    }

                                } // container port-redirect-group

                            } // container network

                        } // container qos

                    } // container egress

                    container cpu-protection {
                        description "Enter the cpu-protection context";

                        leaf policy-id {
                            type leafref {
                                path "../../../../../../system/security/cpu-protection/policy/policy-id";
                            }
                            description "CPM protection policy";
                        }

                        choice monitoring {
                            case mac {

                                leaf mac-monitoring {
                                    type empty;
                                    description "Monitor MAC for CPU protection";
                                }

                            }
                            case cfm {

                                container eth-cfm-monitoring {
                                    presence "Enable the eth-cfm-monitoring context";
                                    description "Enable the eth-cfm-monitoring context";

                                    leaf aggregate {
                                        type empty;
                                        description "Apply rate limit to the sum of the per peer packet rates";
                                    }

                                    leaf car {
                                        type empty;
                                        description "Ignore Ethernet CFM packets when enforcing overall rate";
                                    }

                                } // container eth-cfm-monitoring

                            }
                            case ip {

                                leaf ip-src-monitoring {
                                    type empty;
                                    description "Enable IP source monitoring for CPU protection";
                                }

                            }
                        }
                    } // container cpu-protection

                    container aarp {
                        presence "Enable the aarp context";
                        description "Enable the aarp context";

                        leaf id {
                            type leafref {
                                path "../../../../../../application-assurance/aarp/aarp-id";
                            }
                            description "AARP instance ID";
                        }

                        leaf type {
                            type types-services:dual-homing-bsx-aarp-service-ref-type;
                            description "Role referenced by the AARP";
                        }

                    } // container aarp

                    container bfd-liveness {
                        status obsolete;
                        presence "Enable the bfd-liveness context";
                        description "Enable the bfd-liveness context";

                        leaf encap {
                            status obsolete;
                            type types-services:bfd-encap;
                            default "ipv4";
                            description "BFD encapsulation used on the SDP binding";
                        }

                    } // container bfd-liveness

                    container bfd {
                        description "Enter the bfd context";

                        leaf bfd-template {
                            type leafref {
                                path "../../../../../../bfd/bfd-template/name";
                            }
                            description "BFD template associated with the SDP binding";
                        }

                        leaf failure-action {
                            type types-services:sbind-bfd-fail-action;
                            default "none";
                            description "VCCV BFD action taken on the SDP binding";
                        }

                        leaf wait-for-up-timer {
                            type uint32 {
                                range "1..60";
                            }
                            units "seconds";
                            description "Time waited for BFD up status";
                        }

                        container bfd-liveness {
                            presence "Enable the bfd-liveness context";
                            description "Enable the bfd-liveness context";

                            leaf encap {
                                type types-services:bfd-encap;
                                default "ipv4";
                                description "BFD encapsulation used on the SDP binding";
                            }

                        } // container bfd-liveness

                    } // container bfd

                    container transit-policy {
                        presence "Enable the transit-policy context";
                        description "Enable the transit-policy context";

                        choice transit-policy {
                            mandatory true;
                            case prefix {

                                leaf prefix {
                                    type leafref {
                                        path "../../../../../../application-assurance/group/partition/transit-prefix-policy/prefix-policy-id";
                                    }
                                    sros-ext:immutable;
                                    description "IP prefix policy ID";
                                }

                            }
                            case ip {

                                leaf ip {
                                    type leafref {
                                        path "../../../../../../application-assurance/group/partition/transit-ip-policy/ip-policy-id";
                                    }
                                    sros-ext:immutable;
                                    description "IP transit policy ID";
                                }

                            }
                        }
                    } // container transit-policy

                    container eth-cfm {
                        description "Enter the eth-cfm context";

                        leaf collect-lmm-stats {
                            type boolean;
                            default "false";
                            description "Collect statistics for loss measurement message tests";
                        }

                        leaf-list squelch-ingress-levels {
                            type uint32 {
                                range "0..7";
                            }
                            max-elements 8;
                            description "Levels for which ETH-CFM packets are silently discarded";
                        }

                        leaf-list apply-groups {
                            type leafref {
                                path "../../../../../../groups/group/name";
                            }
                            max-elements 8;
                            ordered-by user;
                            description "Apply a configuration group at this level";
                        }

                        leaf-list apply-groups-exclude {
                            type leafref {
                                path "../../../../../../groups/group/name";
                            }
                            max-elements 8;
                            ordered-by user;
                            description "Exclude a configuration group at this level";
                        }

                        container collect-lmm-fc-stats {
                            description "Enter the collect-lmm-fc-stats context";

                            leaf-list fc {
                                type types-eth-cfm:fc-type;
                                max-elements 8;
                                description "Forwarding class name for profile-unaware counter";
                            }

                            leaf-list fc-in-profile {
                                type types-eth-cfm:fc-type;
                                max-elements 8;
                                description "Forwarding class name for profile-aware counter";
                            }

                        } // container collect-lmm-fc-stats

                        list mep {
                            key "md-admin-name ma-admin-name mep-id";
                            description "Enter the mep list instance";

                            leaf md-admin-name {
                                type leafref {
                                    path "../../../../../../../eth-cfm/domain/md-admin-name";
                                }
                                description "Maintenance Domain (MD) name";
                            }

                            leaf ma-admin-name {
                                type leafref {
                                    path "../../../../../../../eth-cfm/domain[md-admin-name=current()/../md-admin-name]/association/ma-admin-name";
                                }
                                description "Maintenance Association (MA) name";
                            }

                            leaf mep-id {
                                type types-eth-cfm:mep-id-type;
                                description "Maintenance Endpoint (MEP) ID";
                            }

                            leaf admin-state {
                                type types-sros:admin-state;
                                default "disable";
                                description "Administrative state of the MEP";
                            }

                            leaf description {
                                type types-sros:description;
                                description "Text description";
                            }

                            leaf low-priority-defect {
                                type types-eth-cfm:lowest-alarm-priority;
                                default "mac-rem-err-xcon";
                                description "Lowest priority defect allowed to generate fault alarm";
                            }

                            leaf fault-propagation {
                                type types-eth-cfm:fault-propagation-type;
                                description "Fault propagation for the MEP";
                            }

                            leaf ccm {
                                type boolean;
                                default "false";
                                description "Generate CCM messages";
                            }

                            leaf ccm-ltm-priority {
                                type types-eth-cfm:frame-priority;
                                default "7";
                                description "Priority of CCM and LTM messages transmitted by the MEP";
                            }

                            leaf ccm-padding-size {
                                type uint32 {
                                    range "3..1500";
                                }
                                description "Number of octets of padding to insert in CCM packets";
                            }

                            leaf one-way-delay-threshold {
                                type uint32 {
                                    range "0..600";
                                }
                                units "seconds";
                                default "3";
                                description "Threshold time limit for the one-way delay test";
                            }

                            leaf ais {
                                type boolean;
                                default "false";
                                description "Enable the generation and the reception of AIS messages";
                            }

                            leaf-list apply-groups {
                                type leafref {
                                    path "../../../../../../../groups/group/name";
                                }
                                max-elements 8;
                                ordered-by user;
                                description "Apply a configuration group at this level";
                            }

                            leaf-list apply-groups-exclude {
                                type leafref {
                                    path "../../../../../../../groups/group/name";
                                }
                                max-elements 8;
                                ordered-by user;
                                description "Exclude a configuration group at this level";
                            }

                            container alarm-notification {
                                description "Enter the alarm-notification context";

                                leaf fng-alarm-time {
                                    type int32 {
                                        range "250|500|1000";
                                    }
                                    units "centiseconds";
                                    description "Time that must expire before an FNG alarm is raised";
                                }

                                leaf fng-reset-time {
                                    type int32 {
                                        range "250|500|1000";
                                    }
                                    units "centiseconds";
                                    description "Time that must expire before an FNG alarm is reset";
                                }

                            } // container alarm-notification

                            container csf {
                                presence "Enable the csf context";
                                description "Enable the csf context";

                                leaf multiplier {
                                    type decimal64 {
                                        range "0.0|2.0..30.0";
                                        fraction-digits 1;
                                    }
                                    default "3.5";
                                    description "Multiplication factor used to clear the CSF condition";
                                }

                            } // container csf

                            container eth-test {
                                presence "Enable the eth-test context";
                                description "Enable the eth-test context";

                                leaf bit-error-threshold {
                                    type uint32 {
                                        range "0..11840";
                                    }
                                    units "bit errors";
                                    default "1";
                                    description "Lowest priority defect allowed to generate fault alarm";
                                }

                                container test-pattern {
                                    description "Enter the test-pattern context";

                                    leaf pattern {
                                        type enumeration {
                                            enum all-zeros                      { value 0; }
                                            enum all-ones                       { value 1; }
                                        }
                                        default "all-zeros";
                                        description "Test pattern for Ethernet Test frames";
                                    }

                                    leaf crc-tlv {
                                        type boolean;
                                        default "false";
                                        description "Generate a CRC checksum";
                                    }

                                } // container test-pattern

                            } // container eth-test

                            container grace {
                                description "Enter the grace context";

                                container eth-ed {
                                    description "Enter the eth-ed context";

                                    leaf max-rx-defect-window {
                                        type uint32 {
                                            range "1..86400";
                                        }
                                        units "seconds";
                                        description "Maximum received ETH-ED expected defect window duration";
                                    }

                                    leaf priority {
                                        type int32 {
                                            range "0..7";
                                        }
                                        description "Transmission priority for ETH-ED PDUs";
                                    }

                                    leaf rx-eth-ed {
                                        type boolean;
                                        default "true";
                                        description "Receive and process ETH-ED ITU-T Y.1731 PDUs on the MEP";
                                    }

                                    leaf tx-eth-ed {
                                        type boolean;
                                        default "false";
                                        description "Transmit ETH-ED PDUs from the MEP";
                                    }

                                } // container eth-ed

                                container eth-vsm-grace {
                                    description "Enter the eth-vsm-grace context";

                                    leaf rx-eth-vsm-grace {
                                        type boolean;
                                        default "true";
                                        description "Receive and process Nokia ETH-CFM Grace PDU on the MEP";
                                    }

                                    leaf tx-eth-vsm-grace {
                                        type boolean;
                                        default "true";
                                        description "Transmit ETH-ED PDUs from the MEP";
                                    }

                                } // container eth-vsm-grace

                            } // container grace

                        } // list mep

                    } // container eth-cfm

                } // list spoke-sdp

                list sap {
                    key "sap-id";
                    max-elements 1;
                    description "Enter the sap list instance";

                    leaf sap-id {
                        type types-sros:sap;
                        description "SAP ID";
                    }

                    leaf description {
                        type types-sros:long-description;
                        description "Text description";
                    }

                    leaf admin-state {
                        type types-sros:admin-state;
                        default "enable";
                        description "Administrative state of the SAP";
                    }

                    leaf accounting-policy {
                        type leafref {
                            path "../../../../../log/accounting-policy/policy-id";
                        }
                        description "Accounting policy";
                    }

                    leaf anti-spoof {
                        type types-services:anti-spoof-option;
                        description "Anti-spoof filtering";
                    }

                    leaf app-profile {
                        type leafref {
                            path "../../../../../application-assurance/group/partition/policy/app-profile/app-profile-name";
                        }
                        description "Application profile name";
                    }

                    leaf bandwidth {
                        type types-services:sap-bandwidth;
                        units "kilobps";
                        description "SAP bandwidth";
                    }

                    leaf calling-station-id {
                        type types-sros:string-not-all-spaces {
                            length "1..64";
                        }
                        description "Calling station ID";
                    }

                    leaf collect-stats {
                        type boolean;
                        default "false";
                        description "Collect accounting statistics";
                    }

                    leaf dist-cpu-protection {
                        type leafref {
                            path "../../../../../system/security/dist-cpu-protection/policy/policy-name";
                        }
                        description "Distributed CPU protection policy for SAP";
                    }

                    leaf host-admin-state {
                        type types-sros:admin-state;
                        default "enable";
                        description "Administrative state of the hosts";
                    }

                    leaf host-lockout-policy {
                        type leafref {
                            path "../../../../../subscriber-mgmt/host-lockout-policy/name";
                        }
                        description "Host lockout policy";
                    }

                    leaf multi-service-site {
                        type leafref {
                            path "../../../../customer/multi-service-site/multi-service-site-name";
                        }
                        description "Multi service site name";
                    }

                    leaf-list apply-groups {
                        type leafref {
                            path "../../../../../groups/group/name";
                        }
                        max-elements 8;
                        ordered-by user;
                        description "Apply a configuration group at this level";
                    }

                    leaf-list apply-groups-exclude {
                        type leafref {
                            path "../../../../../groups/group/name";
                        }
                        max-elements 8;
                        ordered-by user;
                        description "Exclude a configuration group at this level";
                    }

                    container ingress {
                        description "Enter the ingress context";

                        leaf queue-group-redirect-list {
                            type leafref {
                                path "../../../../../../qos/queue-group-redirect-list/name";
                            }
                            description "Queue group redirect list";
                        }

                        leaf shared-policer {
                            type leafref {
                                path "../../../../../../qos/shared-policers/policer/shared-policer-name";
                            }
                            description "Ingress shared policer";
                        }

                        leaf ip-filter-pair {
                            type boolean;
                            default "false";
                            description "Enable pairing IPv4 and IPv6 filters";
                        }

                        container qos {
                            description "Enter the qos context";

                            leaf match-qinq-dot1p {
                                type enumeration {
                                    enum top                            { value 2; }
                                    enum bottom                         { value 3; }
                                }
                                description "Ingress match QinQ Dot1p";
                            }

                            container sap-ingress {
                                description "Enter the sap-ingress context";

                                leaf policy-name {
                                    type leafref {
                                        path "../../../../../../../../qos/sap-ingress/sap-ingress-policy-name";
                                    }
                                    description "Policy ID";
                                }

                                leaf queuing-type {
                                    type types-services:services-sap-queuing-type;
                                    description "Queuing type";
                                }

                                container fp-redirect-group {
                                    description "Enter the fp-redirect-group context";

                                    leaf group-name {
                                        type leafref {
                                            path "../../../../../../../../../qos/queue-group-templates/ingress/queue-group/ingress-queue-group-name";
                                        }
                                        description "Queue group template name created on forwarding plane";
                                    }

                                    leaf instance {
                                        type types-services:qos-qgrp-instance-id;
                                        description "Queue group instance";
                                    }

                                } // container fp-redirect-group

                                container overrides {
                                    description "Enter the overrides context";

                                    container ip-criteria {
                                        description "Enter the ip-criteria context";

                                        leaf activate-entry-tag {
                                            type int32 {
                                                range "1..255";
                                            }
                                            description "Tag ID activated for IPv4 criteria";
                                        }

                                    } // container ip-criteria

                                    container ipv6-criteria {
                                        description "Enter the ipv6-criteria context";

                                        leaf activate-entry-tag {
                                            type int32 {
                                                range "1..255";
                                            }
                                            description "Tag ID activated for IPv6 criteria";
                                        }

                                    } // container ipv6-criteria

                                    list queue {
                                        key "queue-id";
                                        description "Enter the queue list instance";

                                        leaf queue-id {
                                            type leafref {
                                                path "../../../../../../../../../../qos/sap-ingress[sap-ingress-policy-name=current()/../../../policy-name]/queue/queue-id";
                                            }
                                            description "Policer unique ID";
                                        }

                                        leaf cbs {
                                            type union {
                                                type uint32 {
                                                    range "0..1048576";
                                                }
                                                type enumeration {
                                                    enum auto                           { value -1; }
                                                }
                                            }
                                            units "kilobytes";
                                            description "CBS";
                                        }

                                        leaf mbs {
                                            type union {
                                                type types-qos:bytes {
                                                    range "0..1073741824";
                                                }
                                                type enumeration {
                                                    enum auto                           { value -1; }
                                                }
                                            }
                                            units "bytes";
                                            description "MBS";
                                        }

                                        leaf monitor-depth {
                                            status obsolete;
                                            type boolean;
                                            default "false";
                                            description "Monitor queue depth";
                                        }

                                        leaf-list apply-groups {
                                            type leafref {
                                                path "../../../../../../../../../../groups/group/name";
                                            }
                                            max-elements 8;
                                            ordered-by user;
                                            description "Apply a configuration group at this level";
                                        }

                                        leaf-list apply-groups-exclude {
                                            type leafref {
                                                path "../../../../../../../../../../groups/group/name";
                                            }
                                            max-elements 8;
                                            ordered-by user;
                                            description "Exclude a configuration group at this level";
                                        }

                                        choice queue-override-rate {
                                            case rate {

                                                container rate {
                                                    description "Enter the rate context";

                                                    leaf pir {
                                                        type types-services:sap-pir-rate-ovr;
                                                        units "kilobps";
                                                        description "PIR rate";
                                                    }

                                                    leaf cir {
                                                        type types-services:sap-cir-rate-ovr;
                                                        units "kilobps";
                                                        description "CIR rate";
                                                    }

                                                } // container rate

                                            }
                                            case percent-rate {

                                                container percent-rate {
                                                    description "Enter the percent-rate context";

                                                    leaf pir {
                                                        type decimal64 {
                                                            range "0.01..100.00";
                                                            fraction-digits 2;
                                                        }
                                                        description "PIR percent rate";
                                                    }

                                                    leaf cir {
                                                        type decimal64 {
                                                            range "0.00..100.00";
                                                            fraction-digits 2;
                                                        }
                                                        description "CIR percent rate";
                                                    }

                                                } // container percent-rate

                                            }
                                        }
                                        container adaptation-rule {
                                            description "Enter the adaptation-rule context";

                                            leaf pir {
                                                type types-qos:adaptation-rule-override;
                                                description "Constraint used when deriving the operational PIR value";
                                            }

                                            leaf cir {
                                                type types-qos:adaptation-rule-override;
                                                description "Constraint used when deriving the operational CIR value";
                                            }

                                        } // container adaptation-rule

                                        container drop-tail {
                                            description "Enter the drop-tail context";

                                            container low {
                                                description "Enter the low context";

                                                leaf percent-reduction-from-mbs {
                                                    type types-qos:burst-percent-or-default-override;
                                                    description "Percentage reduction from the MBS for a queue drop tail";
                                                }

                                            } // container low

                                        } // container drop-tail

                                        container parent {
                                            description "Enter the parent context";

                                            leaf weight {
                                                type types-qos:weight-override;
                                                description "PIR parameter that overrides parent for queue group";
                                            }

                                            leaf cir-weight {
                                                type types-qos:weight-override;
                                                description "CIR parameter that overrides parent for queue group";
                                            }

                                        } // container parent

                                        container monitor-queue-depth {
                                            presence "Enable the monitor-queue-depth context";
                                            description "Enable the monitor-queue-depth context";

                                            leaf fast-polling {
                                                type boolean;
                                                default "false";
                                                description "Enable fast polling of the queue depth";
                                            }

                                        } // container monitor-queue-depth

                                    } // list queue

                                    list policer {
                                        key "policer-id";
                                        description "Enter the policer list instance";

                                        leaf policer-id {
                                            type leafref {
                                                path "../../../../../../../../../../qos/sap-ingress[sap-ingress-policy-name=current()/../../../policy-name]/policer/policer-id";
                                            }
                                            description "Policer unique ID";
                                        }

                                        leaf cbs {
                                            type types-qos:policer-burst-size-override-max;
                                            description "CBS";
                                        }

                                        leaf mbs {
                                            type types-qos:policer-burst-size-override-max;
                                            description "MBS";
                                        }

                                        leaf packet-byte-offset {
                                            type types-qos:ingress-per-packet-offset-override;
                                            description "Packet size modification for policing information";
                                        }

                                        leaf stat-mode {
                                            type types-qos:ingress-policer-stat-mode;
                                            description "Mode of statistics collected by the policer";
                                        }

                                        leaf-list apply-groups {
                                            type leafref {
                                                path "../../../../../../../../../../groups/group/name";
                                            }
                                            max-elements 8;
                                            ordered-by user;
                                            description "Apply a configuration group at this level";
                                        }

                                        leaf-list apply-groups-exclude {
                                            type leafref {
                                                path "../../../../../../../../../../groups/group/name";
                                            }
                                            max-elements 8;
                                            ordered-by user;
                                            description "Exclude a configuration group at this level";
                                        }

                                        choice policer-override-rate {
                                            case rate {

                                                container rate {
                                                    description "Enter the rate context";

                                                    leaf pir {
                                                        type union {
                                                            type int64 {
                                                                range "1..6400000000";
                                                            }
                                                            type enumeration {
                                                                enum max                            { value -1; }
                                                            }
                                                        }
                                                        units "kilobps";
                                                        description "PIR rate";
                                                    }

                                                    leaf cir {
                                                        type union {
                                                            type int64 {
                                                                range "0..6400000000";
                                                            }
                                                            type enumeration {
                                                                enum max                            { value -1; }
                                                            }
                                                        }
                                                        units "kilobps";
                                                        description "CIR rate";
                                                    }

                                                } // container rate

                                            }
                                            case percent-rate {

                                                container percent-rate {
                                                    description "Enter the percent-rate context";

                                                    leaf pir {
                                                        type decimal64 {
                                                            range "0.01..100.00";
                                                            fraction-digits 2;
                                                        }
                                                        description "PIR percent rate";
                                                    }

                                                    leaf cir {
                                                        type decimal64 {
                                                            range "0.00..100.00";
                                                            fraction-digits 2;
                                                        }
                                                        description "CIR percent rate";
                                                    }

                                                } // container percent-rate

                                            }
                                        }
                                    } // list policer

                                } // container overrides

                            } // container sap-ingress

                            container policer-control-policy {
                                description "Enter the policer-control-policy context";

                                leaf policy-name {
                                    type leafref {
                                        path "../../../../../../../../qos/policer-control-policy/policer-control-policy-name";
                                    }
                                    description "Policer control policy name";
                                }

                                container overrides {
                                    presence "Enable the overrides context";
                                    description "Enable the overrides context";

                                    leaf-list apply-groups {
                                        type leafref {
                                            path "../../../../../../../../../groups/group/name";
                                        }
                                        max-elements 8;
                                        ordered-by user;
                                        description "Apply a configuration group at this level";
                                    }

                                    leaf-list apply-groups-exclude {
                                        type leafref {
                                            path "../../../../../../../../../groups/group/name";
                                        }
                                        max-elements 8;
                                        ordered-by user;
                                        description "Exclude a configuration group at this level";
                                    }

                                    container root {
                                        description "Enter the root context";

                                        leaf max-rate {
                                            type types-services:sap-max-rate-ovr;
                                            description "Maximum frame-based bandwidth limit";
                                        }

                                        container priority-mbs-thresholds {
                                            description "Enter the priority-mbs-thresholds context";

                                            leaf min-thresh-separation {
                                                type union {
                                                    type types-qos:bytes {
                                                        range "0..16777216";
                                                    }
                                                    type enumeration {
                                                        enum auto                           { value -1; }
                                                    }
                                                }
                                                units "bytes";
                                                description "Minimum amount of separation buffer space";
                                            }

                                            list priority {
                                                key "priority-level";
                                                description "Enter the priority list instance";

                                                leaf priority-level {
                                                    type types-qos:hierarchy-level;
                                                    description "Priority level";
                                                }

                                                leaf mbs-contribution {
                                                    type union {
                                                        type types-qos:bytes {
                                                            range "0..16777216";
                                                        }
                                                        type enumeration {
                                                            enum auto                           { value -1; }
                                                        }
                                                    }
                                                    units "bytes";
                                                    description "Minimum amount of cumulative buffer space allowed";
                                                }

                                                leaf-list apply-groups {
                                                    type leafref {
                                                        path "../../../../../../../../../../../../groups/group/name";
                                                    }
                                                    max-elements 8;
                                                    ordered-by user;
                                                    description "Apply a configuration group at this level";
                                                }

                                                leaf-list apply-groups-exclude {
                                                    type leafref {
                                                        path "../../../../../../../../../../../../groups/group/name";
                                                    }
                                                    max-elements 8;
                                                    ordered-by user;
                                                    description "Exclude a configuration group at this level";
                                                }

                                            } // list priority

                                        } // container priority-mbs-thresholds

                                    } // container root

                                } // container overrides

                            } // container policer-control-policy

                            container scheduler-policy {
                                description "Enter the scheduler-policy context";

                                leaf policy-name {
                                    type leafref {
                                        path "../../../../../../../../qos/scheduler-policy/scheduler-policy-name";
                                    }
                                    description "Scheduler policy name";
                                }

                                container overrides {
                                    description "Enter the overrides context";

                                    list scheduler {
                                        key "scheduler-name";
                                        description "Enter the scheduler list instance";

                                        leaf scheduler-name {
                                            type types-sros:named-item;
                                            description "Scheduler name";
                                        }

                                        leaf-list apply-groups {
                                            type leafref {
                                                path "../../../../../../../../../../groups/group/name";
                                            }
                                            max-elements 8;
                                            ordered-by user;
                                            description "Apply a configuration group at this level";
                                        }

                                        leaf-list apply-groups-exclude {
                                            type leafref {
                                                path "../../../../../../../../../../groups/group/name";
                                            }
                                            max-elements 8;
                                            ordered-by user;
                                            description "Exclude a configuration group at this level";
                                        }

                                        container parent {
                                            description "Enter the parent context";

                                            leaf weight {
                                                type types-qos:weight;
                                                description "Relative weight of the scheduler to feed the queue";
                                            }

                                            leaf cir-weight {
                                                type types-qos:weight;
                                                description "Weight used at the within-CIR port priority level";
                                            }

                                        } // container parent

                                        container rate {
                                            description "Enter the rate context";

                                            leaf pir {
                                                type union {
                                                    type int64 {
                                                        range "1..6400000000";
                                                    }
                                                    type enumeration {
                                                        enum max                            { value -1; }
                                                    }
                                                }
                                                units "kilobps";
                                                description "PIR at which the queue is to operate";
                                            }

                                            leaf cir {
                                                type union {
                                                    type int64 {
                                                        range "0..6400000000";
                                                    }
                                                    type enumeration {
                                                        enum sum                            { value -3; }
                                                        enum max                            { value -1; }
                                                    }
                                                }
                                                units "kilobps";
                                                description "CIR at which the queue it to operate";
                                            }

                                        } // container rate

                                    } // list scheduler

                                } // container overrides

                            } // container scheduler-policy

                        } // container qos

                        container filter {
                            description "Enter the filter context";

                            leaf ip {
                                type leafref {
                                    path "../../../../../../../filter/ip-filter/filter-name";
                                }
                                description "IPv4 filter policy name";
                            }

                            leaf ipv6 {
                                type leafref {
                                    path "../../../../../../../filter/ipv6-filter/filter-name";
                                }
                                description "IPv6 filter policy name";
                            }

                        } // container filter

                        container aggregate-policer {
                            description "Enter the aggregate-policer context";

                            leaf rate {
                                type types-qos:aggr-policer-rate;
                                units "kilobps";
                                default "max";
                                description "Aggregate policer rate";
                            }

                            leaf burst {
                                type types-qos:aggr-policer-burst;
                                default "default";
                                description "Aggregate policer burst";
                            }

                            leaf cir {
                                type types-qos:aggr-policer-cir;
                                units "kilobps";
                                description "Aggregate policer CIR";
                            }

                            leaf cbs {
                                type types-qos:aggr-policer-cbs;
                                units "kilobytes";
                                description "Aggregate policer CBS";
                            }

                        } // container aggregate-policer

                    } // container ingress

                    container egress {
                        description "Enter the egress context";

                        leaf queue-group-redirect-list {
                            type leafref {
                                path "../../../../../../qos/queue-group-redirect-list/name";
                            }
                            description "Assign queue-group redirect list";
                        }

                        choice agg-rate-or-percent-agg-rate {
                            default "agg-rate";
                            case agg-rate {

                                container agg-rate {
                                    description "Enter the agg-rate context";

                                    leaf limit-unused-bandwidth {
                                        type boolean;
                                        default "false";
                                        description "Enable aggregate rate overrun protection";
                                    }

                                    leaf rate {
                                        type types-services:agg-rate-rate;
                                        units "kilobps";
                                        description "Enforced aggregate rate for all queues";
                                    }

                                    leaf queue-frame-based-accounting {
                                        type boolean;
                                        default "false";
                                        description "Enable frame based accounting on policers and queues";
                                    }

                                    leaf cir {
                                        type union {
                                            type int32 {
                                                range "0..400000000";
                                            }
                                            type enumeration {
                                                enum max                            { value -1; }
                                            }
                                        }
                                        units "kilobps";
                                        default "0";
                                        description "Administrative CIR";
                                    }

                                    leaf burst-limit {
                                        type union {
                                            type types-qos:bytes {
                                                range "1..14000000";
                                            }
                                            type enumeration {
                                                enum auto                           { value -1; }
                                            }
                                        }
                                        default "auto";
                                        description "Shaping burst size when an aggregate shaper is used";
                                    }

                                    leaf adaptation-rule {
                                        type types-qos:adaptation-rule;
                                        default "closest";
                                        description "Adaptation rule to compute the operational PIR value when an aggregate shaper is used";
                                    }

                                } // container agg-rate

                            }
                            case percent-agg-rate {

                                container percent-agg-rate {
                                    description "Enter the percent-agg-rate context";

                                    leaf pir {
                                        type decimal64 {
                                            range "0.01..100.00";
                                            fraction-digits 2;
                                        }
                                        description "PIR percent rate";
                                    }

                                    leaf cir {
                                        type decimal64 {
                                            range "0.00..100.00";
                                            fraction-digits 2;
                                        }
                                        description "CIR percent rate";
                                    }

                                } // container percent-agg-rate

                            }
                        }
                        container qos {
                            description "Enter the qos context";

                            leaf qinq-mark-top-only {
                                type boolean;
                                default "false";
                                description "Mark top Q-tags";
                            }

                            leaf burst-limit {
                                type types-qos:vlan-qos-burst-limit;
                                description "Maximum traffic burst size for SAP egress";
                            }

                            leaf latency-budget {
                                type uint32 {
                                    range "1..1000000";
                                }
                                units "microseconds";
                                description "SAP egress latency budget";
                            }

                            container sap-egress {
                                description "Enter the sap-egress context";

                                leaf policy-name {
                                    type leafref {
                                        path "../../../../../../../../qos/sap-egress/sap-egress-policy-name";
                                    }
                                    description "Policy ID to associate with SAP for mirrored service";
                                }

                                container port-redirect-group {
                                    description "Enter the port-redirect-group context";

                                    leaf group-name {
                                        type leafref {
                                            path "../../../../../../../../../qos/queue-group-templates/egress/queue-group/egress-queue-group-name";
                                        }
                                        description "Name of the queue group redirect list policy";
                                    }

                                    leaf instance {
                                        type types-services:qos-qgrp-instance-id;
                                        description "Instance of port queue group";
                                    }

                                } // container port-redirect-group

                                container overrides {
                                    description "Enter the overrides context";

                                    leaf hs-secondary-shaper {
                                        type types-sros:named-item;
                                        description "HS Secondary Shaper";
                                    }

                                    list queue {
                                        key "queue-id";
                                        description "Enter the queue list instance";

                                        leaf queue-id {
                                            type leafref {
                                                path "../../../../../../../../../../qos/sap-egress[sap-egress-policy-name=current()/../../../policy-name]/queue/queue-id";
                                            }
                                            description "Policer unique ID";
                                        }

                                        leaf avg-frame-overhead {
                                            type decimal64 {
                                                range "0.00..100.00";
                                                fraction-digits 2;
                                            }
                                            description "Average packet-to-frame encapsulation overhead";
                                        }

                                        leaf burst-limit {
                                            type union {
                                                type types-qos:bytes {
                                                    range "1..14000000";
                                                }
                                                type enumeration {
                                                    enum auto                           { value -1; }
                                                }
                                            }
                                            description "Explicit shaping burst size for the queue";
                                        }

                                        leaf cbs {
                                            type union {
                                                type uint32 {
                                                    range "0..1048576";
                                                }
                                                type enumeration {
                                                    enum auto                           { value -1; }
                                                }
                                            }
                                            units "kilobytes";
                                            description "CBS";
                                        }

                                        leaf mbs {
                                            type union {
                                                type types-qos:bytes {
                                                    range "0..1073741824";
                                                }
                                                type enumeration {
                                                    enum auto                           { value -1; }
                                                }
                                            }
                                            units "bytes";
                                            description "MBS";
                                        }

                                        leaf monitor-depth {
                                            status obsolete;
                                            type boolean;
                                            default "false";
                                            description "Monitor queue depth";
                                        }

                                        leaf hs-wrr-weight {
                                            type types-qos:hs-wrr-weight-override;
                                            default "1";
                                            description "WRR weight to parent with the queue into the scheduler";
                                        }

                                        leaf hs-class-weight {
                                            type types-qos:hs-class-weight-override;
                                            description "Class weight override for the queue";
                                        }

                                        leaf-list apply-groups {
                                            type leafref {
                                                path "../../../../../../../../../../groups/group/name";
                                            }
                                            max-elements 8;
                                            ordered-by user;
                                            description "Apply a configuration group at this level";
                                        }

                                        leaf-list apply-groups-exclude {
                                            type leafref {
                                                path "../../../../../../../../../../groups/group/name";
                                            }
                                            max-elements 8;
                                            ordered-by user;
                                            description "Exclude a configuration group at this level";
                                        }

                                        choice queue-override-rate {
                                            case rate {

                                                container rate {
                                                    description "Enter the rate context";

                                                    leaf pir {
                                                        type types-services:sap-pir-rate-ovr;
                                                        units "kilobps";
                                                        description "PIR rate";
                                                    }

                                                    leaf cir {
                                                        type types-services:sap-cir-rate-ovr;
                                                        units "kilobps";
                                                        description "CIR rate";
                                                    }

                                                } // container rate

                                            }
                                            case percent-rate {

                                                container percent-rate {
                                                    description "Enter the percent-rate context";

                                                    leaf pir {
                                                        type decimal64 {
                                                            range "0.01..100.00";
                                                            fraction-digits 2;
                                                        }
                                                        description "PIR percent rate";
                                                    }

                                                    leaf cir {
                                                        type decimal64 {
                                                            range "0.00..100.00";
                                                            fraction-digits 2;
                                                        }
                                                        description "CIR percent rate";
                                                    }

                                                } // container percent-rate

                                            }
                                        }
                                        container adaptation-rule {
                                            description "Enter the adaptation-rule context";

                                            leaf pir {
                                                type types-qos:adaptation-rule-override;
                                                description "Constraint used when deriving the operational PIR value";
                                            }

                                            leaf cir {
                                                type types-qos:adaptation-rule-override;
                                                description "Constraint used when deriving the operational CIR value";
                                            }

                                        } // container adaptation-rule

                                        container drop-tail {
                                            description "Enter the drop-tail context";

                                            container low {
                                                description "Enter the low context";

                                                leaf percent-reduction-from-mbs {
                                                    type types-qos:burst-percent-or-default-override;
                                                    description "Percentage reduction from the MBS for a queue drop tail";
                                                }

                                            } // container low

                                        } // container drop-tail

                                        container parent {
                                            description "Enter the parent context";

                                            leaf weight {
                                                type types-qos:weight-override;
                                                description "PIR parameter that overrides parent for queue group";
                                            }

                                            leaf cir-weight {
                                                type types-qos:weight-override;
                                                description "CIR parameter that overrides parent for queue group";
                                            }

                                        } // container parent

                                        container monitor-queue-depth {
                                            presence "Enable the monitor-queue-depth context";
                                            description "Enable the monitor-queue-depth context";

                                            leaf fast-polling {
                                                type boolean;
                                                default "false";
                                                description "Enable fast polling of the queue depth";
                                            }

                                            leaf violation-threshold {
                                                type decimal64 {
                                                    range "0.01..99.99";
                                                    fraction-digits 2;
                                                }
                                                description "Threshold for queue depth before violation is raised";
                                            }

                                        } // container monitor-queue-depth

                                        container hs-wred-queue {
                                            description "Enter the hs-wred-queue context";

                                            leaf policy {
                                                type leafref {
                                                    path "../../../../../../../../../../../qos/slope-policy/slope-policy-name";
                                                }
                                                description "Slope policy applied to the HSQ queue group queue";
                                            }

                                        } // container hs-wred-queue

                                    } // list queue

                                    list policer {
                                        key "policer-id";
                                        description "Enter the policer list instance";

                                        leaf policer-id {
                                            type leafref {
                                                path "../../../../../../../../../../qos/sap-egress[sap-egress-policy-name=current()/../../../policy-name]/policer/policer-id";
                                            }
                                            description "Policer unique ID";
                                        }

                                        leaf cbs {
                                            type types-qos:policer-burst-size-override-max;
                                            description "CBS";
                                        }

                                        leaf mbs {
                                            type types-qos:policer-burst-size-override-max;
                                            description "MBS";
                                        }

                                        leaf packet-byte-offset {
                                            type types-qos:egress-per-packet-offset-override;
                                            description "Packet size modification for policing information";
                                        }

                                        leaf stat-mode {
                                            type types-qos:egress-policer-stat-mode;
                                            description "Mode of statistics collected by the policer";
                                        }

                                        leaf-list apply-groups {
                                            type leafref {
                                                path "../../../../../../../../../../groups/group/name";
                                            }
                                            max-elements 8;
                                            ordered-by user;
                                            description "Apply a configuration group at this level";
                                        }

                                        leaf-list apply-groups-exclude {
                                            type leafref {
                                                path "../../../../../../../../../../groups/group/name";
                                            }
                                            max-elements 8;
                                            ordered-by user;
                                            description "Exclude a configuration group at this level";
                                        }

                                        choice policer-override-rate {
                                            case rate {

                                                container rate {
                                                    description "Enter the rate context";

                                                    leaf pir {
                                                        type union {
                                                            type int64 {
                                                                range "1..6400000000";
                                                            }
                                                            type enumeration {
                                                                enum max                            { value -1; }
                                                            }
                                                        }
                                                        units "kilobps";
                                                        description "PIR rate";
                                                    }

                                                    leaf cir {
                                                        type union {
                                                            type int64 {
                                                                range "0..6400000000";
                                                            }
                                                            type enumeration {
                                                                enum max                            { value -1; }
                                                            }
                                                        }
                                                        units "kilobps";
                                                        description "CIR rate";
                                                    }

                                                } // container rate

                                            }
                                            case percent-rate {

                                                container percent-rate {
                                                    description "Enter the percent-rate context";

                                                    leaf pir {
                                                        type decimal64 {
                                                            range "0.01..100.00";
                                                            fraction-digits 2;
                                                        }
                                                        description "PIR percent rate";
                                                    }

                                                    leaf cir {
                                                        type decimal64 {
                                                            range "0.00..100.00";
                                                            fraction-digits 2;
                                                        }
                                                        description "CIR percent rate";
                                                    }

                                                } // container percent-rate

                                            }
                                        }
                                    } // list policer

                                    list hs-wrr-group {
                                        key "group-id";
                                        description "Enter the hs-wrr-group list instance";

                                        leaf group-id {
                                            type leafref {
                                                path "../../../../../../../../../../qos/sap-egress[sap-egress-policy-name=current()/../../../policy-name]/hs-wrr-group/group-id";
                                            }
                                            description "HS WRR group identifier";
                                        }

                                        leaf hs-class-weight {
                                            type types-qos:hs-class-weight-override;
                                            description "Class weight override of the WRR group";
                                        }

                                        leaf-list apply-groups {
                                            type leafref {
                                                path "../../../../../../../../../../groups/group/name";
                                            }
                                            max-elements 8;
                                            ordered-by user;
                                            description "Apply a configuration group at this level";
                                        }

                                        leaf-list apply-groups-exclude {
                                            type leafref {
                                                path "../../../../../../../../../../groups/group/name";
                                            }
                                            max-elements 8;
                                            ordered-by user;
                                            description "Exclude a configuration group at this level";
                                        }

                                        choice rate-or-percent-rate {
                                            case rate {

                                                leaf rate {
                                                    type union {
                                                        type uint32 {
                                                            range "1..2000000000";
                                                        }
                                                        type enumeration {
                                                            enum max                            { value -1; }
                                                        }
                                                    }
                                                    units "kilobps";
                                                    description "Scheduling rate override applied to the HS WRR group";
                                                }

                                            }
                                            case percent-rate {

                                                leaf percent-rate {
                                                    type decimal64 {
                                                        range "0.01..100.00";
                                                        fraction-digits 2;
                                                    }
                                                    description "Percent rate override applied to the HS WRR group";
                                                }

                                            }
                                        }
                                    } // list hs-wrr-group

                                } // container overrides

                            } // container sap-egress

                            container policer-control-policy {
                                description "Enter the policer-control-policy context";

                                leaf policy-name {
                                    type leafref {
                                        path "../../../../../../../../qos/policer-control-policy/policer-control-policy-name";
                                    }
                                    description "Policer control policy name";
                                }

                                container overrides {
                                    presence "Enable the overrides context";
                                    description "Enable the overrides context";

                                    leaf-list apply-groups {
                                        type leafref {
                                            path "../../../../../../../../../groups/group/name";
                                        }
                                        max-elements 8;
                                        ordered-by user;
                                        description "Apply a configuration group at this level";
                                    }

                                    leaf-list apply-groups-exclude {
                                        type leafref {
                                            path "../../../../../../../../../groups/group/name";
                                        }
                                        max-elements 8;
                                        ordered-by user;
                                        description "Exclude a configuration group at this level";
                                    }

                                    container root {
                                        description "Enter the root context";

                                        leaf max-rate {
                                            type types-services:sap-max-rate-ovr;
                                            description "Maximum frame-based bandwidth limit";
                                        }

                                        container priority-mbs-thresholds {
                                            description "Enter the priority-mbs-thresholds context";

                                            leaf min-thresh-separation {
                                                type union {
                                                    type types-qos:bytes {
                                                        range "0..16777216";
                                                    }
                                                    type enumeration {
                                                        enum auto                           { value -1; }
                                                    }
                                                }
                                                units "bytes";
                                                description "Minimum amount of separation buffer space";
                                            }

                                            list priority {
                                                key "priority-level";
                                                description "Enter the priority list instance";

                                                leaf priority-level {
                                                    type types-qos:hierarchy-level;
                                                    description "Priority level";
                                                }

                                                leaf mbs-contribution {
                                                    type union {
                                                        type types-qos:bytes {
                                                            range "0..16777216";
                                                        }
                                                        type enumeration {
                                                            enum auto                           { value -1; }
                                                        }
                                                    }
                                                    units "bytes";
                                                    description "Minimum amount of cumulative buffer space allowed";
                                                }

                                                leaf-list apply-groups {
                                                    type leafref {
                                                        path "../../../../../../../../../../../../groups/group/name";
                                                    }
                                                    max-elements 8;
                                                    ordered-by user;
                                                    description "Apply a configuration group at this level";
                                                }

                                                leaf-list apply-groups-exclude {
                                                    type leafref {
                                                        path "../../../../../../../../../../../../groups/group/name";
                                                    }
                                                    max-elements 8;
                                                    ordered-by user;
                                                    description "Exclude a configuration group at this level";
                                                }

                                            } // list priority

                                        } // container priority-mbs-thresholds

                                    } // container root

                                } // container overrides

                            } // container policer-control-policy

                            container scheduler-policy {
                                description "Enter the scheduler-policy context";

                                leaf policy-name {
                                    type leafref {
                                        path "../../../../../../../../qos/scheduler-policy/scheduler-policy-name";
                                    }
                                    description "Scheduler policy name";
                                }

                                container overrides {
                                    description "Enter the overrides context";

                                    list scheduler {
                                        key "scheduler-name";
                                        description "Enter the scheduler list instance";

                                        leaf scheduler-name {
                                            type types-sros:named-item;
                                            description "Scheduler name";
                                        }

                                        leaf-list apply-groups {
                                            type leafref {
                                                path "../../../../../../../../../../groups/group/name";
                                            }
                                            max-elements 8;
                                            ordered-by user;
                                            description "Apply a configuration group at this level";
                                        }

                                        leaf-list apply-groups-exclude {
                                            type leafref {
                                                path "../../../../../../../../../../groups/group/name";
                                            }
                                            max-elements 8;
                                            ordered-by user;
                                            description "Exclude a configuration group at this level";
                                        }

                                        container parent {
                                            description "Enter the parent context";

                                            leaf weight {
                                                type types-qos:weight;
                                                description "Relative weight of the scheduler to feed the queue";
                                            }

                                            leaf cir-weight {
                                                type types-qos:weight;
                                                description "Weight used at the within-CIR port priority level";
                                            }

                                        } // container parent

                                        container rate {
                                            description "Enter the rate context";

                                            leaf pir {
                                                type union {
                                                    type int64 {
                                                        range "1..6400000000";
                                                    }
                                                    type enumeration {
                                                        enum max                            { value -1; }
                                                    }
                                                }
                                                units "kilobps";
                                                description "PIR at which the queue is to operate";
                                            }

                                            leaf cir {
                                                type union {
                                                    type int64 {
                                                        range "0..6400000000";
                                                    }
                                                    type enumeration {
                                                        enum sum                            { value -3; }
                                                        enum max                            { value -1; }
                                                    }
                                                }
                                                units "kilobps";
                                                description "CIR at which the queue it to operate";
                                            }

                                        } // container rate

                                    } // list scheduler

                                } // container overrides

                            } // container scheduler-policy

                            container vlan-qos-policy {
                                description "Enter the vlan-qos-policy context";

                                leaf policy-name {
                                    type leafref {
                                        path "../../../../../../../../qos/vlan-qos-policy/vlan-qos-policy-name";
                                    }
                                    description "Egress vlan-qos-policy name";
                                }

                                leaf port-redirect {
                                    type boolean;
                                    default "false";
                                    description "Enable egress vlan-qos-policy port-redirect";
                                }

                            } // container vlan-qos-policy

                            container egress-remark-policy {
                                description "Enter the egress-remark-policy context";

                                leaf policy-name {
                                    type leafref {
                                        path "../../../../../../../../qos/egress-remark-policy/egress-remark-policy-name";
                                    }
                                    description "Egress-remark-policy name";
                                }

                            } // container egress-remark-policy

                        } // container qos

                        container filter {
                            description "Enter the filter context";

                            leaf ip {
                                type leafref {
                                    path "../../../../../../../filter/ip-filter/filter-name";
                                }
                                description "IPv4 filter policy name";
                            }

                            leaf ipv6 {
                                type leafref {
                                    path "../../../../../../../filter/ipv6-filter/filter-name";
                                }
                                description "IPv6 filter policy name";
                            }

                        } // container filter

                        container virtual-port {
                            description "Enter the virtual-port context";

                            leaf vport-name {
                                type leafref {
                                    path "../../../../../../../port/ethernet/access/egress/virtual-port/vport-name";
                                }
                                description "Virtual port assigned to the SAP";
                            }

                        } // container virtual-port

                    } // container egress

                    container cpu-protection {
                        description "Enter the cpu-protection context";

                        leaf policy-id {
                            type leafref {
                                path "../../../../../../system/security/cpu-protection/policy/policy-id";
                            }
                            description "CPM protection policy";
                        }

                        choice monitoring {
                            case mac {

                                leaf mac-monitoring {
                                    type empty;
                                    description "Monitor MAC for CPU protection";
                                }

                            }
                            case cfm {

                                container eth-cfm-monitoring {
                                    presence "Enable the eth-cfm-monitoring context";
                                    description "Enable the eth-cfm-monitoring context";

                                    leaf aggregate {
                                        type empty;
                                        description "Apply rate limit to the sum of the per peer packet rates";
                                    }

                                    leaf car {
                                        type empty;
                                        description "Ignore Ethernet CFM packets when enforcing overall rate";
                                    }

                                } // container eth-cfm-monitoring

                            }
                            case ip {

                                leaf ip-src-monitoring {
                                    type empty;
                                    description "Enable IP source monitoring for CPU protection";
                                }

                            }
                        }
                    } // container cpu-protection

                    container lag {
                        description "Enter the lag context";

                        leaf link-map-profile {
                            type types-services:link-map-profile-id;
                            description "LAG link map profile for a SAP or network interface";
                        }

                        container per-link-hash {
                            description "Enter the per-link-hash context";

                            leaf class {
                                type types-services:sap-lag-per-link-hash-class;
                                default "1";
                                description "Class used on LAG egress using weighted per-link-hash";
                            }

                            leaf weight {
                                type types-services:sap-lag-per-link-hash-weight;
                                default "1";
                                description "Weight used on LAG egress using weighted per-link-hash";
                            }

                        } // container per-link-hash

                    } // container lag

                    container fwd-wholesale {
                        description "Enter the fwd-wholesale context";

                        leaf pppoe-service {
                            type leafref {
                                path "../../../../../epipe/service-name";
                            }
                            description "PPPoE service name";
                        }

                    } // container fwd-wholesale

                    container aarp {
                        presence "Enable the aarp context";
                        description "Enable the aarp context";

                        leaf id {
                            type leafref {
                                path "../../../../../../application-assurance/aarp/aarp-id";
                            }
                            description "AARP instance ID";
                        }

                        leaf type {
                            type types-services:dual-homing-bsx-aarp-service-ref-type;
                            description "Role referenced by the AARP";
                        }

                    } // container aarp

                    container transit-policy {
                        presence "Enable the transit-policy context";
                        description "Enable the transit-policy context";

                        choice transit-policy {
                            mandatory true;
                            case prefix {

                                leaf prefix {
                                    type leafref {
                                        path "../../../../../../application-assurance/group/partition/transit-prefix-policy/prefix-policy-id";
                                    }
                                    sros-ext:immutable;
                                    description "IP prefix policy ID";
                                }

                            }
                            case ip {

                                leaf ip {
                                    type leafref {
                                        path "../../../../../../application-assurance/group/partition/transit-ip-policy/ip-policy-id";
                                    }
                                    sros-ext:immutable;
                                    description "IP transit policy ID";
                                }

                            }
                        }
                    } // container transit-policy


                    container eth-cfm {
                        description "Enter the eth-cfm context";

                        leaf collect-lmm-stats {
                            type boolean;
                            default "false";
                            description "Collect statistics for loss measurement message tests";
                        }

                        leaf-list squelch-ingress-levels {
                            type uint32 {
                                range "0..7";
                            }
                            max-elements 8;
                            description "Levels for which ETH-CFM packets are silently discarded";
                        }

                        leaf-list apply-groups {
                            type leafref {
                                path "../../../../../../groups/group/name";
                            }
                            max-elements 8;
                            ordered-by user;
                            description "Apply a configuration group at this level";
                        }

                        leaf-list apply-groups-exclude {
                            type leafref {
                                path "../../../../../../groups/group/name";
                            }
                            max-elements 8;
                            ordered-by user;
                            description "Exclude a configuration group at this level";
                        }

                        container collect-lmm-fc-stats {
                            description "Enter the collect-lmm-fc-stats context";

                            leaf-list fc {
                                type types-eth-cfm:fc-type;
                                max-elements 8;
                                description "Forwarding class name for profile-unaware counter";
                            }

                            leaf-list fc-in-profile {
                                type types-eth-cfm:fc-type;
                                max-elements 8;
                                description "Forwarding class name for profile-aware counter";
                            }

                        } // container collect-lmm-fc-stats

                        list mep {
                            key "md-admin-name ma-admin-name mep-id";
                            description "Enter the mep list instance";

                            leaf md-admin-name {
                                type leafref {
                                    path "../../../../../../../eth-cfm/domain/md-admin-name";
                                }
                                description "Maintenance Domain (MD) name";
                            }

                            leaf ma-admin-name {
                                type leafref {
                                    path "../../../../../../../eth-cfm/domain[md-admin-name=current()/../md-admin-name]/association/ma-admin-name";
                                }
                                description "Maintenance Association (MA) name";
                            }

                            leaf mep-id {
                                type types-eth-cfm:mep-id-type;
                                description "Maintenance Endpoint (MEP) ID";
                            }

                            leaf admin-state {
                                type types-sros:admin-state;
                                default "disable";
                                description "Administrative state of the MEP";
                            }

                            leaf description {
                                type types-sros:description;
                                description "Text description";
                            }

                            leaf low-priority-defect {
                                type types-eth-cfm:lowest-alarm-priority;
                                default "mac-rem-err-xcon";
                                description "Lowest priority defect allowed to generate fault alarm";
                            }

                            leaf fault-propagation {
                                type types-eth-cfm:fault-propagation-type;
                                description "Fault propagation for the MEP";
                            }

                            leaf ccm {
                                type boolean;
                                default "false";
                                description "Generate CCM messages";
                            }

                            leaf ccm-ltm-priority {
                                type types-eth-cfm:frame-priority;
                                default "7";
                                description "Priority of CCM and LTM messages transmitted by the MEP";
                            }

                            leaf ccm-padding-size {
                                type uint32 {
                                    range "3..1500";
                                }
                                description "Number of octets of padding to insert in CCM packets";
                            }

                            leaf one-way-delay-threshold {
                                type uint32 {
                                    range "0..600";
                                }
                                units "seconds";
                                default "3";
                                description "Threshold time limit for the one-way delay test";
                            }

                            leaf ais {
                                type boolean;
                                default "false";
                                description "Enable the generation and the reception of AIS messages";
                            }

                            leaf-list apply-groups {
                                type leafref {
                                    path "../../../../../../../groups/group/name";
                                }
                                max-elements 8;
                                ordered-by user;
                                description "Apply a configuration group at this level";
                            }

                            leaf-list apply-groups-exclude {
                                type leafref {
                                    path "../../../../../../../groups/group/name";
                                }
                                max-elements 8;
                                ordered-by user;
                                description "Exclude a configuration group at this level";
                            }

                            container alarm-notification {
                                description "Enter the alarm-notification context";

                                leaf fng-alarm-time {
                                    type int32 {
                                        range "250|500|1000";
                                    }
                                    units "centiseconds";
                                    description "Time that must expire before an FNG alarm is raised";
                                }

                                leaf fng-reset-time {
                                    type int32 {
                                        range "250|500|1000";
                                    }
                                    units "centiseconds";
                                    description "Time that must expire before an FNG alarm is reset";
                                }

                            } // container alarm-notification

                            container csf {
                                presence "Enable the csf context";
                                description "Enable the csf context";

                                leaf multiplier {
                                    type decimal64 {
                                        range "0.0|2.0..30.0";
                                        fraction-digits 1;
                                    }
                                    default "3.5";
                                    description "Multiplication factor used to clear the CSF condition";
                                }

                            } // container csf

                            container eth-test {
                                presence "Enable the eth-test context";
                                description "Enable the eth-test context";

                                leaf bit-error-threshold {
                                    type uint32 {
                                        range "0..11840";
                                    }
                                    units "bit errors";
                                    default "1";
                                    description "Lowest priority defect allowed to generate fault alarm";
                                }

                                container test-pattern {
                                    description "Enter the test-pattern context";

                                    leaf pattern {
                                        type enumeration {
                                            enum all-zeros                      { value 0; }
                                            enum all-ones                       { value 1; }
                                        }
                                        default "all-zeros";
                                        description "Test pattern for Ethernet Test frames";
                                    }

                                    leaf crc-tlv {
                                        type boolean;
                                        default "false";
                                        description "Generate a CRC checksum";
                                    }

                                } // container test-pattern

                            } // container eth-test

                            container grace {
                                description "Enter the grace context";

                                container eth-ed {
                                    description "Enter the eth-ed context";

                                    leaf max-rx-defect-window {
                                        type uint32 {
                                            range "1..86400";
                                        }
                                        units "seconds";
                                        description "Maximum received ETH-ED expected defect window duration";
                                    }

                                    leaf priority {
                                        type int32 {
                                            range "0..7";
                                        }
                                        description "Transmission priority for ETH-ED PDUs";
                                    }

                                    leaf rx-eth-ed {
                                        type boolean;
                                        default "true";
                                        description "Receive and process ETH-ED ITU-T Y.1731 PDUs on the MEP";
                                    }

                                    leaf tx-eth-ed {
                                        type boolean;
                                        default "false";
                                        description "Transmit ETH-ED PDUs from the MEP";
                                    }

                                } // container eth-ed

                                container eth-vsm-grace {
                                    description "Enter the eth-vsm-grace context";

                                    leaf rx-eth-vsm-grace {
                                        type boolean;
                                        default "true";
                                        description "Receive and process Nokia ETH-CFM Grace PDU on the MEP";
                                    }

                                    leaf tx-eth-vsm-grace {
                                        type boolean;
                                        default "true";
                                        description "Transmit ETH-ED PDUs from the MEP";
                                    }

                                } // container eth-vsm-grace

                            } // container grace

                        } // list mep

                    } // container eth-cfm

                    list ip-tunnel {
                        key "tunnel-name";
                        max-elements 1;
                        description "Enter the ip-tunnel list instance";

                        leaf tunnel-name {
                            type types-sros:interface-name;
                            description "IP tunnel name";
                        }

                        leaf admin-state {
                            type types-sros:admin-state;
                            default "disable";
                            description "Administrative state of the IP tunnel";
                        }

                        leaf description {
                            type types-sros:description;
                            sros-ext:auto-restart-to-modify;
                            description "Text description";
                        }

                        leaf clear-df-bit {
                            type boolean;
                            sros-ext:auto-restart-to-modify;
                            default "false";
                            description "Clear the Do-not-Fragment bit";
                        }

                        leaf delivery-service {
                            type types-services:service-name;
                            sros-ext:auto-restart-to-modify;
                            description "Service to originate and terminate GRE packets";
                        }

                        leaf dscp {
                            type types-qos:dscp-name;
                            sros-ext:auto-restart-to-modify;
                            description "Differentiated Services Code Point (DSCP) name";
                        }

                        leaf encapsulated-ip-mtu {
                            type uint32 {
                                range "512..9000";
                            }
                            units "bytes";
                            sros-ext:auto-restart-to-modify;
                            description "Maximum size of the encapsulated tunnel packet";
                        }

                        leaf ip-mtu {
                            type uint32 {
                                range "512..9000";
                            }
                            units "bytes";
                            sros-ext:auto-restart-to-modify;
                            description "IP MTU for the interface";
                        }

                        leaf public-tcp-mss-adjust {
                            type union {
                                type uint32 {
                                    range "512..9000";
                                }
                                type enumeration {
                                    enum auto                           { value 0; }
                                }
                            }
                            units "bytes";
                            sros-ext:auto-restart-to-modify;
                            description "TCP Maximum Segment Size (MSS) on the public side";
                        }

                        leaf private-tcp-mss-adjust {
                            type int32 {
                                range "512..9000";
                            }
                            units "bytes";
                            sros-ext:auto-restart-to-modify;
                            description "TCP Maximum Segment Size (MSS) on the private side";
                        }

                        leaf reassembly {
                            type union {
                                type int32 {
                                    range "1..5000";
                                }
                                type enumeration {
                                    enum use-tunnel-group-setting       { value -1; }
                                    enum none                           { value 0; }
                                }
                            }
                            units "milliseconds";
                            sros-ext:auto-restart-to-modify;
                            description "Maximum reassembly wait time";
                        }

                        leaf remote-ip-address {
                            type types-sros:ip-address;
                            sros-ext:auto-restart-to-modify;
                            description "Remote IP address of the tunnel";
                        }

                        leaf backup-remote-ip-address {
                            type types-sros:ip-address;
                            sros-ext:auto-restart-to-modify;
                            description "Backup remote IP address that is applied to this tunnel";
                        }

                        leaf local-ip-address {
                            type types-sros:ip-address;
                            sros-ext:auto-restart-to-modify;
                            description "Local IP address of this tunnel";
                        }

                        leaf ipsec-transport-mode-profile {
                            type leafref {
                                path "../../../../../../ipsec/ipsec-transport-mode-profile/name";
                            }
                            sros-ext:auto-restart-to-modify;
                            description "IPsec transport mode profile name";
                        }

                        leaf propagate-pmtu-v4 {
                            type boolean;
                            sros-ext:auto-restart-to-modify;
                            description "Enable propagation of the path MTU to IPv4 hosts";
                        }

                        leaf propagate-pmtu-v6 {
                            type boolean;
                            sros-ext:auto-restart-to-modify;
                            description "Enable propagation of path MTU to IPv6 hosts";
                        }

                        leaf pmtu-discovery-aging {
                            type uint32 {
                                range "900..3600";
                            }
                            units "seconds";
                            sros-ext:auto-restart-to-modify;
                            default "900";
                            description "Time to age out the learned path MTU";
                        }

                        leaf-list apply-groups {
                            type leafref {
                                path "../../../../../../groups/group/name";
                            }
                            max-elements 8;
                            ordered-by user;
                            sros-ext:auto-restart-to-modify;
                            description "Apply a configuration group at this level";
                        }

                        leaf-list apply-groups-exclude {
                            type leafref {
                                path "../../../../../../groups/group/name";
                            }
                            max-elements 8;
                            ordered-by user;
                            sros-ext:auto-restart-to-modify;
                            description "Exclude a configuration group at this level";
                        }

                        container icmp6-generation {
                            sros-ext:auto-restart-to-modify;
                            description "Enter the icmp6-generation context";

                            container packet-too-big {
                                sros-ext:auto-restart-to-modify;
                                description "Enter the packet-too-big context";

                                leaf admin-state {
                                    type types-sros:admin-state;
                                    sros-ext:auto-restart-to-modify;
                                    description "Administrative state of sending Packet Too Big messages";
                                }

                                leaf number {
                                    type uint32 {
                                        range "10..1000";
                                    }
                                    sros-ext:auto-restart-to-modify;
                                    default "100";
                                    description "Maximum number of PTB ICMPv6 messages that can be sent";
                                }

                                leaf seconds {
                                    type uint32 {
                                        range "1..60";
                                    }
                                    units "seconds";
                                    sros-ext:auto-restart-to-modify;
                                    default "10";
                                    description "Maximum interval when PTB messages can be sent";
                                }

                            } // container packet-too-big

                        } // container icmp6-generation

                        container gre-header {
                            sros-ext:auto-restart-to-modify;
                            description "Enter the gre-header context";

                            leaf admin-state {
                                type types-sros:admin-state;
                                sros-ext:auto-restart-to-modify;
                                description "Administrative state of the GRE header in the tunnel";
                            }

                            container key {
                                sros-ext:auto-restart-to-modify;
                                description "Enter the key context";

                                leaf admin-state {
                                    type types-sros:admin-state;
                                    sros-ext:auto-restart-to-modify;
                                    default "disable";
                                    description "Administrative state of the keys in the GRE header";
                                }

                                leaf send {
                                    type uint32;
                                    sros-ext:auto-restart-to-modify;
                                    default "0";
                                    description "Send key of the GRE header";
                                }

                                leaf receive {
                                    type uint32;
                                    sros-ext:auto-restart-to-modify;
                                    default "0";
                                    description "Receive key of the GRE header";
                                }

                            } // container key

                        } // container gre-header

                        container icmp-generation {
                            sros-ext:auto-restart-to-modify;
                            description "Enter the icmp-generation context";

                            container frag-required {
                                sros-ext:auto-restart-to-modify;
                                description "Enter the frag-required context";

                                leaf admin-state {
                                    type types-sros:admin-state;
                                    sros-ext:auto-restart-to-modify;
                                    description "Administrative state of sending ICMP messages";
                                }

                                leaf message-count {
                                    type uint32 {
                                        range "10..1000";
                                    }
                                    sros-ext:auto-restart-to-modify;
                                    default "100";
                                    description "Maximum number of ICMP messages sent";
                                }

                                leaf interval {
                                    type uint32 {
                                        range "1..60";
                                    }
                                    units "seconds";
                                    sros-ext:auto-restart-to-modify;
                                    default "10";
                                    description "Interval for sending ICMP messages";
                                }

                            } // container frag-required

                        } // container icmp-generation

                        list dest-ip {
                            key "dest-ip-address";
                            description "Add a list entry for dest-ip";

                            leaf dest-ip-address {
                                type types-sros:ip-address;
                                description "IP address of the remote IP tunnel endpoint";
                            }

                        } // list dest-ip

                    } // list ip-tunnel

                    list ipsec-gateway {
                        key "name";
                        max-elements 1;
                        description "Enter the ipsec-gateway list instance";

                        leaf name {
                            type types-sros:named-item;
                            description "IPsec gateway name";
                        }

                        leaf admin-state {
                            type types-sros:admin-state;
                            default "disable";
                            description "Administrative state of the IPsec gateway";
                        }

                        leaf default-tunnel-template {
                            type leafref {
                                path "../../../../../../ipsec/tunnel-template/id";
                            }
                            description "Default tunnel policy template for the gateway";
                        }

                        leaf ike-policy {
                            type leafref {
                                path "../../../../../../ipsec/ike-policy/id";
                            }
                            description "IKE policy ID";
                        }

                        leaf pre-shared-key {
                            type types-sros:encrypted-leaf {
                                length "1..115";
                            }
                            description "Pre-shared key for the IPsec gateway";
                        }

                        leaf ts-list {
                            type leafref {
                                path "../../../../../../ipsec/ts-list/name";
                            }
                            description "TS list used for IKEv2 TS negotiation";
                        }

                        leaf-list apply-groups {
                            type leafref {
                                path "../../../../../../groups/group/name";
                            }
                            max-elements 8;
                            ordered-by user;
                            description "Apply a configuration group at this level";
                        }

                        leaf-list apply-groups-exclude {
                            type leafref {
                                path "../../../../../../groups/group/name";
                            }
                            max-elements 8;
                            ordered-by user;
                            description "Exclude a configuration group at this level";
                        }

                        container dhcp-address-assignment {
                            description "Enter the dhcp-address-assignment context";

                            container dhcpv4 {
                                presence "Enable the dhcpv4 context";
                                description "Enable the dhcpv4 context";

                                leaf admin-state {
                                    type types-sros:admin-state;
                                    default "disable";
                                    description "Administrative state of the IPsec DHCPv4 server";
                                }

                                leaf gi-address {
                                    type types-sros:ipv4-unicast-address;
                                    sros-ext:auto-restart-to-modify;
                                    description "Gateway IP address of DHCPv4 packets sent by the system";
                                }

                                leaf send-release {
                                    type boolean;
                                    sros-ext:auto-restart-to-modify;
                                    default "true";
                                    description "Send DHCPv4 release message when IPsec tunnel removed";
                                }

                                leaf-list apply-groups {
                                    type leafref {
                                        path "../../../../../../../../groups/group/name";
                                    }
                                    max-elements 8;
                                    ordered-by user;
                                    sros-ext:auto-restart-to-modify;
                                    description "Apply a configuration group at this level";
                                }

                                leaf-list apply-groups-exclude {
                                    type leafref {
                                        path "../../../../../../../../groups/group/name";
                                    }
                                    max-elements 8;
                                    ordered-by user;
                                    sros-ext:auto-restart-to-modify;
                                    description "Exclude a configuration group at this level";
                                }

                                container server {
                                    sros-ext:auto-restart-to-modify;
                                    description "Enter the server context";

                                    leaf-list address {
                                        type types-sros:ipv4-unicast-address;
                                        max-elements 8;
                                        sros-ext:auto-restart-to-modify;
                                        description "DHCPv4 server addresses";
                                    }

                                    leaf router-instance {
                                        type types-sros:router-instance-base-vprn-loose;
                                        sros-ext:auto-restart-to-modify;
                                        description "Router instance used to reach the DHCPv4 server";
                                    }

                                } // container server

                            } // container dhcpv4

                            container dhcpv6 {
                                presence "Enable the dhcpv6 context";
                                description "Enable the dhcpv6 context";

                                leaf admin-state {
                                    type types-sros:admin-state;
                                    default "disable";
                                    description "Administrative state of the DHCPv6 server";
                                }

                                leaf link-address {
                                    type types-sros:ipv6-unicast-address;
                                    sros-ext:auto-restart-to-modify;
                                    description "Link address of the relayed DHCPv6 packets";
                                }

                                leaf send-release {
                                    type boolean;
                                    sros-ext:auto-restart-to-modify;
                                    default "true";
                                    description "Send DHCPv6 release message when IPsec tunnel removed";
                                }

                                leaf-list apply-groups {
                                    type leafref {
                                        path "../../../../../../../../groups/group/name";
                                    }
                                    max-elements 8;
                                    ordered-by user;
                                    sros-ext:auto-restart-to-modify;
                                    description "Apply a configuration group at this level";
                                }

                                leaf-list apply-groups-exclude {
                                    type leafref {
                                        path "../../../../../../../../groups/group/name";
                                    }
                                    max-elements 8;
                                    ordered-by user;
                                    sros-ext:auto-restart-to-modify;
                                    description "Exclude a configuration group at this level";
                                }

                                container server {
                                    sros-ext:auto-restart-to-modify;
                                    description "Enter the server context";

                                    leaf-list address {
                                        type types-sros:ipv6-unicast-address;
                                        max-elements 8;
                                        sros-ext:auto-restart-to-modify;
                                        description "DHCPv6 server addresses";
                                    }

                                    leaf router-instance {
                                        type types-sros:router-instance-base-vprn-loose;
                                        sros-ext:auto-restart-to-modify;
                                        description "Router instance to reach the DHCPv6 server";
                                    }

                                } // container server

                            } // container dhcpv6

                        } // container dhcp-address-assignment

                        container cert {
                            description "Enter the cert context";

                            leaf cert-profile {
                                type leafref {
                                    path "../../../../../../../ipsec/cert-profile/name";
                                }
                                description "Certificate profile name";
                            }

                            leaf trust-anchor-profile {
                                type leafref {
                                    path "../../../../../../../ipsec/trust-anchor-profile/name";
                                }
                                description "Trust anchor profile name";
                            }

                            container status-verify {
                                description "Enter the status-verify context";

                                leaf default-result {
                                    type enumeration {
                                        enum revoked                        { value 0; }
                                        enum good                           { value 1; }
                                    }
                                    default "revoked";
                                    description "Default result of Certificate Status Verification (CSV)";
                                }

                                leaf primary {
                                    type types-ipsec:cert-revocation-status;
                                    default "crl";
                                    description "Primary method of CSV to verify the revocation status";
                                }

                                leaf secondary {
                                    type types-ipsec:cert-revocation-status-with-none;
                                    default "none";
                                    description "Secondary method of CSV to verify the revocation status";
                                }

                            } // container status-verify

                        } // container cert

                        container client-db {
                            presence "Enable the client-db context";
                            description "Enable the client-db context";

                            leaf name {
                                type leafref {
                                    path "../../../../../../../ipsec/client-db/name";
                                }
                                mandatory true;
                                description "Client database name";
                            }

                            leaf fallback {
                                type boolean;
                                default "true";
                                description "Fall back to the default authentication policy";
                            }

                        } // container client-db

                        container default-secure-service {
                            presence "Enable the default-secure-service context";
                            description "Enable the default-secure-service context";

                            leaf service-name {
                                type types-services:service-name;
                                sros-ext:auto-restart-to-modify;
                                description "Default security service name";
                            }

                            leaf interface {
                                type types-sros:interface-name;
                                sros-ext:auto-restart-to-modify;
                                description "Private IPsec tunnel interface name";
                            }

                        } // container default-secure-service

                        container local {
                            description "Enter the local context";

                            leaf gateway-address {
                                type types-sros:ip-address;
                                sros-ext:auto-restart-to-modify;
                                description "Local gateway address of the IPsec gateway";
                            }

                            container id {
                                description "Enter the id context";

                                choice id {
                                    default "auto";
                                    case auto {

                                        leaf auto {
                                            type empty;
                                            sros-ext:auto-restart-to-modify;
                                            description "Select ID based on authentication method in IKE policy";
                                        }

                                    }
                                    case ipv4 {

                                        leaf ipv4 {
                                            type types-sros:ipv4-unicast-address;
                                            sros-ext:auto-restart-to-modify;
                                            description "IPv4 address as the local ID type";
                                        }

                                    }
                                    case ipv6 {

                                        leaf ipv6 {
                                            type types-sros:ip-address;
                                            sros-ext:auto-restart-to-modify;
                                            description "IPv6 address as the local ID type";
                                        }

                                    }
                                    case fqdn {

                                        leaf fqdn {
                                            type types-sros:fully-qualified-domain-name;
                                            sros-ext:auto-restart-to-modify;
                                            description "FQDN as the local ID type";
                                        }

                                    }
                                }
                            } // container id

                            container address-assignment {
                                presence "Enable the address-assignment context";
                                description "Enable the address-assignment context";

                                leaf admin-state {
                                    type types-sros:admin-state;
                                    default "disable";
                                    description "Administrative state of local address assignments";
                                }

                                leaf-list apply-groups {
                                    type leafref {
                                        path "../../../../../../../../groups/group/name";
                                    }
                                    max-elements 8;
                                    ordered-by user;
                                    sros-ext:auto-restart-to-modify;
                                    description "Apply a configuration group at this level";
                                }

                                leaf-list apply-groups-exclude {
                                    type leafref {
                                        path "../../../../../../../../groups/group/name";
                                    }
                                    max-elements 8;
                                    ordered-by user;
                                    sros-ext:auto-restart-to-modify;
                                    description "Exclude a configuration group at this level";
                                }

                                container ipv4 {
                                    presence "Enable the ipv4 context";
                                    sros-ext:auto-restart-to-modify;
                                    description "Enable the ipv4 context";

                                    leaf router-instance {
                                        type types-sros:router-instance-base-vprn-loose;
                                        sros-ext:auto-restart-to-modify;
                                        mandatory true;
                                        description "Router instance ID for the local DHCPv4 server";
                                    }

                                    leaf dhcp-server {
                                        type types-sros:named-item;
                                        sros-ext:auto-restart-to-modify;
                                        mandatory true;
                                        description "Local DHCPv4 server name";
                                    }

                                    leaf pool {
                                        type types-sros:named-item;
                                        sros-ext:auto-restart-to-modify;
                                        mandatory true;
                                        description "Name of the pool defined in the specified DHCPv4 server";
                                    }

                                    leaf secondary-pool {
                                        type types-sros:named-item;
                                        sros-ext:auto-restart-to-modify;
                                        description "Name of the secondary pool defined in the DHCPv4 server";
                                    }

                                } // container ipv4

                                container ipv6 {
                                    presence "Enable the ipv6 context";
                                    sros-ext:auto-restart-to-modify;
                                    description "Enable the ipv6 context";

                                    leaf router-instance {
                                        type types-sros:router-instance-base-vprn-loose;
                                        sros-ext:auto-restart-to-modify;
                                        mandatory true;
                                        description "Router instance ID hosting the DHCPv6 connection";
                                    }

                                    leaf dhcp-server {
                                        type types-sros:named-item;
                                        sros-ext:auto-restart-to-modify;
                                        mandatory true;
                                        description "Local DHCPv6 server name";
                                    }

                                    leaf pool {
                                        type types-sros:named-item;
                                        sros-ext:auto-restart-to-modify;
                                        mandatory true;
                                        description "Secondary pool name defined in the DHCPv6 server";
                                    }

                                } // container ipv6

                            } // container address-assignment

                        } // container local

                        container radius {
                            description "Enter the radius context";

                            leaf accounting-policy {
                                type leafref {
                                    path "../../../../../../../ipsec/radius/accounting-policy/name";
                                }
                                description "RADIUS accounting policy";
                            }

                            leaf authentication-policy {
                                type leafref {
                                    path "../../../../../../../ipsec/radius/authentication-policy/name";
                                }
                                description "RADIUS authentication policy";
                            }

                        } // container radius

                        container max-history-key-records {
                            description "Enter the max-history-key-records context";

                            leaf ike {
                                type uint32 {
                                    range "1..3";
                                }
                                description "Maximum number of historical IKE keys recorded";
                            }

                            leaf esp {
                                type uint32 {
                                    range "1..48";
                                }
                                description "Maximum number of recent records";
                            }

                        } // container max-history-key-records

                    } // list ipsec-gateway

                    list ipsec-tunnel {
                        key "name";
                        description "Enter the ipsec-tunnel list instance";

                        leaf name {
                            type types-sros:named-item {
                                pattern "[a-zA-Z]+.*" {
                                    error-message "IPSec tunnel name cannot start with a number";
                                }
                            }
                            description "IPsec tunnel name";
                        }

                        leaf admin-state {
                            type types-sros:admin-state;
                            default "disable";
                            description "Administrative state of the IPsec tunnel";
                        }

                        leaf description {
                            type types-sros:description;
                            description "Text description";
                        }

                        leaf clear-df-bit {
                            type boolean;
                            sros-ext:auto-restart-to-modify;
                            default "false";
                            description "Reset the DF bit to 0 in all payload IP packets";
                        }

                        leaf copy-traffic-class-upon-decapsulation {
                            type boolean;
                            sros-ext:auto-restart-to-modify;
                            default "false";
                            description "Enable traffic class copy upon decapsulation";
                        }

                        leaf encapsulated-ip-mtu {
                            type uint32 {
                                range "512..9000";
                            }
                            units "bytes";
                            sros-ext:auto-restart-to-modify;
                            description "Maximum size of the encapsulated tunnel packet";
                        }

                        leaf ip-mtu {
                            type uint32 {
                                range "512..9000";
                            }
                            units "bytes";
                            sros-ext:auto-restart-to-modify;
                            description "Private MTU of the IPsec tunnel";
                        }

                        leaf replay-window {
                            type uint32 {
                                range "32|64|128|256|512";
                            }
                            units "packets";
                            sros-ext:auto-restart-to-modify;
                            description "Anti-replay window size";
                        }

                        leaf public-tcp-mss-adjust {
                            type union {
                                type uint32 {
                                    range "512..9000";
                                }
                                type enumeration {
                                    enum auto                           { value 0; }
                                }
                            }
                            units "bytes";
                            sros-ext:auto-restart-to-modify;
                            description "TCP maximum segment size (MSS) on the public network";
                        }

                        leaf private-tcp-mss-adjust {
                            type int32 {
                                range "512..9000";
                            }
                            units "bytes";
                            sros-ext:auto-restart-to-modify;
                            description "TCP maximum segment size (MSS) adjustment";
                        }

                        leaf propagate-pmtu-v4 {
                            type boolean;
                            sros-ext:auto-restart-to-modify;
                            default "true";
                            description "Enable propagation of the path MTU to IPv4 hosts";
                        }

                        leaf propagate-pmtu-v6 {
                            type boolean;
                            sros-ext:auto-restart-to-modify;
                            default "true";
                            description "Enable propagation of the path MTU to IPv6 hosts";
                        }

                        leaf pmtu-discovery-aging {
                            type uint32 {
                                range "900..3600";
                            }
                            units "seconds";
                            sros-ext:auto-restart-to-modify;
                            default "900";
                            description "Aging out time of the learned path MTU";
                        }

                        leaf-list apply-groups {
                            type leafref {
                                path "../../../../../../groups/group/name";
                            }
                            max-elements 8;
                            ordered-by user;
                            sros-ext:auto-restart-to-modify;
                            description "Apply a configuration group at this level";
                        }

                        leaf-list apply-groups-exclude {
                            type leafref {
                                path "../../../../../../groups/group/name";
                            }
                            max-elements 8;
                            ordered-by user;
                            sros-ext:auto-restart-to-modify;
                            description "Exclude a configuration group at this level";
                        }

                        container bfd {
                            sros-ext:auto-restart-to-modify;
                            description "Enter the bfd context";

                            leaf bfd-designate {
                                type boolean;
                                sros-ext:auto-restart-to-modify;
                                default "false";
                                description "Designate IPsec tunnel to carry BFD traffic";
                            }

                            container bfd-liveness {
                                presence "Enable the bfd-liveness context";
                                sros-ext:auto-restart-to-modify;
                                description "Enable the bfd-liveness context";

                                leaf dest-ip {
                                    type types-sros:ipv4-unicast-address;
                                    sros-ext:auto-restart-to-modify;
                                    mandatory true;
                                    description "Destination address used for the BFD session";
                                }

                                leaf interface {
                                    type types-sros:interface-name;
                                    sros-ext:auto-restart-to-modify;
                                    mandatory true;
                                    description "Name of the interface used by the BFD session";
                                }

                                leaf service-name {
                                    type types-services:service-name;
                                    sros-ext:auto-restart-to-modify;
                                    mandatory true;
                                    description "Administrative service name";
                                }

                            } // container bfd-liveness

                        } // container bfd

                        container icmp6-generation {
                            sros-ext:auto-restart-to-modify;
                            description "Enter the icmp6-generation context";

                            container packet-too-big {
                                sros-ext:auto-restart-to-modify;
                                description "Enter the packet-too-big context";

                                leaf admin-state {
                                    type types-sros:admin-state;
                                    sros-ext:auto-restart-to-modify;
                                    default "enable";
                                    description "Administrative state of Packet Too Big message sends";
                                }

                                leaf message-count {
                                    type uint32 {
                                        range "10..1000";
                                    }
                                    sros-ext:auto-restart-to-modify;
                                    default "100";
                                    description "Maximum number of ICMPv6 PTB messages that can be sent";
                                }

                                leaf interval {
                                    type uint32 {
                                        range "1..60";
                                    }
                                    units "seconds";
                                    sros-ext:auto-restart-to-modify;
                                    default "10";
                                    description "Interval for sending Packet Too Big messages";
                                }

                            } // container packet-too-big

                        } // container icmp6-generation

                        container key-exchange {
                            sros-ext:auto-restart-to-modify;
                            description "Enter the key-exchange context";

                            choice type {
                                case dynamic {

                                    container dynamic {
                                        presence "Enable the dynamic context";
                                        sros-ext:auto-restart-to-modify;
                                        description "Enable the dynamic context";

                                        leaf auto-establish {
                                            type boolean;
                                            sros-ext:auto-restart-to-modify;
                                            default "false";
                                            description "Attempt to establish a phase 1 exchange automatically";
                                        }

                                        leaf ike-policy {
                                            type leafref {
                                                path "../../../../../../../../ipsec/ike-policy/id";
                                            }
                                            sros-ext:auto-restart-to-modify;
                                            description "IKE policy ID";
                                        }

                                        leaf-list ipsec-transform {
                                            type leafref {
                                                path "../../../../../../../../ipsec/ipsec-transform/id";
                                            }
                                            max-elements 4;
                                            sros-ext:auto-restart-to-modify;
                                            description "IPsec transform IDs used by the dynamic key";
                                        }

                                        leaf pre-shared-key {
                                            type types-sros:encrypted-leaf {
                                                length "1..115";
                                            }
                                            sros-ext:auto-restart-to-modify;
                                            description "Pre-shared key for authentication";
                                        }

                                        container cert {
                                            sros-ext:auto-restart-to-modify;
                                            description "Enter the cert context";

                                            leaf cert-profile {
                                                type leafref {
                                                    path "../../../../../../../../../ipsec/cert-profile/name";
                                                }
                                                description "Certificate profile name";
                                            }

                                            leaf trust-anchor-profile {
                                                type leafref {
                                                    path "../../../../../../../../../ipsec/trust-anchor-profile/name";
                                                }
                                                description "Trust anchor profile name";
                                            }

                                            container status-verify {
                                                sros-ext:auto-restart-to-modify;
                                                description "Enter the status-verify context";

                                                leaf default-result {
                                                    type enumeration {
                                                        enum revoked                        { value 0; }
                                                        enum good                           { value 1; }
                                                    }
                                                    default "revoked";
                                                    description "Default result for Certificate Status Verification";
                                                }

                                                leaf primary {
                                                    type types-ipsec:cert-revocation-status;
                                                    default "crl";
                                                    description "Primary method of CSV to verify the revocation status";
                                                }

                                                leaf secondary {
                                                    type types-ipsec:cert-revocation-status-with-none;
                                                    default "none";
                                                    description "Secondary method used to verify certificate revocation";
                                                }

                                            } // container status-verify

                                        } // container cert

                                        container id {
                                            sros-ext:auto-restart-to-modify;
                                            description "Enter the id context";

                                            choice id {
                                                case ipv4 {

                                                    leaf ipv4 {
                                                        type types-sros:ipv4-unicast-address;
                                                        sros-ext:auto-restart-to-modify;
                                                        description "IPv4 as the local ID type";
                                                    }

                                                }
                                                case ipv6 {

                                                    leaf ipv6 {
                                                        type types-sros:ip-address;
                                                        sros-ext:auto-restart-to-modify;
                                                        description "IPv6 used as the local IKE ID type";
                                                    }

                                                }
                                                case fqdn {

                                                    leaf fqdn {
                                                        type types-sros:fully-qualified-domain-name;
                                                        sros-ext:auto-restart-to-modify;
                                                        description "FQDN used as the local ID IKE type";
                                                    }

                                                }
                                            }
                                        } // container id


                                    } // container dynamic

                                }
                                case manual {

                                    container manual {
                                        presence "Enable the manual context";
                                        sros-ext:auto-restart-to-modify;
                                        description "Enable the manual context";

                                        list keys {
                                            key "security-association direction";
                                            description "Enter the keys list instance";

                                            leaf security-association {
                                                type uint32 {
                                                    range "1..16";
                                                }
                                                description "SA entry ID";
                                            }

                                            leaf direction {
                                                type enumeration {
                                                    enum inbound                        { value 1; }
                                                    enum outbound                       { value 2; }
                                                }
                                                description "Direction of the IPsec tunnel";
                                            }

                                            leaf ipsec-transform {
                                                type leafref {
                                                    path "../../../../../../../../../ipsec/ipsec-transform/id";
                                                }
                                                sros-ext:immutable;
                                                mandatory true;
                                                description "Transform entry used by manual SAs";
                                            }

                                            leaf spi {
                                                type uint32 {
                                                    range "256..16383";
                                                }
                                                sros-ext:immutable;
                                                mandatory true;
                                                description "SPI of inbound and outbound packets";
                                            }

                                            leaf authentication-key {
                                                type types-sros:hex-string {
                                                    length "1..130";
                                                }
                                                sros-ext:immutable;
                                                description "Key used for the authentication algorithm";
                                            }

                                            leaf encryption-key {
                                                type types-sros:hex-string {
                                                    length "1..66";
                                                }
                                                sros-ext:immutable;
                                                description "Key used for the encryption algorithm";
                                            }

                                            leaf-list apply-groups {
                                                type leafref {
                                                    path "../../../../../../../../../groups/group/name";
                                                }
                                                max-elements 8;
                                                ordered-by user;
                                                description "Apply a configuration group at this level";
                                            }

                                            leaf-list apply-groups-exclude {
                                                type leafref {
                                                    path "../../../../../../../../../groups/group/name";
                                                }
                                                max-elements 8;
                                                ordered-by user;
                                                description "Exclude a configuration group at this level";
                                            }

                                        } // list keys

                                    } // container manual

                                }
                            }
                        } // container key-exchange

                        container max-history-key-records {
                            sros-ext:auto-restart-to-modify;
                            description "Enter the max-history-key-records context";

                            leaf ike {
                                type uint32 {
                                    range "1..3";
                                }
                                sros-ext:auto-restart-to-modify;
                                description "Maximum number of historical IKE key records";
                            }

                            leaf esp {
                                type uint32 {
                                    range "1..48";
                                }
                                sros-ext:auto-restart-to-modify;
                                description "Maximum number of recent records";
                            }

                        } // container max-history-key-records

                        container tunnel-endpoint {
                            presence "Enable the tunnel-endpoint context";
                            sros-ext:auto-restart-to-modify;
                            description "Enable the tunnel-endpoint context";

                            leaf local-gateway-address {
                                type types-sros:ip-address;
                                sros-ext:auto-restart-to-modify;
                                mandatory true;
                                description "Address used for tunnel of the remote security gateway";
                            }

                            leaf remote-ip-address {
                                type types-sros:ip-address;
                                sros-ext:auto-restart-to-modify;
                                mandatory true;
                                description "Remote IP address of the tunnel";
                            }

                            leaf delivery-service {
                                type types-services:service-name;
                                sros-ext:auto-restart-to-modify;
                                mandatory true;
                                description "Delivery service name";
                            }

                        } // container tunnel-endpoint

                        container icmp-generation {
                            sros-ext:auto-restart-to-modify;
                            description "Enter the icmp-generation context";

                            container frag-required {
                                sros-ext:auto-restart-to-modify;
                                description "Enter the frag-required context";

                                leaf admin-state {
                                    type types-sros:admin-state;
                                    sros-ext:auto-restart-to-modify;
                                    default "enable";
                                    description "Administrative state of sending ICMP messages";
                                }

                                leaf message-count {
                                    type uint32 {
                                        range "10..1000";
                                    }
                                    sros-ext:auto-restart-to-modify;
                                    default "100";
                                    description "Maximum number of ICMP messages that can be sent";
                                }

                                leaf interval {
                                    type uint32 {
                                        range "1..60";
                                    }
                                    units "seconds";
                                    sros-ext:auto-restart-to-modify;
                                    default "10";
                                    description "Interval for sending ICMP messages";
                                }

                            } // container frag-required

                        } // container icmp-generation

                        list dest-ip {
                            key "address";
                            max-elements 16;
                            description "Add a list entry for dest-ip";

                            leaf address {
                                type types-sros:ip-address;
                                description "Private IP address of the remote IP tunnel endpoint";
                            }

                        } // list dest-ip

                        container security-policy {
                            sros-ext:auto-restart-to-modify;
                            description "Enter the security-policy context";

                            leaf id {
                                type leafref {
                                    path "../../../../../ipsec/security-policy/id";
                                }
                                sros-ext:auto-restart-to-modify;
                                description "IPsec security policy ID";
                            }

                            leaf strict-match {
                                type boolean;
                                sros-ext:auto-restart-to-modify;
                                default "false";
                                description "Enable strict match of the security policy entry";
                            }

                        } // container security-policy

                    } // list ipsec-tunnel

                    container static-host {
                        description "Enter the static-host context";

                        list ipv4 {
                            key "ip mac";
                            description "Enter the ipv4 list instance";

                            leaf ip {
                                type types-sros:ipv4-address;
                                description "IP address";
                            }

                            leaf mac {
                                type types-sros:mac-unicast-address;
                                description "MAC address";
                            }

                            leaf admin-state {
                                type types-sros:admin-state;
                                default "disable";
                                description "Administrative state of the static host";
                            }

                            leaf sub-profile {
                                type leafref {
                                    path "../../../../../../../subscriber-mgmt/sub-profile/name";
                                }
                                description "Sub-profile name";
                            }

                            leaf sla-profile {
                                type leafref {
                                    path "../../../../../../../subscriber-mgmt/sla-profile/name";
                                }
                                description "SLA profile name";
                            }

                            leaf ancp-string {
                                type types-submgt:ancp-string;
                                description "ANCP string";
                            }

                            leaf int-dest-id {
                                type types-submgt:int-dest-id;
                                description "Intermediate destination ID";
                            }

                            leaf-list apply-groups {
                                type leafref {
                                    path "../../../../../../../groups/group/name";
                                }
                                max-elements 8;
                                ordered-by user;
                                description "Apply a configuration group at this level";
                            }

                            leaf-list apply-groups-exclude {
                                type leafref {
                                    path "../../../../../../../groups/group/name";
                                }
                                max-elements 8;
                                ordered-by user;
                                description "Exclude a configuration group at this level";
                            }

                            container app-profile {
                                description "Enter the app-profile context";

                                leaf profile {
                                    type leafref {
                                        path "../../../../../../../../application-assurance/group/partition/policy/app-profile/app-profile-name";
                                    }
                                    description "Application profile used by the static host";
                                }

                            } // container app-profile

                            container subscriber-id {
                                description "Enter the subscriber-id context";

                                choice subscriber-id {
                                    case string {

                                        leaf string {
                                            type types-submgt:subscriber-id;
                                            description "Subscriber identification";
                                        }

                                    }
                                    case use-sap-id {

                                        leaf use-sap-id {
                                            type empty;
                                            description "Use the SAP id as subscriber ID";
                                        }

                                    }
                                }
                            } // container subscriber-id

                        } // list ipv4

                    } // container static-host

                } // list sap

                list vpls {
                    when "../tunnel = 'false'" {
                        description "vpls not allowed in a tunnel interface";
                    }
                    key "vpls-name";
                    max-elements 1;
                    description "Enter the vpls list instance";

                    leaf vpls-name {
                        type types-sros:named-item-64;
                        description "VPLS service";
                    }

                    leaf ip-stats {
                        type boolean;
                        default "false";
                        description "Enable statistics collection";
                    }

                    leaf-list apply-groups {
                        type leafref {
                            path "../../../../../groups/group/name";
                        }
                        max-elements 8;
                        ordered-by user;
                        description "Apply a configuration group at this level";
                    }

                    leaf-list apply-groups-exclude {
                        type leafref {
                            path "../../../../../groups/group/name";
                        }
                        max-elements 8;
                        ordered-by user;
                        description "Exclude a configuration group at this level";
                    }

                    container evpn {
                        description "Enter the evpn context";

                        container arp {
                            description "Enter the arp context";

                            leaf learn-dynamic {
                                type boolean;
                                default "true";
                                description "Process ARP or ND messages on EVPN tunnels";
                            }

                            leaf flood-garp-and-unknown-req {
                                type boolean;
                                default "true";
                                description "Allow CPM originated ARP frames to flood R-VPLS service";
                            }

                            list advertise {
                                key "route-type";
                                description "Enter the advertise list instance";

                                leaf route-type {
                                    type enumeration {
                                        enum static                         { value 1; }
                                        enum dynamic                        { value 2; }
                                    }
                                    description "Type of ARP or ND entries that generate host routes";
                                }

                                leaf route-tag {
                                    type uint32 {
                                        range "0..255";
                                    }
                                    sros-ext:immutable;
                                    description "Tag value used with the host route from an ARP/ND entry";
                                }

                                leaf-list apply-groups {
                                    type leafref {
                                        path "../../../../../../../../groups/group/name";
                                    }
                                    max-elements 8;
                                    ordered-by user;
                                    description "Apply a configuration group at this level";
                                }

                                leaf-list apply-groups-exclude {
                                    type leafref {
                                        path "../../../../../../../../groups/group/name";
                                    }
                                    max-elements 8;
                                    ordered-by user;
                                    description "Exclude a configuration group at this level";
                                }

                            } // list advertise

                        } // container arp

                        container nd {
                            description "Enter the nd context";

                            leaf learn-dynamic {
                                type boolean;
                                default "true";
                                description "Process ARP or ND messages on EVPN tunnels";
                            }

                            list advertise {
                                key "route-type";
                                description "Enter the advertise list instance";

                                leaf route-type {
                                    type enumeration {
                                        enum static                         { value 1; }
                                        enum dynamic                        { value 2; }
                                    }
                                    description "Type of ARP or ND entries that generate host routes";
                                }

                                leaf route-tag {
                                    type uint32 {
                                        range "0..255";
                                    }
                                    sros-ext:immutable;
                                    description "Tag value used with the host route from an ARP/ND entry";
                                }

                                leaf-list apply-groups {
                                    type leafref {
                                        path "../../../../../../../../groups/group/name";
                                    }
                                    max-elements 8;
                                    ordered-by user;
                                    description "Apply a configuration group at this level";
                                }

                                leaf-list apply-groups-exclude {
                                    type leafref {
                                        path "../../../../../../../../groups/group/name";
                                    }
                                    max-elements 8;
                                    ordered-by user;
                                    description "Exclude a configuration group at this level";
                                }

                            } // list advertise

                        } // container nd

                    } // container evpn

                    container evpn-tunnel {
                        presence "Enable the evpn-tunnel context";
                        description "Enable the evpn-tunnel context";

                        leaf ipv6-gateway-address {
                            type enumeration {
                                enum ip                             { value 0; }
                                enum mac                            { value 1; }
                            }
                            default "ip";
                            description "Type of IPv6 gateway address";
                        }

                        leaf supplementary-broadcast-domain {
                            type boolean;
                            default "false";
                            description "Use the EVPN tunnel as a Supplementary Broadcast Domain";
                        }

                        leaf allow-bfd {
                            type boolean;
                            default "false";
                            description "Allow BFD on the EVPN tunnel";
                        }

                    } // container evpn-tunnel

                    container egress {
                        description "Enter the egress context";

                        leaf reclassify-using-qos {
                            type leafref {
                                path "../../../../../../qos/sap-egress/sap-egress-policy-name";
                            }
                            description "Egress QoS policy";
                        }

                        container routed-override-filter {
                            description "Enter the routed-override-filter context";

                            leaf ip {
                                type leafref {
                                    path "../../../../../../../filter/ip-filter/filter-name";
                                }
                                description "IPv4 filter policy name";
                            }

                            leaf ipv6 {
                                type leafref {
                                    path "../../../../../../../filter/ipv6-filter/filter-name";
                                }
                                description "IPv6 filter policy name";
                            }

                        } // container routed-override-filter

                    } // container egress

                    container ingress {
                        description "Enter the ingress context";

                        container routed-override-filter {
                            description "Enter the routed-override-filter context";

                            leaf ip {
                                type leafref {
                                    path "../../../../../../../filter/ip-filter/filter-name";
                                }
                                description "IPv4 filter policy name";
                            }

                            leaf ipv6 {
                                type leafref {
                                    path "../../../../../../../filter/ipv6-filter/filter-name";
                                }
                                description "IPv6 filter policy name";
                            }

                        } // container routed-override-filter

                    } // container ingress

                } // list vpls

                container ipv6 {
                    presence "Enable the ipv6 context";
                    description "Enable the ipv6 context";

                    leaf qos-route-lookup {
                        type types-router:qos-route-lookup;
                        description "IP address for QoS route lookup for ingress IP packets";
                    }

                    leaf forward-ipv4-packets {
                        type boolean;
                        default "false";
                        description "Forward unencapsulated IPv4 packets";
                    }

                    leaf tcp-mss {
                        type types-router:ipv6-tcp-mss-ext;
                        description "TCP maximum segment size for the interface";
                    }

                    leaf duplicate-address-detection {
                        type boolean;
                        default "true";
                        description "Enable Duplicate Address Detection per interface";
                    }

                    leaf local-dhcp-server {
                        when "../../tunnel = 'false'" {
                            description "not allowed in a tunnel interface";
                        }
                        type leafref {
                            path "../../../dhcp-server/dhcpv6/name";
                        }
                        description "DHCP server for the interface";
                    }

                    container urpf-check {
                        presence "Enable the urpf-check context";
                        description "Enable the urpf-check context";

                        leaf ignore-default {
                            type boolean;
                            default "false";
                            description "Ignore default route when performing a uRPF check";
                        }

                        leaf mode {
                            type types-router:urpf-check-mode;
                            default "strict";
                            description "Unicast RPF check mode";
                        }

                    } // container urpf-check

                    container icmp6 {
                        description "Enter the icmp6 context";

                        container packet-too-big {
                            description "Enter the packet-too-big context";

                            leaf admin-state {
                                type types-sros:admin-state;
                                default "enable";
                                description "Administrative state of Packet Too Big message sends";
                            }

                            leaf number {
                                type uint16 {
                                    range "10..1000";
                                }
                                default "100";
                                description "Number of Packet Too big Messages issued per time frame";
                            }

                            leaf seconds {
                                type uint16 {
                                    range "1..60";
                                }
                                default "10";
                                description "Time used to limit Packet Too Big messages";
                            }

                        } // container packet-too-big

                        container param-problem {
                            description "Enter the param-problem context";

                            leaf admin-state {
                                type types-sros:admin-state;
                                default "enable";
                                description "Administrative state of Parameter Problem message sends";
                            }

                            leaf number {
                                type uint16 {
                                    range "10..1000";
                                }
                                default "100";
                                description "Number used to limit ICMPv6 Parameter Problem messages";
                            }

                            leaf seconds {
                                type uint16 {
                                    range "1..60";
                                }
                                default "10";
                                description "Time used to limit ICMPv6 Parameter Problem messages";
                            }

                        } // container param-problem

                        container redirects {
                            description "Enter the redirects context";

                            leaf admin-state {
                                type types-sros:admin-state;
                                default "enable";
                                description "Administrative state of Redirect message sends";
                            }

                            leaf number {
                                type uint16 {
                                    range "10..1000";
                                }
                                default "100";
                                description "Number to limit ICMPv6 Redirect messages per time frame";
                            }

                            leaf seconds {
                                type uint16 {
                                    range "1..60";
                                }
                                default "10";
                                description "Time used to limit ICMPv6 Redirect messages";
                            }

                        } // container redirects

                        container time-exceeded {
                            description "Enter the time-exceeded context";

                            leaf admin-state {
                                type types-sros:admin-state;
                                default "enable";
                                description "Administrative state of Time Exceeded message sends";
                            }

                            leaf number {
                                type uint16 {
                                    range "10..2000";
                                }
                                default "100";
                                description "Number to limit Time Exceeded messages per time frame";
                            }

                            leaf seconds {
                                type uint16 {
                                    range "1..60";
                                }
                                default "10";
                                description "Time used to limit ICMPv6 Time Exceeded messages";
                            }

                        } // container time-exceeded

                        container unreachables {
                            description "Enter the unreachables context";

                            leaf admin-state {
                                type types-sros:admin-state;
                                default "enable";
                                description "Administrative state of Unreachable message sends";
                            }

                            leaf number {
                                type uint16 {
                                    range "10..2000";
                                }
                                default "100";
                                description "Number to limit Unreachable messages per time frame";
                            }

                            leaf seconds {
                                type uint16 {
                                    range "1..60";
                                }
                                default "10";
                                description "Time used to limit ICMPv6 Unreachable messages";
                            }

                        } // container unreachables

                    } // container icmp6

                    container bfd {
                        description "Enter the bfd context";

                        leaf admin-state {
                            type types-sros:admin-state;
                            default "disable";
                            description "Administrative state of BFD sessions";
                        }

                        leaf transmit-interval {
                            type uint32 {
                                range "10..100000";
                            }
                            units "milliseconds";
                            default "100";
                            description "BFD transmit interval over this interface";
                        }

                        leaf receive {
                            type uint32 {
                                range "10..100000";
                            }
                            units "milliseconds";
                            default "100";
                            description "BFD receive interval over this interface";
                        }

                        leaf multiplier {
                            type uint32 {
                                range "1..20";
                            }
                            default "3";
                            description "Number of consecutive BFD messages missed from the peer";
                        }

                        leaf echo-receive {
                            type uint32 {
                                range "100..100000";
                            }
                            units "milliseconds";
                            description "Minimum echo interval over this interface";
                        }

                        leaf type {
                            type enumeration {
                                enum cpm-np                         { value 1; }
                                enum auto                           { value 2; }
                                enum fp                             { value 3; }
                            }
                            default "auto";
                            description "Local termination point for the BFD session";
                        }

                    } // container bfd

                    container link-local-address {
                        description "Enter the link-local-address context";

                        leaf address {
                            type types-sros:ipv6-address;
                            description "IPv6 link-local address";
                        }

                        leaf duplicate-address-detection {
                            type boolean;
                            default "true";
                            description "Enable Duplicate Address Detection";
                        }

                    } // container link-local-address

                    list address {
                        key "ipv6-address";
                        description "Enter the address list instance";

                        leaf ipv6-address {
                            type types-sros:ipv6-address;
                            description "IPv6 address assigned to the interface";
                        }

                        leaf prefix-length {
                            type uint32 {
                                range "4..128";
                            }
                            mandatory true;
                            description "IPv6 address prefix length";
                        }

                        leaf eui-64 {
                            type boolean;
                            sros-ext:immutable;
                            default "false";
                            description "Form IPv6 address from prefix and 64-bit interface ID";
                        }

                        leaf duplicate-address-detection {
                            type boolean;
                            sros-ext:immutable;
                            default "true";
                            description "Enable Duplicate Address Detection";
                        }

                        leaf primary-preference {
                            type uint32 {
                                range "1..4294967295";
                            }
                            description "Index assigned to the IPv6 address of the interface";
                        }

                        leaf track-srrp {
                            type uint32 {
                                range "1..4294967295";
                            }
                            description "SRRP ID whose state is tracked on this IP address";
                        }

                        leaf-list apply-groups {
                            type leafref {
                                path "../../../../../../groups/group/name";
                            }
                            max-elements 8;
                            ordered-by user;
                            description "Apply a configuration group at this level";
                        }

                        leaf-list apply-groups-exclude {
                            type leafref {
                                path "../../../../../../groups/group/name";
                            }
                            max-elements 8;
                            ordered-by user;
                            description "Exclude a configuration group at this level";
                        }

                    } // list address

                    container dhcp6 {
                        when "../../tunnel = 'false'" {
                            description "not allowed in a tunnel interface";
                        }
                        description "Enter the dhcp6 context";

                        leaf-list apply-groups {
                            type leafref {
                                path "../../../../../../groups/group/name";
                            }
                            max-elements 8;
                            ordered-by user;
                            description "Apply a configuration group at this level";
                        }

                        leaf-list apply-groups-exclude {
                            type leafref {
                                path "../../../../../../groups/group/name";
                            }
                            max-elements 8;
                            ordered-by user;
                            description "Exclude a configuration group at this level";
                        }

                        container relay {
                            description "Enter the relay context";

                            leaf description {
                                type types-sros:description;
                                description "Text description";
                            }

                            leaf admin-state {
                                type types-sros:admin-state;
                                default "disable";
                                description "Administrative state of DHCPv6 Relay";
                            }

                            leaf link-address {
                                type types-sros:ipv6-address;
                                description "Link address of the DHCPv6 relay messages";
                            }

                            leaf neighbor-resolution {
                                type boolean;
                                default "false";
                                description "Enable neighbor resolution via DHCPv6 relay";
                            }

                            leaf python-policy {
                                type leafref {
                                    path "../../../../../../../python/python-policy/name";
                                }
                                description "Python policy name";
                            }

                            leaf source-address {
                                type types-sros:ipv6-unicast-or-linklocal-address;
                                description "Source IPv6 address of the DHCPv6 relay messages";
                            }

                            leaf user-db {
                                type leafref {
                                    path "../../../../../../../subscriber-mgmt/local-user-db/name";
                                }
                                description "Local user database for authentication";
                            }

                            leaf-list server {
                                type types-sros:ipv6-address-with-zone;
                                max-elements 8;
                                ordered-by user;
                                description "DHCPv6 server to which the DHCPv6 requests are forwarded";
                            }

                            leaf-list apply-groups {
                                type leafref {
                                    path "../../../../../../../groups/group/name";
                                }
                                max-elements 8;
                                ordered-by user;
                                description "Apply a configuration group at this level";
                            }

                            leaf-list apply-groups-exclude {
                                type leafref {
                                    path "../../../../../../../groups/group/name";
                                }
                                max-elements 8;
                                ordered-by user;
                                description "Exclude a configuration group at this level";
                            }

                            container lease-populate {
                                description "Enter the lease-populate context";

                                leaf max-nbr-of-leases {
                                    type int32 {
                                        range "0..32767";
                                    }
                                    default "0";
                                    description "Maximum lease state entries allowed for the interface";
                                }

                                container route-populate {
                                    description "Enter the route-populate context";

                                    leaf na {
                                        type boolean;
                                        default "false";
                                        description "Create route based on IA_NA prefix option in relay-reply message";
                                    }

                                    leaf ta {
                                        type boolean;
                                        default "false";
                                        description "Create route based on IA_TA prefix option in relay-reply message";
                                    }

                                    container pd {
                                        presence "Enable the pd context";
                                        description "Enable the pd context";

                                        leaf exclude {
                                            type boolean;
                                            default "false";
                                            description "Create back hole route based on prefix exclude option in relay-reply message";
                                        }

                                    } // container pd

                                } // container route-populate

                            } // container lease-populate

                            container option {
                                description "Enter the option context";

                                leaf remote-id {
                                    type boolean;
                                    default "false";
                                    description "Send remote ID option in the DHCPv6 relay packet";
                                }

                                leaf-list apply-groups {
                                    type leafref {
                                        path "../../../../../../../../groups/group/name";
                                    }
                                    max-elements 8;
                                    ordered-by user;
                                    description "Apply a configuration group at this level";
                                }

                                leaf-list apply-groups-exclude {
                                    type leafref {
                                        path "../../../../../../../../groups/group/name";
                                    }
                                    max-elements 8;
                                    ordered-by user;
                                    description "Exclude a configuration group at this level";
                                }

                                container interface-id {
                                    description "Enter the interface-id context";

                                    choice interface-id {
                                        case ascii-tuple {

                                            leaf ascii-tuple {
                                                type empty;
                                                description "Use ASCII-encoded concatenated tuple";
                                            }

                                        }
                                        case sap-id {

                                            leaf sap-id {
                                                type empty;
                                                description "Use SAP ID in interface ID option in relay packet";
                                            }

                                        }
                                        case if-index {

                                            leaf if-index {
                                                type empty;
                                                description "Use interface index in the DHCPv6 relay packet";
                                            }

                                        }
                                        case string {

                                            leaf string {
                                                type types-sros:string-not-all-spaces {
                                                    length "1..80";
                                                }
                                                description "String for interface ID option in DHCPv6 relay packet";
                                            }

                                        }
                                    }
                                } // container interface-id

                            } // container option

                        } // container relay

                        container server {
                            description "Enter the server context";

                            leaf max-nbr-of-leases {
                                type int32 {
                                    range "0..8000";
                                }
                                default "8000";
                                description "DHCPv6 leases allowed";
                            }

                            leaf-list apply-groups {
                                type leafref {
                                    path "../../../../../../../groups/group/name";
                                }
                                max-elements 8;
                                ordered-by user;
                                description "Apply a configuration group at this level";
                            }

                            leaf-list apply-groups-exclude {
                                type leafref {
                                    path "../../../../../../../groups/group/name";
                                }
                                max-elements 8;
                                ordered-by user;
                                description "Exclude a configuration group at this level";
                            }

                            container prefix-delegation {
                                description "Enter the prefix-delegation context";

                                leaf admin-state {
                                    type types-sros:admin-state;
                                    default "disable";
                                    description "Administrative state of the prefix delegation";
                                }

                                list prefix {
                                    key "ipv6-prefix";
                                    description "Enter the prefix list instance";

                                    leaf ipv6-prefix {
                                        type types-sros:ipv6-prefix;
                                        description "IPv6 address and prefix";
                                    }

                                    leaf preferred-lifetime {
                                        type types-services:ipv6-prefix-lifetime;
                                        units "seconds";
                                        default "604800";
                                        description "Preferred lifetime of the prefix";
                                    }

                                    leaf valid-lifetime {
                                        type types-services:ipv6-prefix-lifetime;
                                        units "seconds";
                                        default "2592000";
                                        description "Valid lifetime of the prefix";
                                    }

                                    leaf-list apply-groups {
                                        type leafref {
                                            path "../../../../../../../../../groups/group/name";
                                        }
                                        max-elements 8;
                                        ordered-by user;
                                        description "Apply a configuration group at this level";
                                    }

                                    leaf-list apply-groups-exclude {
                                        type leafref {
                                            path "../../../../../../../../../groups/group/name";
                                        }
                                        max-elements 8;
                                        ordered-by user;
                                        description "Exclude a configuration group at this level";
                                    }

                                    container client-id {
                                        description "Enter the client-id context";

                                        leaf duid {
                                            type string {
                                                length "1..130";
                                            }
                                            description "Requesting router ID";
                                        }

                                        leaf iaid {
                                            type uint32 {
                                                range "1..4294967295";
                                            }
                                            description "IAID from the requesting router to match";
                                        }

                                    } // container client-id

                                } // list prefix

                            } // container prefix-delegation

                        } // container server

                    } // container dhcp6

                    container neighbor-discovery {
                        when "../../tunnel = 'false'" {
                            description "not allowed in a tunnel interface";
                        }
                        description "Enter the neighbor-discovery context";

                        leaf reachable-time {
                            type types-router:neighbor-discovery-reachable-time;
                            description "Neighbor reachability detection timer";
                        }

                        leaf stale-time {
                            type types-router:neighbor-discovery-stale-time;
                            description "Time a Neighbor Discovery cache entry remains stale";
                        }

                        leaf learn-unsolicited {
                            type types-router:ipv6-address-type-selection;
                            description "Type of entries learned from unsolicited NA messages";
                        }

                        leaf proactive-refresh {
                            type types-router:ipv6-address-type-selection;
                            description "Proactive refresh of neighbor entries";
                        }

                        leaf populate-host {
                            status obsolete;
                            type boolean;
                            default "false";
                            description "Allow addition or deletion of host routes in route table derived from ARP entries in ARP cache";
                        }

                        leaf route-tag {
                            status obsolete;
                            type types-router:route-tag;
                            description "ARP route tag";
                        }

                        leaf local-proxy-nd {
                            type boolean;
                            default "false";
                            description "Enable local proxy neighbor discovery on the interface";
                        }

                        leaf-list proxy-nd-policy {
                            type leafref {
                                path "../../../../../../policy-options/policy-statement/name";
                            }
                            max-elements 5;
                            ordered-by user;
                            description "Proxy Neighbor Discovery policy name for the interface";
                        }

                        container host-route {
                            description "Enter the host-route context";

                            list populate {
                                key "route-type";
                                description "Enter the populate list instance";

                                leaf route-type {
                                    type enumeration {
                                        enum static                         { value 1; }
                                        enum dynamic                        { value 2; }
                                        enum evpn                           { value 3; }
                                    }
                                    description "Type of ARP or ND entries that generate host routes";
                                }

                                leaf route-tag {
                                    type uint32 {
                                        range "1..255";
                                    }
                                    sros-ext:immutable;
                                    description "Tag value used with the host route from an ARP/ND entry";
                                }

                                leaf-list apply-groups {
                                    type leafref {
                                        path "../../../../../../../../groups/group/name";
                                    }
                                    max-elements 8;
                                    ordered-by user;
                                    description "Apply a configuration group at this level";
                                }

                                leaf-list apply-groups-exclude {
                                    type leafref {
                                        path "../../../../../../../../groups/group/name";
                                    }
                                    max-elements 8;
                                    ordered-by user;
                                    description "Exclude a configuration group at this level";
                                }

                            } // list populate

                        } // container host-route

                        container secure-nd {
                            description "Enter the secure-nd context";

                            leaf allow-unsecured-msgs {
                                type boolean;
                                default "true";
                                description "Accept unsecured messages";
                            }

                            leaf public-key-min-bits {
                                type uint32 {
                                    range "512..1024";
                                }
                                default "1024";
                                description "Minimum acceptable key length for public keys in CGA";
                            }

                            leaf security-parameter {
                                type uint32 {
                                    range "0..1";
                                }
                                default "1";
                                description "Security parameter used in the generation of a CGA";
                            }

                            leaf admin-state {
                                type types-sros:admin-state;
                                default "disable";
                                description "Administrative state of Secure Neighbor Discovery";
                            }

                        } // container secure-nd

                        container limit {
                            description "Enter the limit context";

                            leaf max-entries {
                                type types-router:ipv6-neighbor-limit;
                                description "Maximum number of entries learned on an IP interface";
                            }

                            leaf log-only {
                                type boolean;
                                default "false";
                                description "Generate log entries when limit is reached";
                            }

                            leaf threshold {
                                type uint32 {
                                    range "1..100";
                                }
                                units "percent";
                                default "90";
                                description "Threshold percentage that triggers a warning message";
                            }

                        } // container limit

                        list static-neighbor {
                            key "ipv6-address";
                            description "Enter the static-neighbor list instance";

                            leaf ipv6-address {
                                type types-sros:ipv6-address;
                                description "IPv6 address corresponding to the physical address";
                            }

                            leaf mac-address {
                                type yang:mac-address;
                                mandatory true;
                                description "MAC address for the static neighbor";
                            }

                            leaf-list apply-groups {
                                type leafref {
                                    path "../../../../../../../groups/group/name";
                                }
                                max-elements 8;
                                ordered-by user;
                                description "Apply a configuration group at this level";
                            }

                            leaf-list apply-groups-exclude {
                                type leafref {
                                    path "../../../../../../../groups/group/name";
                                }
                                max-elements 8;
                                ordered-by user;
                                description "Exclude a configuration group at this level";
                            }

                        } // list static-neighbor

                    } // container neighbor-discovery

                    list vrrp {
                        key "virtual-router-id";
                        max-elements 4;
                        description "Enter the vrrp list instance";

                        leaf virtual-router-id {
                            type int32 {
                                range "1..255";
                            }
                            description "Virtual Router Identifier (VRID) for the IP interface";
                        }

                        leaf-list backup {
                            type types-sros:ipv6-address;
                            description "Virtual router IP addresses for the interface";
                        }

                        leaf message-interval {
                            type uint32 {
                                range "10..4095";
                            }
                            units "centiseconds";
                            default "100";
                            description "Interval for sending VRRP advertisement messages";
                        }

                        leaf owner {
                            type boolean;
                            sros-ext:immutable;
                            default "false";
                            description "Designate the virtual router instance as owner";
                        }

                        leaf passive {
                            type boolean;
                            sros-ext:immutable;
                            default "false";
                            description "Suppress the processing of VRRP advertisement messages";
                        }

                        leaf init-delay {
                            type uint32 {
                                range "1..65535";
                            }
                            units "seconds";
                            description "VRRP initialization delay timer";
                        }

                        leaf mac {
                            type types-sros:mac-unicast-address;
                            description "Virtual MAC address to use in ARP responses";
                        }

                        leaf priority {
                            type uint32 {
                                range "1..255";
                            }
                            description "Base priority for the VRRP";
                        }

                        leaf admin-state {
                            type types-sros:admin-state;
                            default "enable";
                            description "Administrative state of VRRP";
                        }

                        leaf master-int-inherit {
                            type boolean;
                            description "Allow master instance to dictate the master down timer";
                        }

                        leaf ping-reply {
                            type boolean;
                            default "false";
                            description "Allow non-owner master to reply to ICMP echo requests";
                        }

                        leaf policy {
                            type leafref {
                                path "../../../../../../vrrp/policy/policy-id";
                            }
                            description "VRRP priority control policy";
                        }

                        leaf preempt {
                            type boolean;
                            default "true";
                            description "Allow the VRRP to override an existing non-owner master";
                        }

                        leaf telnet-reply {
                            type boolean;
                            default "false";
                            description "Allow non-owner master to reply to Telnet requests";
                        }

                        leaf traceroute-reply {
                            type boolean;
                            default "false";
                            description "Allow non-owner master to reply to traceroute requests";
                        }

                        leaf standby-forwarding {
                            type boolean;
                            default "false";
                            description "Allow standby router to forward traffic";
                        }

                        leaf ntp-reply {
                            type boolean;
                            default "false";
                            description "Allow processing of NTP requests";
                        }

                        leaf oper-group {
                            type leafref {
                                path "../../../../../oper-group/name";
                            }
                            description "Operational group name associated with the VRRP";
                        }

                        leaf monitor-oper-group {
                            type leafref {
                                path "../../../../../oper-group/name";
                            }
                            sros-ext:immutable;
                            description "VRRP instance to follow a specified operational group";
                        }

                        leaf-list apply-groups {
                            type leafref {
                                path "../../../../../../groups/group/name";
                            }
                            max-elements 8;
                            ordered-by user;
                            description "Apply a configuration group at this level";
                        }

                        leaf-list apply-groups-exclude {
                            type leafref {
                                path "../../../../../../groups/group/name";
                            }
                            max-elements 8;
                            ordered-by user;
                            description "Exclude a configuration group at this level";
                        }

                        container bfd-liveness {
                            presence "Enable the bfd-liveness context";
                            description "Enable the bfd-liveness context";

                            leaf dest-ip {
                                type types-sros:ip-address;
                                sros-ext:immutable;
                                mandatory true;
                                description "Destination address for the BFD session";
                            }

                            leaf service-name {
                                type types-services:service-name;
                                sros-ext:immutable;
                                description "Administrative service name";
                            }

                            leaf interface-name {
                                type types-sros:interface-name;
                                sros-ext:immutable;
                                mandatory true;
                                description "Name of the interface running BFD";
                            }

                            leaf-list apply-groups {
                                type leafref {
                                    path "../../../../../../../groups/group/name";
                                }
                                max-elements 8;
                                ordered-by user;
                                description "Apply a configuration group at this level";
                            }

                            leaf-list apply-groups-exclude {
                                type leafref {
                                    path "../../../../../../../groups/group/name";
                                }
                                max-elements 8;
                                ordered-by user;
                                description "Exclude a configuration group at this level";
                            }

                        } // container bfd-liveness

                    } // list vrrp

                } // container ipv6

                container if-attribute {
                    description "Enter the if-attribute context";

                    leaf-list admin-group {
                        type leafref {
                            path "../../../../../routing-options/if-attribute/admin-group/group-name";
                        }
                        max-elements 32;
                        description "Administrative group name for the interface";
                    }

                    list srlg-group {
                        key "name";
                        description "Add a list entry for srlg-group";

                        leaf name {
                            type leafref {
                                path "../../../../../../routing-options/if-attribute/srlg-group/name";
                            }
                            description "SRLG name";
                        }

                    } // list srlg-group

                } // container if-attribute

                container external-reference {
                    description "Enter the external-reference context";

                    container openconfig {
                        description "Enter the openconfig context";

                        leaf subinterface {
                            type int64 {
                                range "0..4294967295";
                            }
                            description "Reference to the subinterface";
                        }

                    } // container openconfig

                } // container external-reference


            } // list interface

            list network-interface {
                key "interface-name";
                description "Enter the network-interface list instance";

                leaf interface-name {
                    type types-sros:interface-name;
                    description "Network interface name";
                }

                leaf description {
                    type types-sros:very-long-description;
                    description "Text description";
                }

                leaf admin-state {
                    type types-sros:admin-state;
                    default "enable";
                    description "Administrative state of the interface";
                }

                leaf cpu-protection {
                    type leafref {
                        path "../../../../system/security/cpu-protection/policy/policy-id";
                    }
                    description "CPM Protection policy associated with an interface";
                }

                leaf ip-mtu {
                    type types-router:ip-mtu-ext;
                    units "bytes";
                    description "IP MTU applied to outgoing packets";
                }

                leaf mac {
                    type types-sros:mac-unicast-address;
                    description "MAC address for the interface";
                }

                leaf tos-marking-state {
                    type types-router:tos-marking-state;
                    default "trusted";
                    description "TOS marking state";
                }

                leaf dist-cpu-protection {
                    type leafref {
                        path "../../../../system/security/dist-cpu-protection/policy/policy-name";
                    }
                    description "Distributed CPU protection policy";
                }

                leaf ingress-stats {
                    type boolean;
                    default "false";
                    description "Collect ingress statistics";
                }

                leaf-list apply-groups {
                    type leafref {
                        path "../../../../groups/group/name";
                    }
                    max-elements 8;
                    ordered-by user;
                    description "Apply a configuration group at this level";
                }

                leaf-list apply-groups-exclude {
                    type leafref {
                        path "../../../../groups/group/name";
                    }
                    max-elements 8;
                    ordered-by user;
                    description "Exclude a configuration group at this level";
                }

                choice port-binding {
                    case port-encap {

                        leaf port {
                            type types-sros:port-and-encap;
                            description "Port to bind the interface";
                        }

                    }
                    case loopback {

                        leaf loopback {
                            type empty;
                            description "Use interface as a loopback interface";
                        }

                    }
                }
                container egress {
                    description "Enter the egress context";

                    container filter {
                        description "Enter the filter context";

                        leaf ip {
                            type leafref {
                                path "../../../../../../filter/ip-filter/filter-name";
                            }
                            description "IPv4 filter policy name";
                        }

                    } // container filter

                } // container egress

                container ingress {
                    description "Enter the ingress context";

                    container filter {
                        description "Enter the filter context";

                        leaf ip {
                            type leafref {
                                path "../../../../../../filter/ip-filter/filter-name";
                            }
                            description "IPv4 filter policy name";
                        }

                    } // container filter

                } // container ingress

                container load-balancing {
                    description "Enter the load-balancing context";

                    leaf lsr-load-balancing {
                        type types-router:lsr-load-balancing;
                        description "LSR load-balancing algorithm";
                    }

                    leaf ip-load-balancing {
                        type types-router:ip-load-balancing;
                        default "both";
                        description "IP load-balancing algorithm";
                    }

                    leaf spi-load-balancing {
                        type boolean;
                        default "false";
                        description "Enable SPI use in hashing";
                    }

                    leaf teid-load-balancing {
                        type boolean;
                        default "false";
                        description "Enable use of TEID in hashing";
                    }

                    leaf flow-label-load-balancing {
                        type boolean;
                        default "false";
                        description "Enable flow label load balancing";
                    }

                } // container load-balancing

                container lag {
                    description "Enter the lag context";

                    leaf link-map-profile {
                        type types-services:link-map-profile-id;
                        description "LAG link map profile for a SAP or network interface";
                    }

                    container per-link-hash {
                        description "Enter the per-link-hash context";

                        leaf class {
                            type types-services:sap-lag-per-link-hash-class;
                            default "1";
                            description "Class used on LAG egress using weighted per-link-hash";
                        }

                        leaf weight {
                            type types-services:sap-lag-per-link-hash-weight;
                            default "1";
                            description "Weight used on LAG egress using weighted per-link-hash";
                        }

                    } // container per-link-hash

                } // container lag

                container hold-time {
                    description "Enter the hold-time context";

                    container ipv4 {
                        description "Enter the ipv4 context";

                        container up {
                            description "Enter the up context";

                            leaf seconds {
                                type types-router:hold-time-seconds;
                                units "seconds";
                                description "Up hold time for the IP interface";
                            }

                        } // container up

                        container down {
                            description "Enter the down context";

                            leaf seconds {
                                type types-router:hold-time-seconds;
                                units "seconds";
                                description "Down hold time for the IP interface";
                            }

                            leaf init-only {
                                type boolean;
                                default "false";
                                description "Apply delay only at interface configuration or reboot";
                            }

                        } // container down

                    } // container ipv4

                } // container hold-time

                container cflowd-parameters {
                    description "Enter the cflowd-parameters context";

                    list sampling {
                        key "sampling-type";
                        description "Enter the sampling list instance";

                        leaf sampling-type {
                            type types-router:cflowd-sampling;
                            description "Traffic sampling type";
                        }

                        leaf type {
                            when "not(../sampling-type = 'both')";
                            type enumeration {
                                enum acl                            { value 1; }
                                enum interface                      { value 2; }
                            }
                            mandatory true;
                            description "Type of cflowd analysis";
                        }

                        leaf direction {
                            type enumeration {
                                enum ingress-only                   { value 1; }
                                enum egress-only                    { value 2; }
                                enum both                           { value 3; }
                            }
                            default "ingress-only";
                            description "Direction of traffic for cflowd sampling";
                        }

                        leaf sample-profile {
                            type union {
                                type enumeration {
                                    enum 1                              { value 1; }
                                }
                                type uint32;
                            }
                            description "Sample profile ID";
                        }

                        leaf-list apply-groups {
                            type leafref {
                                path "../../../../../../groups/group/name";
                            }
                            max-elements 8;
                            ordered-by user;
                            description "Apply a configuration group at this level";
                        }

                        leaf-list apply-groups-exclude {
                            type leafref {
                                path "../../../../../../groups/group/name";
                            }
                            max-elements 8;
                            ordered-by user;
                            description "Exclude a configuration group at this level";
                        }

                    } // list sampling

                } // container cflowd-parameters

                container qos {
                    description "Enter the qos context";

                    leaf network-policy {
                        type leafref {
                            path "../../../../../qos/network/network-policy-name";
                        }
                        description "Network policy name associated with a network interface";
                    }

                    leaf egress-port-redirect-group {
                        type leafref {
                            path "../../../../../qos/queue-group-templates/egress/queue-group/egress-queue-group-name";
                        }
                        description "QoS queue group name";
                    }

                    leaf egress-instance {
                        type types-services:qos-qgrp-instance-id;
                        description "Port egress queue group instance for this interface";
                    }

                    leaf ingress-fp-redirect-group {
                        type leafref {
                            path "../../../../../qos/queue-group-templates/ingress/queue-group/ingress-queue-group-name";
                        }
                        description "Forwarding plane queue group policy for the interface";
                    }

                    leaf ingress-instance {
                        type types-services:qos-qgrp-instance-id;
                        description "Forwarding plane ingress queue group for this interface";
                    }

                    leaf-list apply-groups {
                        type leafref {
                            path "../../../../../groups/group/name";
                        }
                        max-elements 8;
                        ordered-by user;
                        description "Apply a configuration group at this level";
                    }

                    leaf-list apply-groups-exclude {
                        type leafref {
                            path "../../../../../groups/group/name";
                        }
                        max-elements 8;
                        ordered-by user;
                        description "Exclude a configuration group at this level";
                    }

                } // container qos

                container ipv4 {
                    description "Enter the ipv4 context";

                    leaf tcp-mss {
                        type types-router:ipv4-tcp-mss-ext;
                        description "TCP maximum segment size for the interface";
                    }

                    leaf allow-directed-broadcasts {
                        type boolean;
                        default "false";
                        description "Accept broadcasts that are directed to this interface";
                    }

                    container icmp {
                        description "Enter the icmp context";

                        leaf mask-reply {
                            type boolean;
                            default "true";
                            description "Allow responses to ICMP mask requests on the interface";
                        }

                        container redirects {
                            description "Enter the redirects context";

                            leaf admin-state {
                                type types-sros:admin-state;
                                default "enable";
                                description "Administrative state of sending ICMP redirect messages";
                            }

                            leaf number {
                                type uint16 {
                                    range "10..1000";
                                }
                                default "100";
                                description "Maximum number of ICMP redirect messages to send";
                            }

                            leaf seconds {
                                type uint16 {
                                    range "1..60";
                                }
                                units "seconds";
                                default "10";
                                description "Time used to limit the number of ICMP redirect messages";
                            }

                        } // container redirects

                        container ttl-expired {
                            description "Enter the ttl-expired context";

                            leaf admin-state {
                                type types-sros:admin-state;
                                default "enable";
                                description "Administrative state of sending TTL expired messages";
                            }

                            leaf number {
                                type uint16 {
                                    range "10..2000";
                                }
                                default "100";
                                description "Maximum number of TTL expired messages to send";
                            }

                            leaf seconds {
                                type uint16 {
                                    range "1..60";
                                }
                                units "seconds";
                                default "10";
                                description "Time used to limit the number of TTL expired messages";
                            }

                        } // container ttl-expired

                        container unreachables {
                            description "Enter the unreachables context";

                            leaf admin-state {
                                type types-sros:admin-state;
                                default "enable";
                                description "Administrative state of sending unreachable messages";
                            }

                            leaf number {
                                type uint16 {
                                    range "10..2000";
                                }
                                default "100";
                                description "Maximum number of unreachable messages to send";
                            }

                            leaf seconds {
                                type uint16 {
                                    range "1..60";
                                }
                                units "seconds";
                                default "10";
                                description "Time to limit the number of ICMP unreachable messages";
                            }

                        } // container unreachables

                        container param-problem {
                            description "Enter the param-problem context";

                            leaf admin-state {
                                type types-sros:admin-state;
                                default "enable";
                                description "Administrative state of sent Parameter Problem messages";
                            }

                            leaf number {
                                type uint32 {
                                    range "10..1000";
                                }
                                default "100";
                                description "Maximum number of Parameter Problem messages to send";
                            }

                            leaf seconds {
                                type uint32 {
                                    range "1..60";
                                }
                                units "seconds";
                                default "10";
                                description "Time used to limit number of Parameter Problem messages";
                            }

                        } // container param-problem

                    } // container icmp

                    container urpf-check {
                        presence "Enable the urpf-check context";
                        description "Enable the urpf-check context";

                        leaf ignore-default {
                            type boolean;
                            default "false";
                            description "Ignore default route when performing a uRPF check";
                        }

                        leaf mode {
                            type types-router:urpf-check-mode;
                            default "strict";
                            description "Unicast RPF check mode";
                        }

                    } // container urpf-check

                    container primary {
                        presence "Enable the primary context";
                        description "Enable the primary context";

                        leaf address {
                            type types-sros:ipv4-unicast-address;
                            mandatory true;
                            description "Primary IPv4 address assigned to the interface";
                        }

                        leaf prefix-length {
                            type uint32 {
                                range "0..32";
                            }
                            mandatory true;
                            description "IPv4 address prefix length";
                        }

                        leaf broadcast {
                            type types-services:broadcast-address-format;
                            default "host-ones";
                            description "Broadcast address format";
                        }

                        leaf-list apply-groups {
                            type leafref {
                                path "../../../../../../groups/group/name";
                            }
                            max-elements 8;
                            ordered-by user;
                            description "Apply a configuration group at this level";
                        }

                        leaf-list apply-groups-exclude {
                            type leafref {
                                path "../../../../../../groups/group/name";
                            }
                            max-elements 8;
                            ordered-by user;
                            description "Exclude a configuration group at this level";
                        }

                    } // container primary

                    list secondary {
                        key "address";
                        description "Enter the secondary list instance";

                        leaf address {
                            type types-sros:ipv4-unicast-address;
                            description "Secondary IPv4 address assigned to the interface";
                        }

                        leaf prefix-length {
                            type uint32 {
                                range "0..32";
                            }
                            mandatory true;
                            description "IPv4 address prefix length";
                        }

                        leaf igp-inhibit {
                            type boolean;
                            default "false";
                            description "Disable the running IGP from recognizing secondary IP";
                        }

                        leaf broadcast {
                            type types-services:broadcast-address-format;
                            default "host-ones";
                            description "Broadcast address format";
                        }

                        leaf-list apply-groups {
                            type leafref {
                                path "../../../../../../groups/group/name";
                            }
                            max-elements 8;
                            ordered-by user;
                            description "Apply a configuration group at this level";
                        }

                        leaf-list apply-groups-exclude {
                            type leafref {
                                path "../../../../../../groups/group/name";
                            }
                            max-elements 8;
                            ordered-by user;
                            description "Exclude a configuration group at this level";
                        }

                    } // list secondary

                    container bfd {
                        description "Enter the bfd context";

                        leaf admin-state {
                            type types-sros:admin-state;
                            default "disable";
                            description "Administrative state of BFD sessions";
                        }

                        leaf transmit-interval {
                            type uint32 {
                                range "10..100000";
                            }
                            units "milliseconds";
                            default "100";
                            description "BFD transmit interval over this interface";
                        }

                        leaf receive {
                            type uint32 {
                                range "10..100000";
                            }
                            units "milliseconds";
                            default "100";
                            description "BFD receive interval over this interface";
                        }

                        leaf multiplier {
                            type uint32 {
                                range "1..20";
                            }
                            default "3";
                            description "Number of consecutive BFD messages missed from the peer";
                        }

                        leaf echo-receive {
                            type uint32 {
                                range "100..100000";
                            }
                            units "milliseconds";
                            description "Minimum echo interval over this interface";
                        }

                        leaf type {
                            type enumeration {
                                enum cpm-np                         { value 1; }
                                enum auto                           { value 2; }
                                enum fp                             { value 3; }
                            }
                            default "auto";
                            description "Local termination point for the BFD session";
                        }

                    } // container bfd

                    container neighbor-discovery {
                        description "Enter the neighbor-discovery context";

                        leaf timeout {
                            type uint32 {
                                range "0..65535";
                            }
                            units "seconds";
                            default "14400";
                            description "Timeout for an ARP entry learned on the interface";
                        }

                        leaf retry-timer {
                            type uint32 {
                                range "1..300";
                            }
                            units "deciseconds";
                            default "50";
                            description "ARP retry interval";
                        }

                        list static-neighbor {
                            key "ipv4-address";
                            description "Enter the static-neighbor list instance";

                            leaf ipv4-address {
                                type types-sros:ipv4-address;
                                description "IPv4 address that corresponds to the physical address";
                            }

                            leaf mac-address {
                                type yang:mac-address;
                                mandatory true;
                                description "MAC address for the static neighbor";
                            }

                            leaf-list apply-groups {
                                type leafref {
                                    path "../../../../../../../groups/group/name";
                                }
                                max-elements 8;
                                ordered-by user;
                                description "Apply a configuration group at this level";
                            }

                            leaf-list apply-groups-exclude {
                                type leafref {
                                    path "../../../../../../../groups/group/name";
                                }
                                max-elements 8;
                                ordered-by user;
                                description "Exclude a configuration group at this level";
                            }

                        } // list static-neighbor

                    } // container neighbor-discovery

                } // container ipv4

            } // list network-interface

            list redundant-interface {
                key "interface-name";
                description "Enter the redundant-interface list instance";

                leaf interface-name {
                    type types-sros:interface-name;
                    description "Interface name";
                }

                leaf description {
                    type types-sros:very-long-description;
                    description "Text description";
                }

                leaf admin-state {
                    type types-sros:admin-state;
                    default "enable";
                    description "Administrative state of the interface";
                }

                leaf ip-mtu {
                    type types-router:ip-mtu-ext;
                    units "bytes";
                    description "IP MTU applied to outgoing packets";
                }

                leaf-list apply-groups {
                    type leafref {
                        path "../../../../groups/group/name";
                    }
                    max-elements 8;
                    ordered-by user;
                    description "Apply a configuration group at this level";
                }

                leaf-list apply-groups-exclude {
                    type leafref {
                        path "../../../../groups/group/name";
                    }
                    max-elements 8;
                    ordered-by user;
                    description "Exclude a configuration group at this level";
                }

                container hold-time {
                    description "Enter the hold-time context";

                    container ipv4 {
                        description "Enter the ipv4 context";

                        container up {
                            description "Enter the up context";

                            leaf seconds {
                                type types-router:hold-time-seconds;
                                units "seconds";
                                description "Up hold time for the IP interface";
                            }

                        } // container up

                        container down {
                            description "Enter the down context";

                            leaf seconds {
                                type types-router:hold-time-seconds;
                                units "seconds";
                                description "Down hold time for the IP interface";
                            }

                            leaf init-only {
                                type boolean;
                                default "false";
                                description "Apply delay only at interface configuration or reboot";
                            }

                        } // container down

                    } // container ipv4

                } // container hold-time

                list spoke-sdp {
                    key "sdp-bind-id";
                    max-elements 1;
                    description "Enter the spoke-sdp list instance";

                    leaf sdp-bind-id {
                        type types-services:sdp-bind-id;
                        description "SDP binding ID";
                    }

                    leaf description {
                        type types-sros:description;
                        description "Text description";
                    }

                    leaf admin-state {
                        type types-sros:admin-state;
                        default "enable";
                        description "Administrative state of the SDP binding to the service";
                    }

                    leaf control-word {
                        type boolean;
                        default "false";
                        description "Use the control word as preferred";
                    }

                    leaf-list apply-groups {
                        type leafref {
                            path "../../../../../groups/group/name";
                        }
                        max-elements 8;
                        ordered-by user;
                        description "Apply a configuration group at this level";
                    }

                    leaf-list apply-groups-exclude {
                        type leafref {
                            path "../../../../../groups/group/name";
                        }
                        max-elements 8;
                        ordered-by user;
                        description "Exclude a configuration group at this level";
                    }

                    container ingress {
                        description "Enter the ingress context";

                        leaf vc-label {
                            type types-services:ingress-vc-label;
                            sros-ext:auto-restart-to-modify;
                            description "Ingress MPLS VC label to send packets to the far end";
                        }

                        container filter {
                            description "Enter the filter context";

                            leaf ip {
                                type leafref {
                                    path "../../../../../../../filter/ip-filter/filter-name";
                                }
                                description "IPv4 filter policy name";
                            }

                        } // container filter

                    } // container ingress

                    container egress {
                        description "Enter the egress context";

                        leaf vc-label {
                            type types-services:egress-vc-label;
                            sros-ext:auto-restart-to-modify;
                            description "Egress MPLS VC label to send packets to the far end";
                        }

                        container filter {
                            description "Enter the filter context";

                            leaf ip {
                                type leafref {
                                    path "../../../../../../../filter/ip-filter/filter-name";
                                }
                                description "IPv4 filter policy name";
                            }

                        } // container filter

                    } // container egress

                } // list spoke-sdp

                container ipv4 {
                    description "Enter the ipv4 context";

                    container primary {
                        presence "Enable the primary context";
                        description "Enable the primary context";

                        leaf address {
                            type types-sros:ipv4-unicast-address;
                            mandatory true;
                            description "IPv4 address to be assigned to the interface";
                        }

                        leaf prefix-length {
                            type uint32 {
                                range "0..32";
                            }
                            mandatory true;
                            description "IPv4 address prefix length";
                        }

                        leaf remote-ip {
                            type types-sros:ipv4-unicast-address;
                            description "Remote IP address for the interface";
                        }

                        leaf-list apply-groups {
                            type leafref {
                                path "../../../../../../groups/group/name";
                            }
                            max-elements 8;
                            ordered-by user;
                            description "Apply a configuration group at this level";
                        }

                        leaf-list apply-groups-exclude {
                            type leafref {
                                path "../../../../../../groups/group/name";
                            }
                            max-elements 8;
                            ordered-by user;
                            description "Exclude a configuration group at this level";
                        }

                    } // container primary

                } // container ipv4

            } // list redundant-interface

            list aarp-interface {
                key "interface-name";
                description "Enter the aarp-interface list instance";

                leaf interface-name {
                    type types-sros:interface-name;
                    description "Interface name";
                }

                leaf description {
                    type types-sros:very-long-description;
                    description "Text description";
                }

                leaf admin-state {
                    type types-sros:admin-state;
                    default "enable";
                    description "Administrative state of the interface";
                }

                leaf ip-mtu {
                    type types-router:ip-mtu-ext;
                    units "bytes";
                    description "IP MTU applied to outgoing packets";
                }

                leaf-list apply-groups {
                    type leafref {
                        path "../../../../groups/group/name";
                    }
                    max-elements 8;
                    ordered-by user;
                    description "Apply a configuration group at this level";
                }

                leaf-list apply-groups-exclude {
                    type leafref {
                        path "../../../../groups/group/name";
                    }
                    max-elements 8;
                    ordered-by user;
                    description "Exclude a configuration group at this level";
                }

                list spoke-sdp {
                    key "sdp-bind-id";
                    max-elements 1;
                    description "Enter the spoke-sdp list instance";

                    leaf sdp-bind-id {
                        type types-services:sdp-bind-id;
                        description "SDP binding ID";
                    }

                    leaf description {
                        type types-sros:description;
                        description "Text description";
                    }

                    leaf admin-state {
                        type types-sros:admin-state;
                        default "enable";
                        description "Administrative state of this service SDP binding";
                    }

                    leaf-list apply-groups {
                        type leafref {
                            path "../../../../../groups/group/name";
                        }
                        max-elements 8;
                        ordered-by user;
                        description "Apply a configuration group at this level";
                    }

                    leaf-list apply-groups-exclude {
                        type leafref {
                            path "../../../../../groups/group/name";
                        }
                        max-elements 8;
                        ordered-by user;
                        description "Exclude a configuration group at this level";
                    }

                    container ingress {
                        description "Enter the ingress context";

                        leaf vc-label {
                            type types-services:ingress-vc-label;
                            sros-ext:auto-restart-to-modify;
                            description "VC ingress value that indicates a specific connection";
                        }

                        container filter {
                            description "Enter the filter context";

                            leaf ip {
                                type leafref {
                                    path "../../../../../../../filter/ip-filter/filter-name";
                                }
                                description "IP filter ID";
                            }

                        } // container filter

                    } // container ingress

                    container egress {
                        description "Enter the egress context";

                        leaf vc-label {
                            type types-services:egress-vc-label;
                            sros-ext:auto-restart-to-modify;
                            description "Static MPLS VC label to send packets to far-end device";
                        }

                        container filter {
                            description "Enter the filter context";

                            leaf ip {
                                type leafref {
                                    path "../../../../../../../filter/ip-filter/filter-name";
                                }
                                description "IP filter identifier";
                            }

                        } // container filter

                    } // container egress

                    container aarp {
                        presence "Enable the aarp context";
                        description "Enable the aarp context";

                        leaf id {
                            type leafref {
                                path "../../../../../../application-assurance/aarp/aarp-id";
                            }
                            sros-ext:immutable;
                            mandatory true;
                            description "AARP instance ID";
                        }

                        leaf type {
                            type types-services:l3-bsx-aarp-service-ref-type;
                            sros-ext:immutable;
                            mandatory true;
                            description "Role of the spoke SDP referenced by the AARP";
                        }

                    } // container aarp

                } // list spoke-sdp

            } // list aarp-interface

            list ip-mirror-interface {
                key "interface-name";
                description "Enter the ip-mirror-interface list instance";

                leaf interface-name {
                    type types-sros:interface-name;
                    description "Interface name";
                }

                leaf description {
                    type types-sros:very-long-description;
                    description "Text description";
                }

                leaf admin-state {
                    type types-sros:admin-state;
                    default "enable";
                    description "Administrative state of the interface";
                }

                leaf-list apply-groups {
                    type leafref {
                        path "../../../../groups/group/name";
                    }
                    max-elements 8;
                    ordered-by user;
                    description "Apply a configuration group at this level";
                }

                leaf-list apply-groups-exclude {
                    type leafref {
                        path "../../../../groups/group/name";
                    }
                    max-elements 8;
                    ordered-by user;
                    description "Exclude a configuration group at this level";
                }

                list spoke-sdp {
                    key "sdp-bind-id";
                    max-elements 1;
                    description "Enter the spoke-sdp list instance";

                    leaf sdp-bind-id {
                        type types-services:sdp-bind-id;
                        description "SDP binding ID";
                    }

                    leaf description {
                        type types-sros:description;
                        description "Text description";
                    }

                    leaf admin-state {
                        type types-sros:admin-state;
                        default "enable";
                        description "Administrative state of the SDP binding to the service";
                    }

                    leaf-list apply-groups {
                        type leafref {
                            path "../../../../../groups/group/name";
                        }
                        max-elements 8;
                        ordered-by user;
                        description "Apply a configuration group at this level";
                    }

                    leaf-list apply-groups-exclude {
                        type leafref {
                            path "../../../../../groups/group/name";
                        }
                        max-elements 8;
                        ordered-by user;
                        description "Exclude a configuration group at this level";
                    }

                    container ingress {
                        description "Enter the ingress context";

                        leaf vc-label {
                            type types-services:ingress-vc-label;
                            sros-ext:auto-restart-to-modify;
                            description "Spoke SDP ingress VC label";
                        }

                        container filter {
                            description "Enter the filter context";

                            leaf ip {
                                type leafref {
                                    path "../../../../../../../filter/ip-filter/filter-name";
                                }
                                description "IPv4 filter policy name";
                            }

                        } // container filter

                    } // container ingress

                } // list spoke-sdp

            } // list ip-mirror-interface

            container ipv6 {
                description "Enter the ipv6 context";

                container neighbor-discovery {
                    description "Enter the neighbor-discovery context";

                    leaf reachable-time {
                        type types-router:neighbor-discovery-reachable-time;
                        default "30";
                        description "Neighbor reachability detection timer";
                    }

                    leaf stale-time {
                        type types-router:neighbor-discovery-stale-time;
                        default "14400";
                        description "Neighbor discovery cache entry stale time";
                    }

                } // container neighbor-discovery

                container router-advertisement {
                    description "Enter the router-advertisement context";

                    leaf-list apply-groups {
                        type leafref {
                            path "../../../../../groups/group/name";
                        }
                        max-elements 8;
                        ordered-by user;
                        description "Apply a configuration group at this level";
                    }

                    leaf-list apply-groups-exclude {
                        type leafref {
                            path "../../../../../groups/group/name";
                        }
                        max-elements 8;
                        ordered-by user;
                        description "Exclude a configuration group at this level";
                    }

                    container dns-options {
                        presence "Enable the dns-options context";
                        description "Enable the dns-options context";

                        leaf rdnss-lifetime {
                            type union {
                                type enumeration {
                                    enum infinite                       { value -1; }
                                }
                                type int32 {
                                    range "0|4..3600";
                                }
                            }
                            units "seconds";
                            default "infinite";
                            description "Maximum time over which the RDNSS address is valid";
                        }

                        leaf-list server {
                            type types-sros:ipv6-address;
                            max-elements 4;
                            ordered-by user;
                            description "RAs that are forwarded to IPv6 DNS servers";
                        }

                        leaf-list apply-groups {
                            type leafref {
                                path "../../../../../../groups/group/name";
                            }
                            max-elements 8;
                            ordered-by user;
                            description "Apply a configuration group at this level";
                        }

                        leaf-list apply-groups-exclude {
                            type leafref {
                                path "../../../../../../groups/group/name";
                            }
                            max-elements 8;
                            ordered-by user;
                            description "Exclude a configuration group at this level";
                        }

                    } // container dns-options

                    list interface {
                        key "ip-int-name";
                        description "Enter the interface list instance";

                        leaf ip-int-name {
                            type leafref {
                                path "../../../../interface/interface-name";
                            }
                            description "VPRN interface name";
                        }

                        leaf current-hop-limit {
                            type uint16 {
                                range "0..255";
                            }
                            default "64";
                            description "Hop limit advertised in RA messages";
                        }

                        leaf managed-configuration {
                            type boolean;
                            default "false";
                            description "Set the managed address configuration flag";
                        }

                        leaf max-advertisement-interval {
                            type uint32 {
                                range "4..1800";
                            }
                            units "seconds";
                            default "600";
                            description "Maximum time between sending advertisement messages";
                        }

                        leaf min-advertisement-interval {
                            type uint32 {
                                range "3..1350";
                            }
                            units "seconds";
                            default "200";
                            description "Minimum interval between router advertisement messages";
                        }

                        leaf mtu {
                            type uint32 {
                                range "1280..9800";
                            }
                            description "MTU for sending packets to the router";
                        }

                        leaf nd-router-preference {
                            type types-router:neighbor-discovery-router-preference;
                            default "medium";
                            description "Default router preference for Router Advertisements";
                        }

                        leaf other-stateful-configuration {
                            type boolean;
                            default "false";
                            description "Set the other configuration flag";
                        }

                        leaf reachable-time {
                            type uint32 {
                                range "0..3600000";
                            }
                            units "milliseconds";
                            default "0";
                            description "Time the router is reachable by other hosts or nodes";
                        }

                        leaf retransmit-time {
                            type uint32 {
                                range "0..1800000";
                            }
                            units "milliseconds";
                            default "0";
                            description "Time to advertise neighbor advertisement messages";
                        }

                        leaf router-lifetime {
                            type uint32 {
                                range "0|4..9000";
                            }
                            units "seconds";
                            default "1800";
                            description "Lifetime value in neighbor advertisement messages";
                        }

                        leaf admin-state {
                            type types-sros:admin-state;
                            default "disable";
                            description "Administrative state of router advertisement";
                        }

                        leaf use-virtual-mac {
                            type boolean;
                            default "false";
                            description "Use VRRP virtual MAC address for advertisement message";
                        }

                        leaf-list apply-groups {
                            type leafref {
                                path "../../../../../../groups/group/name";
                            }
                            max-elements 8;
                            ordered-by user;
                            description "Apply a configuration group at this level";
                        }

                        leaf-list apply-groups-exclude {
                            type leafref {
                                path "../../../../../../groups/group/name";
                            }
                            max-elements 8;
                            ordered-by user;
                            description "Exclude a configuration group at this level";
                        }

                        container dns-options {
                            presence "Enable the dns-options context";
                            description "Enable the dns-options context";

                            leaf include-rdnss {
                                type boolean;
                                default "true";
                                description "Include the RDNSS option in the RA";
                            }

                            leaf rdnss-lifetime {
                                type union {
                                    type int32 {
                                        range "0|4..3600";
                                    }
                                    type enumeration {
                                        enum infinite                       { value -1; }
                                    }
                                }
                                units "seconds";
                                description "Maximum time over which the RDNSS address 25 is valid";
                            }

                            leaf-list server {
                                type types-sros:ipv6-address;
                                max-elements 4;
                                ordered-by user;
                                description "RAs that are forwarded to IPv6 DNS servers";
                            }

                            leaf-list apply-groups {
                                type leafref {
                                    path "../../../../../../../groups/group/name";
                                }
                                max-elements 8;
                                ordered-by user;
                                description "Apply a configuration group at this level";
                            }

                            leaf-list apply-groups-exclude {
                                type leafref {
                                    path "../../../../../../../groups/group/name";
                                }
                                max-elements 8;
                                ordered-by user;
                                description "Exclude a configuration group at this level";
                            }

                        } // container dns-options

                        list prefix {
                            key "ipv6-prefix";
                            max-elements 254;
                            description "Enter the prefix list instance";

                            leaf ipv6-prefix {
                                type types-sros:ipv6-prefix;
                                description "IPv6 address prefix";
                            }

                            leaf autonomous {
                                type boolean;
                                default "true";
                                description "Set the autonomous flag value";
                            }

                            leaf on-link {
                                type boolean;
                                default "true";
                                description "Use prefix for on-link determination";
                            }

                            leaf preferred-lifetime {
                                type union {
                                    type enumeration {
                                        enum infinite                       { value -1; }
                                    }
                                    type uint32 {
                                        range "0..4294967294";
                                    }
                                }
                                units "seconds";
                                default "604800";
                                description "Remaining time that the prefix remains preferred";
                            }

                            leaf valid-lifetime {
                                type union {
                                    type enumeration {
                                        enum infinite                       { value -1; }
                                    }
                                    type uint32 {
                                        range "0..4294967294";
                                    }
                                }
                                units "seconds";
                                default "2592000";
                                description "Remaining time in which the prefix is still valid";
                            }

                            leaf-list apply-groups {
                                type leafref {
                                    path "../../../../../../../groups/group/name";
                                }
                                max-elements 8;
                                ordered-by user;
                                description "Apply a configuration group at this level";
                            }

                            leaf-list apply-groups-exclude {
                                type leafref {
                                    path "../../../../../../../groups/group/name";
                                }
                                max-elements 8;
                                ordered-by user;
                                description "Exclude a configuration group at this level";
                            }

                        } // list prefix

                    } // list interface

                } // container router-advertisement

            } // container ipv6

            list spoke-sdp {
                key "sdp-bind-id";
                description "Enter the spoke-sdp list instance";

                leaf sdp-bind-id {
                    type types-services:sdp-bind-id;
                    description "SDP binding ID";
                }

                leaf description {
                    type types-sros:description;
                    description "Text description";
                }

                leaf-list apply-groups {
                    type leafref {
                        path "../../../../groups/group/name";
                    }
                    max-elements 8;
                    ordered-by user;
                    description "Apply a configuration group at this level";
                }

                leaf-list apply-groups-exclude {
                    type leafref {
                        path "../../../../groups/group/name";
                    }
                    max-elements 8;
                    ordered-by user;
                    description "Exclude a configuration group at this level";
                }

            } // list spoke-sdp

            container source-address {
                description "Enter the source-address context";

                list ipv4 {
                    key "application";
                    description "Enter the ipv4 list instance";

                    leaf application {
                        type enumeration {
                            enum telnet                         { value 1; }
                            enum ssh                            { value 3; }
                            enum snmptrap                       { value 6; }
                            enum ping                           { value 8; }
                            enum traceroute                     { value 9; }
                            enum ntp                            { value 12; }
                            enum cflowd                         { value 13; }
                            enum ptp                            { value 23; }
                            enum icmp-error                     { value 29; }
                        }
                        description "Application that uses the source IP address";
                    }

                    leaf-list apply-groups {
                        type leafref {
                            path "../../../../../groups/group/name";
                        }
                        max-elements 8;
                        ordered-by user;
                        description "Apply a configuration group at this level";
                    }

                    leaf-list apply-groups-exclude {
                        type leafref {
                            path "../../../../../groups/group/name";
                        }
                        max-elements 8;
                        ordered-by user;
                        description "Exclude a configuration group at this level";
                    }

                    choice source {
                        mandatory true;
                        case interface-name {

                            leaf interface-name {
                                type types-sros:interface-name;
                                sros-ext:immutable;
                                description "IP interface name";
                            }

                        }
                        case address {

                            leaf address {
                                type types-sros:ipv4-address;
                                sros-ext:immutable;
                                description "Source IPv4 address";
                            }

                        }
                    }
                } // list ipv4

                list ipv6 {
                    key "application";
                    description "Enter the ipv6 list instance";

                    leaf application {
                        type enumeration {
                            enum telnet                         { value 14; }
                            enum snmptrap                       { value 18; }
                            enum ping                           { value 20; }
                            enum traceroute                     { value 21; }
                            enum cflowd                         { value 25; }
                            enum ntp                            { value 26; }
                            enum icmp6-error                    { value 30; }
                            enum ssh                            { value 33; }
                            enum ptp                            { value 34; }
                        }
                        description "Application that uses the source IP address";
                    }

                    leaf address {
                        type types-sros:ipv6-address;
                        sros-ext:immutable;
                        mandatory true;
                        description "Source IPv6 address";
                    }

                    leaf-list apply-groups {
                        type leafref {
                            path "../../../../../groups/group/name";
                        }
                        max-elements 8;
                        ordered-by user;
                        description "Apply a configuration group at this level";
                    }

                    leaf-list apply-groups-exclude {
                        type leafref {
                            path "../../../../../groups/group/name";
                        }
                        max-elements 8;
                        ordered-by user;
                        description "Exclude a configuration group at this level";
                    }

                } // list ipv6

            } // container source-address

            container static-routes {
                description "Enter the static-routes context";

                leaf-list apply-groups {
                    type leafref {
                        path "../../../../groups/group/name";
                    }
                    max-elements 8;
                    ordered-by user;
                    description "Apply a configuration group at this level";
                }

                leaf-list apply-groups-exclude {
                    type leafref {
                        path "../../../../groups/group/name";
                    }
                    max-elements 8;
                    ordered-by user;
                    description "Exclude a configuration group at this level";
                }

                container hold-down {
                    presence "Enable the hold-down context";
                    description "Enable the hold-down context";

                    leaf initial {
                        type uint32 {
                            range "1..65535";
                        }
                        mandatory true;
                        description "Value for the initial hold-down time";
                    }

                    leaf multiplier {
                        type uint32 {
                            range "1..10";
                        }
                        mandatory true;
                        description "Multiplier of the previous hold-down time";
                    }

                    leaf max-value {
                        type uint32 {
                            range "1..65535";
                        }
                        mandatory true;
                        description "Maximum value of the hold-down time";
                    }

                } // container hold-down

                list route {
                    key "ip-prefix route-type";
                    description "Enter the route list instance";

                    leaf ip-prefix {
                        type types-sros:ip-prefix;
                        description "IP prefix and prefix length for the static routes";
                    }

                    leaf route-type {
                        type types-router:unicast-multicast;
                        description "Static route type";
                    }

                    leaf-list community {
                        type types-sros:community;
                        max-elements 12;
                        ordered-by user;
                        description "Community ID associated with the static route";
                    }

                    leaf tag {
                        type uint32 {
                            range "1..max";
                        }
                        description "Static route tag";
                    }

                    leaf backup-tag {
                        type uint32 {
                            range "1..max";
                        }
                        description "Static route backup tag";
                    }

                    leaf-list apply-groups {
                        type leafref {
                            path "../../../../../groups/group/name";
                        }
                        max-elements 8;
                        ordered-by user;
                        description "Apply a configuration group at this level";
                    }

                    leaf-list apply-groups-exclude {
                        type leafref {
                            path "../../../../../groups/group/name";
                        }
                        max-elements 8;
                        ordered-by user;
                        description "Exclude a configuration group at this level";
                    }

                    container blackhole {
                        presence "Enable the blackhole context";
                        description "Enable the blackhole context";

                        leaf description {
                            type types-sros:description-allow-all-white-spaces;
                            description "Text description";
                        }

                        leaf metric {
                            type uint32 {
                                range "0..65535";
                            }
                            default "1";
                            description "Static route metric";
                        }

                        leaf preference {
                            type uint32 {
                                range "1..255";
                            }
                            default "5";
                            description "Priority of this static route over the routes from different sources";
                        }

                        leaf tag {
                            type uint32 {
                                range "1..max";
                            }
                            description "Static route tag";
                        }

                        leaf community {
                            type types-sros:community;
                            description "Community ID associated with the static route";
                        }

                        leaf admin-state {
                            type types-sros:admin-state;
                            description "Administrative state of the static route operation";
                        }

                        leaf generate-icmp {
                            type boolean;
                            default "false";
                            description "Send ICMP unreachable messages when received packets match a static route with black-hole next-hop";
                        }

                        leaf-list apply-groups {
                            type leafref {
                                path "../../../../../../groups/group/name";
                            }
                            max-elements 8;
                            ordered-by user;
                            description "Apply a configuration group at this level";
                        }

                        leaf-list apply-groups-exclude {
                            type leafref {
                                path "../../../../../../groups/group/name";
                            }
                            max-elements 8;
                            ordered-by user;
                            description "Exclude a configuration group at this level";
                        }

                        container prefix-list {
                            description "Enter the prefix-list context";

                            leaf name {
                                type leafref {
                                    path "../../../../../../../policy-options/prefix-list/name";
                                }
                                description "Prefix list name";
                            }

                            leaf flag {
                                type enumeration {
                                    enum any                            { value 0; }
                                    enum all                            { value 1; }
                                    enum none                           { value 2; }
                                }
                                default "any";
                                description "Static route match condition from prefix list";
                            }

                            leaf router-instance {
                                type string;
                                description "Router instance used for matching prefix list";
                            }

                        } // container prefix-list

                    } // container blackhole

                    container grt {
                        presence "Enable the grt context";
                        description "Enable the grt context";

                        leaf description {
                            type types-sros:description-allow-all-white-spaces;
                            description "Text description";
                        }

                        leaf metric {
                            type uint32 {
                                range "0..65535";
                            }
                            default "1";
                            description "Static route metric";
                        }

                        leaf preference {
                            type uint32 {
                                range "1..255";
                            }
                            default "5";
                            description "Priority of this static route over the routes from different sources";
                        }

                        leaf admin-state {
                            type types-sros:admin-state;
                            description "Administrative state of the static route operation";
                        }

                        leaf-list apply-groups {
                            type leafref {
                                path "../../../../../../groups/group/name";
                            }
                            max-elements 8;
                            ordered-by user;
                            description "Apply a configuration group at this level";
                        }

                        leaf-list apply-groups-exclude {
                            type leafref {
                                path "../../../../../../groups/group/name";
                            }
                            max-elements 8;
                            ordered-by user;
                            description "Exclude a configuration group at this level";
                        }

                    } // container grt

                    list indirect {
                        key "ip-address";
                        description "Enter the indirect list instance";

                        leaf ip-address {
                            type types-sros:ip-address;
                            description "Next-hop IP address used to reach the destination";
                        }

                        leaf description {
                            type types-sros:description-allow-all-white-spaces;
                            description "Text description";
                        }

                        leaf metric {
                            type uint32 {
                                range "0..65535";
                            }
                            default "1";
                            description "Static route metric";
                        }

                        leaf preference {
                            type uint32 {
                                range "1..255";
                            }
                            default "5";
                            description "Priority of this static route over the routes from different sources";
                        }

                        leaf tag {
                            type uint32 {
                                range "1..max";
                            }
                            description "Static route tag";
                        }

                        leaf community {
                            type types-sros:community;
                            description "Community ID associated with the static route";
                        }

                        leaf destination-class {
                            type types-sros:class-index;
                            description "Destination class for this static route";
                        }

                        leaf source-class {
                            type types-sros:class-index;
                            description "Source class for the static route";
                        }

                        leaf admin-state {
                            type types-sros:admin-state;
                            description "Administrative state of the static route operation";
                        }

                        leaf-list apply-groups {
                            type leafref {
                                path "../../../../../../groups/group/name";
                            }
                            max-elements 8;
                            ordered-by user;
                            description "Apply a configuration group at this level";
                        }

                        leaf-list apply-groups-exclude {
                            type leafref {
                                path "../../../../../../groups/group/name";
                            }
                            max-elements 8;
                            ordered-by user;
                            description "Exclude a configuration group at this level";
                        }

                        container qos {
                            description "Enter the qos context";

                            leaf forwarding-class {
                                type types-sros:fc-name;
                                description "Forwarding class associated with the static route";
                            }

                            leaf priority {
                                type types-sros:priority;
                                description "Static route priority";
                            }

                        } // container qos

                        container prefix-list {
                            description "Enter the prefix-list context";

                            leaf name {
                                type leafref {
                                    path "../../../../../../../policy-options/prefix-list/name";
                                }
                                description "Prefix list name";
                            }

                            leaf flag {
                                type enumeration {
                                    enum any                            { value 0; }
                                    enum all                            { value 1; }
                                    enum none                           { value 2; }
                                }
                                default "any";
                                description "Static route match condition from prefix list";
                            }

                            leaf router-instance {
                                type string;
                                description "Router instance used for matching prefix list";
                            }

                        } // container prefix-list

                        list cpe-check {
                            key "address";
                            max-elements 1;
                            description "Enter the cpe-check list instance";

                            leaf address {
                                type types-sros:ip-address;
                                description "IP address of the target CPE device";
                            }

                            leaf drop-count {
                                type uint32 {
                                    range "1..255";
                                }
                                default "3";
                                description "Consecutive ping replies missed before CPE deemed down";
                            }

                            leaf interval {
                                type uint32 {
                                    range "1..255";
                                }
                                units "seconds";
                                default "1";
                                description "Interval between ICMP pings to target CPE IP address";
                            }

                            leaf log {
                                type boolean;
                                default "false";
                                description "Log CPE connectivity checks transitions";
                            }

                            leaf padding-size {
                                type uint32 {
                                    range "0..16384";
                                }
                                units "bytes";
                                default "56";
                                description "Padding size for CPE connectivity checks";
                            }

                            leaf-list apply-groups {
                                type leafref {
                                    path "../../../../../../../groups/group/name";
                                }
                                max-elements 8;
                                ordered-by user;
                                description "Apply a configuration group at this level";
                            }

                            leaf-list apply-groups-exclude {
                                type leafref {
                                    path "../../../../../../../groups/group/name";
                                }
                                max-elements 8;
                                ordered-by user;
                                description "Exclude a configuration group at this level";
                            }

                        } // list cpe-check

                    } // list indirect

                    list interface {
                        key "interface-name";
                        description "Enter the interface list instance";

                        leaf interface-name {
                            type types-sros:interface-name;
                            description "Router interface name";
                        }

                        leaf description {
                            type types-sros:description-allow-all-white-spaces;
                            description "Text description";
                        }

                        leaf metric {
                            type uint32 {
                                range "0..65535";
                            }
                            default "1";
                            description "Static route metric";
                        }

                        leaf preference {
                            type uint32 {
                                range "1..255";
                            }
                            default "5";
                            description "Priority of this static route over the routes from different sources";
                        }

                        leaf tag {
                            type uint32 {
                                range "1..max";
                            }
                            description "Static route tag";
                        }

                        leaf community {
                            type types-sros:community;
                            description "Community ID associated with the static route";
                        }

                        leaf destination-class {
                            type types-sros:class-index;
                            description "Destination class for this static route";
                        }

                        leaf source-class {
                            type types-sros:class-index;
                            description "Source class for the static route";
                        }

                        leaf load-balancing-weight {
                            type uint32 {
                                range "1..max";
                            }
                            description "Load-balancing weight for all of the ECMP next hops";
                        }

                        leaf admin-state {
                            type types-sros:admin-state;
                            description "Administrative state of the static route operation";
                        }

                        leaf-list apply-groups {
                            type leafref {
                                path "../../../../../../groups/group/name";
                            }
                            max-elements 8;
                            ordered-by user;
                            description "Apply a configuration group at this level";
                        }

                        leaf-list apply-groups-exclude {
                            type leafref {
                                path "../../../../../../groups/group/name";
                            }
                            max-elements 8;
                            ordered-by user;
                            description "Exclude a configuration group at this level";
                        }

                        container qos {
                            description "Enter the qos context";

                            leaf forwarding-class {
                                type types-sros:fc-name;
                                description "Forwarding class associated with the static route";
                            }

                            leaf priority {
                                type types-sros:priority;
                                description "Static route priority";
                            }

                        } // container qos

                        container prefix-list {
                            description "Enter the prefix-list context";

                            leaf name {
                                type leafref {
                                    path "../../../../../../../policy-options/prefix-list/name";
                                }
                                description "Prefix list name";
                            }

                            leaf flag {
                                type enumeration {
                                    enum any                            { value 0; }
                                    enum all                            { value 1; }
                                    enum none                           { value 2; }
                                }
                                default "any";
                                description "Static route match condition from prefix list";
                            }

                            leaf router-instance {
                                type string;
                                description "Router instance used for matching prefix list";
                            }

                        } // container prefix-list

                        list cpe-check {
                            key "address";
                            max-elements 1;
                            description "Enter the cpe-check list instance";

                            leaf address {
                                type types-sros:ip-address;
                                description "IP address of the target CPE device";
                            }

                            leaf drop-count {
                                type uint32 {
                                    range "1..255";
                                }
                                default "3";
                                description "Consecutive ping replies missed before CPE deemed down";
                            }

                            leaf interval {
                                type uint32 {
                                    range "1..255";
                                }
                                units "seconds";
                                default "1";
                                description "Interval between ICMP pings to target CPE IP address";
                            }

                            leaf log {
                                type boolean;
                                default "false";
                                description "Log CPE connectivity checks transitions";
                            }

                            leaf padding-size {
                                type uint32 {
                                    range "0..16384";
                                }
                                units "bytes";
                                default "56";
                                description "Padding size for CPE connectivity checks";
                            }

                            leaf-list apply-groups {
                                type leafref {
                                    path "../../../../../../../groups/group/name";
                                }
                                max-elements 8;
                                ordered-by user;
                                description "Apply a configuration group at this level";
                            }

                            leaf-list apply-groups-exclude {
                                type leafref {
                                    path "../../../../../../../groups/group/name";
                                }
                                max-elements 8;
                                ordered-by user;
                                description "Exclude a configuration group at this level";
                            }

                        } // list cpe-check

                    } // list interface

                    list ipsec-tunnel {
                        key "ipsec-tunnel-name";
                        description "Enter the ipsec-tunnel list instance";

                        leaf ipsec-tunnel-name {
                            type types-sros:named-item;
                            description "IPsec tunnel name";
                        }

                        leaf description {
                            type types-sros:description-allow-all-white-spaces;
                            description "Text description";
                        }

                        leaf metric {
                            type uint32 {
                                range "0..65535";
                            }
                            default "1";
                            description "Static route metric";
                        }

                        leaf preference {
                            type uint32 {
                                range "1..255";
                            }
                            default "5";
                            description "Priority of this static route over the routes from different sources";
                        }

                        leaf tag {
                            type uint32 {
                                range "1..max";
                            }
                            description "Static route tag";
                        }

                        leaf community {
                            type types-sros:community;
                            description "Community ID associated with the static route";
                        }

                        leaf destination-class {
                            type types-sros:class-index;
                            description "Destination class for this static route";
                        }

                        leaf source-class {
                            type types-sros:class-index;
                            description "Source class for the static route";
                        }

                        leaf admin-state {
                            type types-sros:admin-state;
                            description "Administrative state of the static route operation";
                        }

                        leaf-list apply-groups {
                            type leafref {
                                path "../../../../../../groups/group/name";
                            }
                            max-elements 8;
                            ordered-by user;
                            description "Apply a configuration group at this level";
                        }

                        leaf-list apply-groups-exclude {
                            type leafref {
                                path "../../../../../../groups/group/name";
                            }
                            max-elements 8;
                            ordered-by user;
                            description "Exclude a configuration group at this level";
                        }

                        container qos {
                            description "Enter the qos context";

                            leaf forwarding-class {
                                type types-sros:fc-name;
                                description "Forwarding class associated with the static route";
                            }

                            leaf priority {
                                type types-sros:priority;
                                description "Static route priority";
                            }

                        } // container qos

                    } // list ipsec-tunnel

                    list next-hop {
                        key "ip-address";
                        description "Enter the next-hop list instance";

                        leaf ip-address {
                            type types-sros:ip-address-with-zone;
                            description "Next-hop IP address used to reach the destination";
                        }

                        leaf description {
                            type types-sros:description-allow-all-white-spaces;
                            description "Text description";
                        }

                        leaf metric {
                            type uint32 {
                                range "0..65535";
                            }
                            default "1";
                            description "Static route metric";
                        }

                        leaf preference {
                            type uint32 {
                                range "1..255";
                            }
                            default "5";
                            description "Priority of this static route over the routes from different sources";
                        }

                        leaf tag {
                            type uint32 {
                                range "1..max";
                            }
                            description "Static route tag";
                        }

                        leaf community {
                            type types-sros:community;
                            description "Community ID associated with the static route";
                        }

                        leaf destination-class {
                            type types-sros:class-index;
                            description "Destination class for this static route";
                        }

                        leaf source-class {
                            type types-sros:class-index;
                            description "Source class for the static route";
                        }

                        leaf bfd-liveness {
                            type boolean;
                            default "false";
                            description "Use Bidirectional Forwarding Detection on this static route";
                        }

                        leaf validate-next-hop {
                            type boolean;
                            default "false";
                            description "Track the state of the next hop in the IPv4 ARP Cache or the IPv6 Neighbor Cache";
                        }

                        leaf load-balancing-weight {
                            type uint32 {
                                range "1..max";
                            }
                            description "Load-balancing weight for all of the ECMP next hops";
                        }

                        leaf admin-state {
                            type types-sros:admin-state;
                            description "Administrative state of the static route operation";
                        }

                        leaf-list apply-groups {
                            type leafref {
                                path "../../../../../../groups/group/name";
                            }
                            max-elements 8;
                            ordered-by user;
                            description "Apply a configuration group at this level";
                        }

                        leaf-list apply-groups-exclude {
                            type leafref {
                                path "../../../../../../groups/group/name";
                            }
                            max-elements 8;
                            ordered-by user;
                            description "Exclude a configuration group at this level";
                        }

                        container qos {
                            description "Enter the qos context";

                            leaf forwarding-class {
                                type types-sros:fc-name;
                                description "Forwarding class associated with the static route";
                            }

                            leaf priority {
                                type types-sros:priority;
                                description "Static route priority";
                            }

                        } // container qos

                        container prefix-list {
                            description "Enter the prefix-list context";

                            leaf name {
                                type leafref {
                                    path "../../../../../../../policy-options/prefix-list/name";
                                }
                                description "Prefix list name";
                            }

                            leaf flag {
                                type enumeration {
                                    enum any                            { value 0; }
                                    enum all                            { value 1; }
                                    enum none                           { value 2; }
                                }
                                default "any";
                                description "Static route match condition from prefix list";
                            }

                            leaf router-instance {
                                type string;
                                description "Router instance used for matching prefix list";
                            }

                        } // container prefix-list

                        container backup-next-hop {
                            description "Enter the backup-next-hop context";

                            leaf address {
                                type types-sros:ip-address;
                                description "Backup next-hop IP address";
                            }

                        } // container backup-next-hop

                        list cpe-check {
                            key "address";
                            max-elements 1;
                            description "Enter the cpe-check list instance";

                            leaf address {
                                type types-sros:ip-address;
                                description "IP address of the target CPE device";
                            }

                            leaf drop-count {
                                type uint32 {
                                    range "1..255";
                                }
                                default "3";
                                description "Consecutive ping replies missed before CPE deemed down";
                            }

                            leaf interval {
                                type uint32 {
                                    range "1..255";
                                }
                                units "seconds";
                                default "1";
                                description "Interval between ICMP pings to target CPE IP address";
                            }

                            leaf log {
                                type boolean;
                                default "false";
                                description "Log CPE connectivity checks transitions";
                            }

                            leaf padding-size {
                                type uint32 {
                                    range "0..16384";
                                }
                                units "bytes";
                                default "56";
                                description "Padding size for CPE connectivity checks";
                            }

                            leaf-list apply-groups {
                                type leafref {
                                    path "../../../../../../../groups/group/name";
                                }
                                max-elements 8;
                                ordered-by user;
                                description "Apply a configuration group at this level";
                            }

                            leaf-list apply-groups-exclude {
                                type leafref {
                                    path "../../../../../../../groups/group/name";
                                }
                                max-elements 8;
                                ordered-by user;
                                description "Exclude a configuration group at this level";
                            }

                        } // list cpe-check

                    } // list next-hop

                } // list route

            } // container static-routes

            container flowspec {
                description "Enter the flowspec context";

                leaf ip-filter-max-size {
                    type uint32 {
                        range "0..262143";
                    }
                    default "512";
                    description "Maximum number of FlowSpec rule entries in IPv4 filter";
                }

                leaf ipv6-filter-max-size {
                    type uint32 {
                        range "0..262143";
                    }
                    default "512";
                    description "Maximum number of flowspec rule entries in IPv6 filter";
                }

                leaf filter-cam-type {
                    type enumeration {
                        enum normal                         { value 0; }
                        enum packet-length                  { value 2; }
                    }
                    default "normal";
                    description "Filter policy type for FlowSpec embedding";
                }

                leaf-list apply-groups {
                    type leafref {
                        path "../../../../groups/group/name";
                    }
                    max-elements 8;
                    ordered-by user;
                    description "Apply a configuration group at this level";
                }

                leaf-list apply-groups-exclude {
                    type leafref {
                        path "../../../../groups/group/name";
                    }
                    max-elements 8;
                    ordered-by user;
                    description "Exclude a configuration group at this level";
                }

            } // container flowspec

            container log {
                description "Enter the log context";

                leaf-list apply-groups {
                    type leafref {
                        path "../../../../groups/group/name";
                    }
                    max-elements 8;
                    ordered-by user;
                    description "Apply a configuration group at this level";
                }

                leaf-list apply-groups-exclude {
                    type leafref {
                        path "../../../../groups/group/name";
                    }
                    max-elements 8;
                    ordered-by user;
                    description "Exclude a configuration group at this level";
                }

                list filter {
                    key "filter-name";
                    max-elements 1500;
                    description "Enter the filter list instance";

                    leaf filter-name {
                        type types-log:log-filter-name;
                        description "Filter ID";
                    }

                    leaf description {
                        type types-sros:description;
                        description "Text description";
                    }

                    leaf default-action {
                        type types-log:filter-action;
                        default "forward";
                        description "Default action for the event filter";
                    }

                    leaf-list apply-groups {
                        type leafref {
                            path "../../../../../groups/group/name";
                        }
                        max-elements 8;
                        ordered-by user;
                        description "Apply a configuration group at this level";
                    }

                    leaf-list apply-groups-exclude {
                        type leafref {
                            path "../../../../../groups/group/name";
                        }
                        max-elements 8;
                        ordered-by user;
                        description "Exclude a configuration group at this level";
                    }

                    list entry {
                        status obsolete;
                        key "entry-id";
                        description "Enter the entry list instance";

                        leaf entry-id {
                            status obsolete;
                            type uint32 {
                                range "1..999";
                            }
                            description "Identification number for an event log filter parameter";
                        }

                        leaf description {
                            status obsolete;
                            type types-sros:description;
                            description "Text description";
                        }

                        leaf action {
                            status obsolete;
                            type types-log:filter-action;
                            description "Action for this event filter entry";
                        }

                        leaf-list apply-groups {
                            status obsolete;
                            type leafref {
                                path "../../../../../../groups/group/name";
                            }
                            max-elements 8;
                            ordered-by user;
                            description "Apply a configuration group at this level";
                        }

                        leaf-list apply-groups-exclude {
                            status obsolete;
                            type leafref {
                                path "../../../../../../groups/group/name";
                            }
                            max-elements 8;
                            ordered-by user;
                            description "Exclude a configuration group at this level";
                        }

                        container match {
                            status obsolete;
                            description "Enter the match context";

                            container application {
                                status obsolete;
                                description "Enter the application context";

                                choice application-match {
                                    status obsolete;
                                    case eq {
                                        status obsolete;

                                        leaf eq {
                                            status obsolete;
                                            type types-log:application-obsolete;
                                            description "Application to match";
                                        }

                                    }
                                    case neq {
                                        status obsolete;

                                        leaf neq {
                                            status obsolete;
                                            type types-log:application-obsolete;
                                            description "Application to be filtered out";
                                        }

                                    }
                                }
                            } // container application

                            container message {
                                status obsolete;
                                description "Enter the message context";

                                leaf regexp {
                                    status obsolete;
                                    type boolean;
                                    default "false";
                                    description "String comparison to determine if the log event matches the value of pattern";
                                }

                                choice message-match {
                                    status obsolete;
                                    case eq {
                                        status obsolete;

                                        leaf eq {
                                            status obsolete;
                                            type string {
                                                length "1..400";
                                            }
                                            description "Log event message to match";
                                        }

                                    }
                                    case neq {
                                        status obsolete;

                                        leaf neq {
                                            status obsolete;
                                            type string {
                                                length "1..400";
                                            }
                                            description "Log event message to be filtered out";
                                        }

                                    }
                                }
                            } // container message

                            container event {
                                status obsolete;
                                description "Enter the event context";

                                choice event-match {
                                    status obsolete;
                                    case eq {
                                        status obsolete;

                                        leaf eq {
                                            status obsolete;
                                            type uint32 {
                                                range "1..max";
                                            }
                                            description "Log event message to match";
                                        }

                                    }
                                    case neq {
                                        status obsolete;

                                        leaf neq {
                                            status obsolete;
                                            type uint32 {
                                                range "1..max";
                                            }
                                            description "Log event message to filter out";
                                        }

                                    }
                                    case lt {
                                        status obsolete;

                                        leaf lt {
                                            status obsolete;
                                            type uint32 {
                                                range "1..max";
                                            }
                                            description "Number of the log event to match";
                                        }

                                    }
                                    case lte {
                                        status obsolete;

                                        leaf lte {
                                            status obsolete;
                                            type uint32 {
                                                range "1..max";
                                            }
                                            description "Number of the log event to match";
                                        }

                                    }
                                    case gt {
                                        status obsolete;

                                        leaf gt {
                                            status obsolete;
                                            type uint32 {
                                                range "1..max";
                                            }
                                            description "Number of the log event to match";
                                        }

                                    }
                                    case gte {
                                        status obsolete;

                                        leaf gte {
                                            status obsolete;
                                            type uint32 {
                                                range "1..max";
                                            }
                                            description "Number of the log event to match";
                                        }

                                    }
                                }
                            } // container event

                            container severity {
                                status obsolete;
                                description "Enter the severity context";

                                choice severity-match {
                                    status obsolete;
                                    case eq {
                                        status obsolete;

                                        leaf eq {
                                            status obsolete;
                                            type types-log:severity-level;
                                            description "Log event severity level to match";
                                        }

                                    }
                                    case neq {
                                        status obsolete;

                                        leaf neq {
                                            status obsolete;
                                            type types-log:severity-level;
                                            description "Log event severity level to filter out";
                                        }

                                    }
                                    case lt {
                                        status obsolete;

                                        leaf lt {
                                            status obsolete;
                                            type types-log:severity-level;
                                            description "Log event severity level";
                                        }

                                    }
                                    case lte {
                                        status obsolete;

                                        leaf lte {
                                            status obsolete;
                                            type types-log:severity-level;
                                            description "Log event severity level";
                                        }

                                    }
                                    case gt {
                                        status obsolete;

                                        leaf gt {
                                            status obsolete;
                                            type types-log:severity-level;
                                            description "Log event severity level";
                                        }

                                    }
                                    case gte {
                                        status obsolete;

                                        leaf gte {
                                            status obsolete;
                                            type types-log:severity-level;
                                            description "Log event severity level";
                                        }

                                    }
                                }
                            } // container severity

                            container subject {
                                status obsolete;
                                description "Enter the subject context";

                                leaf regexp {
                                    status obsolete;
                                    type boolean;
                                    default "false";
                                    description "String comparison to determine if the log event matches the value of subject";
                                }

                                choice subject-match {
                                    status obsolete;
                                    case eq {
                                        status obsolete;

                                        leaf eq {
                                            status obsolete;
                                            type types-sros:named-item;
                                            description "Log event subject string to match";
                                        }

                                    }
                                    case neq {
                                        status obsolete;

                                        leaf neq {
                                            status obsolete;
                                            type types-sros:named-item;
                                            description "Log event subject string to filter out";
                                        }

                                    }
                                }
                            } // container subject

                        } // container match

                    } // list entry

                    list named-entry {
                        key "entry-name";
                        max-elements 999;
                        ordered-by user;
                        description "Enter the named-entry list instance";

                        leaf entry-name {
                            type types-log:log-filter-entry-name;
                            description "Entry name";
                        }

                        leaf description {
                            type types-sros:description;
                            description "Text description";
                        }

                        leaf action {
                            type types-log:filter-action;
                            description "Action for this event filter entry";
                        }

                        leaf-list apply-groups {
                            type leafref {
                                path "../../../../../../groups/group/name";
                            }
                            max-elements 8;
                            ordered-by user;
                            description "Apply a configuration group at this level";
                        }

                        leaf-list apply-groups-exclude {
                            type leafref {
                                path "../../../../../../groups/group/name";
                            }
                            max-elements 8;
                            ordered-by user;
                            description "Exclude a configuration group at this level";
                        }

                        container match {
                            description "Enter the match context";

                            container application {
                                description "Enter the application context";

                                choice application-match {
                                    case eq {

                                        leaf eq {
                                            type types-log:application;
                                            description "Application to match";
                                        }

                                    }
                                    case neq {

                                        leaf neq {
                                            type types-log:application;
                                            description "Application to be filtered out";
                                        }

                                    }
                                }
                            } // container application

                            container message {
                                description "Enter the message context";

                                leaf regexp {
                                    type boolean;
                                    default "false";
                                    description "String comparison to determine if the log event matches the value of pattern";
                                }

                                choice message-match {
                                    case eq {

                                        leaf eq {
                                            type string {
                                                length "1..400";
                                            }
                                            description "Log event message to match";
                                        }

                                    }
                                    case neq {

                                        leaf neq {
                                            type string {
                                                length "1..400";
                                            }
                                            description "Log event message to be filtered out";
                                        }

                                    }
                                }
                            } // container message

                            container event {
                                description "Enter the event context";

                                choice event-match {
                                    case eq {

                                        leaf eq {
                                            type uint32 {
                                                range "1..max";
                                            }
                                            description "Log event message to match";
                                        }

                                    }
                                    case neq {

                                        leaf neq {
                                            type uint32 {
                                                range "1..max";
                                            }
                                            description "Log event message to filter out";
                                        }

                                    }
                                    case lt {

                                        leaf lt {
                                            type uint32 {
                                                range "1..max";
                                            }
                                            description "Number of the log event to match";
                                        }

                                    }
                                    case lte {

                                        leaf lte {
                                            type uint32 {
                                                range "1..max";
                                            }
                                            description "Number of the log event to match";
                                        }

                                    }
                                    case gt {

                                        leaf gt {
                                            type uint32 {
                                                range "1..max";
                                            }
                                            description "Number of the log event to match";
                                        }

                                    }
                                    case gte {

                                        leaf gte {
                                            type uint32 {
                                                range "1..max";
                                            }
                                            description "Number of the log event to match";
                                        }

                                    }
                                }
                            } // container event

                            container severity {
                                description "Enter the severity context";

                                choice severity-match {
                                    case eq {

                                        leaf eq {
                                            type types-log:severity-level;
                                            description "Log event severity level to match";
                                        }

                                    }
                                    case neq {

                                        leaf neq {
                                            type types-log:severity-level;
                                            description "Log event severity level to filter out";
                                        }

                                    }
                                    case lt {

                                        leaf lt {
                                            type types-log:severity-level;
                                            description "Log event severity level";
                                        }

                                    }
                                    case lte {

                                        leaf lte {
                                            type types-log:severity-level;
                                            description "Log event severity level";
                                        }

                                    }
                                    case gt {

                                        leaf gt {
                                            type types-log:severity-level;
                                            description "Log event severity level";
                                        }

                                    }
                                    case gte {

                                        leaf gte {
                                            type types-log:severity-level;
                                            description "Log event severity level";
                                        }

                                    }
                                }
                            } // container severity

                            container subject {
                                description "Enter the subject context";

                                leaf regexp {
                                    type boolean;
                                    default "false";
                                    description "String comparison to determine if the log event matches the value of subject";
                                }

                                choice subject-match {
                                    case eq {

                                        leaf eq {
                                            type types-sros:named-item;
                                            description "Log event subject string to match";
                                        }

                                    }
                                    case neq {

                                        leaf neq {
                                            type types-sros:named-item;
                                            description "Log event subject string to filter out";
                                        }

                                    }
                                }
                            } // container subject

                        } // container match

                    } // list named-entry

                } // list filter

                list log-id {
                    key "name";
                    max-elements 30;
                    description "Enter the log-id list instance";

                    leaf name {
                        type types-log:li-log-name;
                        description "Log ID";
                    }

                    leaf admin-state {
                        type types-sros:admin-state;
                        default "enable";
                        description "Administrative state of the log";
                    }

                    leaf description {
                        type types-sros:description;
                        description "Text description";
                    }

                    leaf netconf-stream {
                        type types-sros:named-item;
                        description "Destination NETCONF stream name";
                    }

                    leaf time-format {
                        type enumeration {
                            enum utc                            { value 1; }
                            enum local                          { value 2; }
                        }
                        default "utc";
                        description "Time zone output for file log contents and syslog";
                    }

                    leaf filter {
                        type leafref {
                            path "../../filter/filter-name";
                        }
                        description "Event filter policy with the log destination";
                    }

                    leaf python-policy {
                        type leafref {
                            path "../../../../../python/python-policy/name";
                        }
                        description "Python policy name";
                    }

                    leaf-list apply-groups {
                        type leafref {
                            path "../../../../../groups/group/name";
                        }
                        max-elements 8;
                        ordered-by user;
                        description "Apply a configuration group at this level";
                    }

                    leaf-list apply-groups-exclude {
                        type leafref {
                            path "../../../../../groups/group/name";
                        }
                        max-elements 8;
                        ordered-by user;
                        description "Exclude a configuration group at this level";
                    }

                    container source {
                        description "Enter the source context";

                        leaf main {
                            type boolean;
                            default "false";
                            description "Collect log events from the main event stream";
                        }

                        leaf security {
                            type boolean;
                            default "false";
                            description "Collect log events from the security event stream";
                        }

                        leaf change {
                            type boolean;
                            default "false";
                            description "Collect log events from the change event stream";
                        }

                        leaf debug {
                            type boolean;
                            default "false";
                            description "Collect log events from the debug event stream";
                        }

                    } // container source

                    container destination {
                        description "Enter the destination context";

                        choice log-id-destination {
                            case syslog {

                                leaf syslog {
                                    type leafref {
                                        path "../../../syslog/syslog-name";
                                    }
                                    sros-ext:immutable;
                                    description "Index with the information to format event messages sent to a specific SYSLOG collector";
                                }

                            }
                            case snmp {

                                container snmp {
                                    presence "Enable the snmp context";
                                    description "Enable the snmp context";

                                    leaf max-entries {
                                        type uint32 {
                                            range "50..3000";
                                        }
                                        sros-ext:immutable;
                                        default "100";
                                        description "Number of events stored in the memory log";
                                    }

                                } // container snmp

                            }
                            case netconf {

                                container netconf {
                                    presence "Enable the netconf context";
                                    description "Enable the netconf context";

                                    leaf max-entries {
                                        type uint32 {
                                            range "50..3000";
                                        }
                                        sros-ext:immutable;
                                        default "100";
                                        description "Number of events stored in the NETCONF log";
                                    }

                                } // container netconf

                            }
                        }
                    } // container destination

                } // list log-id

                list snmp-trap-group {
                    key "log-name";
                    description "Enter the snmp-trap-group list instance";

                    leaf log-name {
                        type types-log:svc-vprn-snmp-trap-group-name;
                        description "Log ID";
                    }

                    leaf description {
                        type types-sros:description;
                        description "Text description";
                    }

                    leaf log-id {
                        status obsolete;
                        type int32 {
                            range "1..100";
                        }
                        sros-ext:immutable;
                        description "SNMP notification group associated with the event log";
                    }

                    leaf-list apply-groups {
                        type leafref {
                            path "../../../../../groups/group/name";
                        }
                        max-elements 8;
                        ordered-by user;
                        description "Apply a configuration group at this level";
                    }

                    leaf-list apply-groups-exclude {
                        type leafref {
                            path "../../../../../groups/group/name";
                        }
                        max-elements 8;
                        ordered-by user;
                        description "Exclude a configuration group at this level";
                    }

                    list trap-target {
                        key "name";
                        max-elements 25;
                        description "Enter the trap-target list instance";

                        leaf name {
                            type string {
                                length "1..28";
                            }
                            description "Trap target name";
                        }

                        leaf description {
                            type types-sros:description;
                            description "Text description";
                        }

                        leaf address {
                            type types-sros:ip-unicast-address;
                            mandatory true;
                            description "IP address of the trap receiver";
                        }

                        leaf port {
                            type types-qos:tcp-udp-match-port;
                            default "162";
                            description "UDP port number to send messages to this remote SNMP notification collector";
                        }

                        leaf version {
                            type enumeration {
                                enum snmpv1                         { value 0; }
                                enum snmpv2c                        { value 1; }
                                enum snmpv3                         { value 3; }
                            }
                            default "snmpv3";
                            description "SNMP version to format notification messages sent to this SNMP notification collector";
                        }

                        leaf notify-community {
                            type string {
                                length "1..31";
                            }
                            mandatory true;
                            description "SNMPv1 or SNMPv2c community name string, or SNMPv3 security name, for sending a notification";
                        }

                        leaf security-level {
                            type enumeration {
                                enum no-auth-no-privacy             { value 1; }
                                enum auth-no-privacy                { value 2; }
                                enum privacy                        { value 3; }
                            }
                            default "no-auth-no-privacy";
                            description "Security level at which SNMP notification messages are sent to SNMP notification collector";
                        }

                        leaf replay {
                            type boolean;
                            default "false";
                            description "Retransmit missed notifications";
                        }

                        leaf-list apply-groups {
                            type leafref {
                                path "../../../../../../groups/group/name";
                            }
                            max-elements 8;
                            ordered-by user;
                            description "Apply a configuration group at this level";
                        }

                        leaf-list apply-groups-exclude {
                            type leafref {
                                path "../../../../../../groups/group/name";
                            }
                            max-elements 8;
                            ordered-by user;
                            description "Exclude a configuration group at this level";
                        }

                    } // list trap-target

                } // list snmp-trap-group

                list syslog {
                    key "syslog-name";
                    max-elements 30;
                    description "Enter the syslog list instance";

                    leaf syslog-name {
                        type types-log:log-vprn-syslog-name;
                        description "Syslog name";
                    }

                    leaf description {
                        type types-sros:description;
                        description "Text description";
                    }

                    leaf address {
                        type types-sros:ip-unicast-address;
                        description "IP address of the Syslog target host";
                    }

                    leaf facility {
                        type enumeration {
                            enum kernel                         { value 0; }
                            enum user                           { value 1; }
                            enum mail                           { value 2; }
                            enum systemd                        { value 3; }
                            enum auth                           { value 4; }
                            enum syslogd                        { value 5; }
                            enum printer                        { value 6; }
                            enum netnews                        { value 7; }
                            enum uucp                           { value 8; }
                            enum cron                           { value 9; }
                            enum authpriv                       { value 10; }
                            enum ftp                            { value 11; }
                            enum ntp                            { value 12; }
                            enum logaudit                       { value 13; }
                            enum logalert                       { value 14; }
                            enum cron2                          { value 15; }
                            enum local0                         { value 16; }
                            enum local1                         { value 17; }
                            enum local2                         { value 18; }
                            enum local3                         { value 19; }
                            enum local4                         { value 20; }
                            enum local5                         { value 21; }
                            enum local6                         { value 22; }
                            enum local7                         { value 23; }
                        }
                        default "local7";
                        description "Facility code for messages";
                    }

                    leaf severity {
                        type enumeration {
                            enum emergency                      { value 0; }
                            enum alert                          { value 1; }
                            enum critical                       { value 2; }
                            enum error                          { value 3; }
                            enum warning                        { value 4; }
                            enum notice                         { value 5; }
                            enum info                           { value 6; }
                            enum debug                          { value 7; }
                        }
                        default "info";
                        description "Severity level threshold for the syslog message";
                    }

                    leaf log-prefix {
                        type union {
                            type enumeration {
                                enum no-prefix                      { value -1; }
                            }
                            type string {
                                length "1..32";
                                pattern "([!-9;<>-~])+" {
                                    error-message "String must contain only printable characters between 33 - 126 ASCII except ':' and '='";
                                }
                            }
                        }
                        default "TMNX";
                        description "Prefix string to log message sent to target syslog host";
                    }

                    leaf tls-client-profile {
                        type leafref {
                            path "../../../../../system/security/tls/client-tls-profile/client-profile-name";
                        }
                        sros-ext:immutable;
                        description "TLS client profile used to encrypt syslog communication";
                    }

                    leaf port {
                        when "not(../tls-client-profile)" {
                            description "Log syslog TLS profile can not be defined together with port. TLS is using default port 6514";
                        }
                        type types-qos:tcp-udp-match-port;
                        default "514";
                        description "Destination port when sending syslog over UDP";
                    }

                    leaf timestamp-format {
                        type enumeration {
                            enum millisecond {
                                value 1;
                                description "Set timestamp format to milliseconds";
                            }
                        }
                        description "Syslog timestamp format";
                    }

                    leaf-list apply-groups {
                        type leafref {
                            path "../../../../../groups/group/name";
                        }
                        max-elements 8;
                        ordered-by user;
                        description "Apply a configuration group at this level";
                    }

                    leaf-list apply-groups-exclude {
                        type leafref {
                            path "../../../../../groups/group/name";
                        }
                        max-elements 8;
                        ordered-by user;
                        description "Exclude a configuration group at this level";
                    }

                    container hostname {
                        description "Enter the hostname context";

                        choice hostname {
                            case value {

                                leaf value {
                                    type types-sros:named-item-255;
                                    description "Syslog HOSTNAME field value";
                                }

                            }
                            case use-system-name {

                                container use-system-name {
                                    presence "Enable the use-system-name context";
                                    description "Enable the use-system-name context";

                                } // container use-system-name

                            }
                            case use-vprn-name {

                                container use-vprn-name {
                                    presence "Enable the use-vprn-name context";
                                    description "Enable the use-vprn-name context";

                                } // container use-vprn-name

                            }
                        }
                    } // container hostname

                } // list syslog

            } // container log

            container igmp-host-tracking {
                description "Enter the igmp-host-tracking context";

                leaf admin-state {
                    type types-sros:admin-state;
                    default "disable";
                    description "Administrative state of IGMP host tracking";
                }

                leaf expiry-time {
                    type types-sros:time-duration {
                        range "1..65535";
                    }
                    units "seconds";
                    default "260";
                    description "Time that the system continues to track inactive hosts";
                }

                leaf-list apply-groups {
                    type leafref {
                        path "../../../../groups/group/name";
                    }
                    max-elements 8;
                    ordered-by user;
                    description "Apply a configuration group at this level";
                }

                leaf-list apply-groups-exclude {
                    type leafref {
                        path "../../../../groups/group/name";
                    }
                    max-elements 8;
                    ordered-by user;
                    description "Exclude a configuration group at this level";
                }

            } // container igmp-host-tracking

            container pcp {
                description "Enter the pcp context";

                list server {
                    key "name";
                    max-elements 8;
                    description "Enter the server list instance";

                    leaf name {
                        type types-sros:named-item;
                        description "PCP server name";
                    }

                    leaf admin-state {
                        type types-sros:admin-state;
                        default "disable";
                        description "Administrative state of the PCP server";
                    }

                    leaf description {
                        type types-sros:description;
                        description "Text description";
                    }

                    leaf dual-stack-lite-address {
                        type types-sros:ipv6-unicast-address;
                        description "Inside Dual Stack Lite AFTR address";
                    }

                    leaf fwd-inside-router {
                        type string;
                        description "PCP forwarding inside virtual router instance";
                    }

                    leaf policy {
                        type leafref {
                            path "../../../../nat/pcp-server-policy/name";
                        }
                        description "PCP server policy";
                    }

                    leaf-list apply-groups {
                        type leafref {
                            path "../../../../../groups/group/name";
                        }
                        max-elements 8;
                        ordered-by user;
                        description "Apply a configuration group at this level";
                    }

                    leaf-list apply-groups-exclude {
                        type leafref {
                            path "../../../../../groups/group/name";
                        }
                        max-elements 8;
                        ordered-by user;
                        description "Exclude a configuration group at this level";
                    }

                    list interface {
                        key "name";
                        max-elements 32;
                        description "Add a list entry for interface";

                        leaf name {
                            type leafref {
                                path "../../../../interface/interface-name";
                            }
                            description "Interface name";
                        }

                    } // list interface

                } // list server

            } // container pcp

            container bgp-vpn-backup {
                description "Enter the bgp-vpn-backup context";

                leaf ipv4 {
                    type boolean;
                    default "false";
                    description "Allow BGP-VPN to be used as backup for IPv4 prefixes";
                }

                leaf ipv6 {
                    type boolean;
                    default "false";
                    description "Allow BGP-VPN to be used as backup for IPv6 prefixes";
                }

            } // container bgp-vpn-backup

            container grt-leaking {
                description "Enter the grt-leaking context";

                leaf export-limit {
                    type uint32 {
                        range "0..1000";
                    }
                    default "5";
                    description "Maximum number of routes exported from VRF to GRT";
                }

                leaf export-v6-limit {
                    type uint32 {
                        range "0..1000";
                    }
                    default "5";
                    description "Maximum number of IPv6 routes exported from VPRN to GRT";
                }

                leaf grt-lookup {
                    type boolean;
                    default "false";
                    description "Enable global route table lookup";
                }

                leaf allow-local-management {
                    type boolean;
                    default "false";
                    description "Enable management traffic";
                }

                leaf-list apply-groups {
                    type leafref {
                        path "../../../../groups/group/name";
                    }
                    max-elements 8;
                    ordered-by user;
                    description "Apply a configuration group at this level";
                }

                leaf-list apply-groups-exclude {
                    type leafref {
                        path "../../../../groups/group/name";
                    }
                    max-elements 8;
                    ordered-by user;
                    description "Exclude a configuration group at this level";
                }

                container export-grt {
                    description "Enter the export-grt context";

                    leaf-list policy-name {
                        type union {
                            type types-sros:policy-expr-string;
                            type string;
                        }
                        max-elements 5;
                        ordered-by user;
                        description "Route policy name or policy logical expression";
                    }

                } // container export-grt

                container import-grt {
                    description "Enter the import-grt context";

                    leaf-list policy-name {
                        type union {
                            type types-sros:policy-expr-string;
                            type string;
                        }
                        max-elements 5;
                        ordered-by user;
                        description "Route policy name or policy logical expression";
                    }

                } // container import-grt

            } // container grt-leaking

            container gsmp {
                description "Enter the gsmp context";

                leaf admin-state {
                    type types-sros:admin-state;
                    default "disable";
                    description "Administrative state of GSMP";
                }

                leaf-list apply-groups {
                    type leafref {
                        path "../../../../groups/group/name";
                    }
                    max-elements 8;
                    ordered-by user;
                    description "Apply a configuration group at this level";
                }

                leaf-list apply-groups-exclude {
                    type leafref {
                        path "../../../../groups/group/name";
                    }
                    max-elements 8;
                    ordered-by user;
                    description "Exclude a configuration group at this level";
                }

                list group {
                    key "name";
                    max-elements 1024;
                    description "Enter the group list instance";

                    leaf name {
                        type types-sros:named-item;
                        description "GSMP group name";
                    }

                    leaf admin-state {
                        type types-sros:admin-state;
                        default "disable";
                        description "Administrative state of the GSMP group";
                    }

                    leaf description {
                        type types-sros:description;
                        description "Text description";
                    }

                    leaf keepalive {
                        type types-sros:time-duration {
                            range "1..25";
                        }
                        units "seconds";
                        default "10";
                        description "Keepalive value for the GSMP connections in this group";
                    }

                    leaf hold-multiplier {
                        type uint32 {
                            range "1..100";
                        }
                        default "3";
                        description "Hold-multiplier for the GSMP connections in this group";
                    }

                    leaf persistency {
                        type boolean;
                        default "false";
                        description "Store DSL line information when the GSMP connection terminates";
                    }

                    leaf idle-filter {
                        type boolean;
                        default "false";
                        description "Filter ANCP messages from IDLE DSL lines";
                    }

                    leaf-list apply-groups {
                        type leafref {
                            path "../../../../../groups/group/name";
                        }
                        max-elements 8;
                        ordered-by user;
                        description "Apply a configuration group at this level";
                    }

                    leaf-list apply-groups-exclude {
                        type leafref {
                            path "../../../../../groups/group/name";
                        }
                        max-elements 8;
                        ordered-by user;
                        description "Exclude a configuration group at this level";
                    }

                    container ancp {
                        description "Enter the ancp context";

                        leaf dynamic-topology-discovery {
                            type boolean;
                            default "true";
                            description "Enable the ANCP dynamic topology discovery capability";
                        }

                        leaf oam {
                            type boolean;
                            default "false";
                            description "Enable GSMP ANCP OAM capability at startup of GSMP connection";
                        }

                    } // container ancp

                    list neighbor {
                        key "remote-address";
                        description "Enter the neighbor list instance";

                        leaf remote-address {
                            type types-sros:ipv4-unicast-address;
                            description "GSMP neighbor remote IP address";
                        }

                        leaf admin-state {
                            type types-sros:admin-state;
                            default "disable";
                            description "Administrative state of the GSMP neighbor";
                        }

                        leaf description {
                            type types-sros:description;
                            description "Text description";
                        }

                        leaf local-address {
                            type types-sros:ipv4-unicast-address;
                            sros-ext:auto-restart-to-modify;
                            description "Restrict connections to this local address only within the service running ANCP";
                        }

                        leaf-list apply-groups {
                            type leafref {
                                path "../../../../../../groups/group/name";
                            }
                            max-elements 8;
                            ordered-by user;
                            sros-ext:auto-restart-to-modify;
                            description "Apply a configuration group at this level";
                        }

                        leaf-list apply-groups-exclude {
                            type leafref {
                                path "../../../../../../groups/group/name";
                            }
                            max-elements 8;
                            ordered-by user;
                            sros-ext:auto-restart-to-modify;
                            description "Exclude a configuration group at this level";
                        }

                        container priority-marking {
                            sros-ext:auto-restart-to-modify;
                            description "Enter the priority-marking context";

                            choice priority-marking {
                                case dscp {

                                    leaf dscp {
                                        type types-qos:dscp-name;
                                        sros-ext:auto-restart-to-modify;
                                        description "DSCP that is used while remarking the in profile packets";
                                    }

                                }
                                case prec {

                                    leaf prec {
                                        type types-qos:precedence-value;
                                        sros-ext:auto-restart-to-modify;
                                        description "Precedence priority marking";
                                    }

                                }
                            }
                        } // container priority-marking

                    } // list neighbor

                } // list group

            } // container gsmp

            container vxlan {
                description "Enter the vxlan context";

                list tunnel-termination {
                    key "ip-address";
                    description "Enter the tunnel-termination list instance";

                    leaf ip-address {
                        type types-sros:ip-unicast-address;
                        description "Non-system IP address that terminates the VXLAN";
                    }

                    leaf fpe-id {
                        type leafref {
                            path "../../../../../fwd-path-ext/fpe/fpe-id";
                        }
                        sros-ext:immutable;
                        mandatory true;
                        description "FPE id for this entry";
                    }

                    leaf-list apply-groups {
                        type leafref {
                            path "../../../../../groups/group/name";
                        }
                        max-elements 8;
                        ordered-by user;
                        description "Apply a configuration group at this level";
                    }

                    leaf-list apply-groups-exclude {
                        type leafref {
                            path "../../../../../groups/group/name";
                        }
                        max-elements 8;
                        ordered-by user;
                        description "Exclude a configuration group at this level";
                    }

                } // list tunnel-termination


            } // container vxlan

            container ttl-propagate {
                description "Enter the ttl-propagate context";

                leaf local {
                    type types-router:vprn-ttl-propagate;
                    default "use-base";
                    description "Local TTL propagation control for the VPRN";
                }

                leaf transit {
                    type types-router:vprn-ttl-propagate;
                    default "use-base";
                    description "Transit TTL propagation control for the VPRN";
                }

            } // container ttl-propagate

            container sgt-qos {
                description "Enter the sgt-qos context";

                container dscp {
                    description "Enter the dscp context";

                    list application {
                        key "dscp-app-name";
                        description "Enter the application list instance";

                        leaf dscp-app-name {
                            type types-router:dscp-app-name-vprn;
                            description "DSCP application ID that generates control traffic";
                        }

                        leaf dscp {
                            type union {
                                type types-qos:dscp-name;
                                type int32 {
                                    range "0..63";
                                }
                            }
                            description "DSCP value to the traffic generated by this application";
                        }

                        leaf-list apply-groups {
                            type leafref {
                                path "../../../../../../groups/group/name";
                            }
                            max-elements 8;
                            ordered-by user;
                            description "Apply a configuration group at this level";
                        }

                        leaf-list apply-groups-exclude {
                            type leafref {
                                path "../../../../../../groups/group/name";
                            }
                            max-elements 8;
                            ordered-by user;
                            description "Exclude a configuration group at this level";
                        }

                    } // list application

                    list dscp-map {
                        key "dscp-name";
                        description "Enter the dscp-map list instance";

                        leaf dscp-name {
                            type types-qos:dscp-name;
                            description "DSCP name mapped to forwarding class";
                        }

                        leaf fc {
                            type types-sros:fc-name;
                            description "Value for the forwarding class for this mapping";
                        }

                        leaf-list apply-groups {
                            type leafref {
                                path "../../../../../../groups/group/name";
                            }
                            max-elements 8;
                            ordered-by user;
                            description "Apply a configuration group at this level";
                        }

                        leaf-list apply-groups-exclude {
                            type leafref {
                                path "../../../../../../groups/group/name";
                            }
                            max-elements 8;
                            ordered-by user;
                            description "Exclude a configuration group at this level";
                        }

                    } // list dscp-map

                } // container dscp

                container dot1p {
                    description "Enter the dot1p context";

                    list application {
                        key "dot1p-app-name";
                        description "Enter the application list instance";

                        leaf dot1p-app-name {
                            type types-router:dot1p-app-name;
                            description "Dot1p application ID that generates control traffic";
                        }

                        leaf dot1p {
                            type union {
                                type types-sros:fc-name;
                                type int32 {
                                    range "0..7";
                                }
                            }
                            description "Dot1p value to the traffic generated by this application";
                        }

                        leaf-list apply-groups {
                            type leafref {
                                path "../../../../../../groups/group/name";
                            }
                            max-elements 8;
                            ordered-by user;
                            description "Apply a configuration group at this level";
                        }

                        leaf-list apply-groups-exclude {
                            type leafref {
                                path "../../../../../../groups/group/name";
                            }
                            max-elements 8;
                            ordered-by user;
                            description "Exclude a configuration group at this level";
                        }

                    } // list application

                } // container dot1p

            } // container sgt-qos

            container snmp {
                description "Enter the snmp context";

                leaf access {
                    type boolean;
                    default "false";
                    description "Enable SNMP access for the VPRN service";
                }

                list community {
                    key "community-string";
                    description "Enter the community list instance";

                    leaf community-string {
                        type types-sros:encrypted-leaf {
                            length "1..114";
                        }
                        description "SNMP v1/v2c community name associated with the VPRN";
                    }

                    leaf access-permissions {
                        type enumeration {
                            enum r                              { value 1; }
                            enum rw                             { value 2; }
                        }
                        mandatory true;
                        description "Access permissions to MIB objects";
                    }

                    leaf version {
                        type enumeration {
                            enum v1                             { value 1; }
                            enum v2c                            { value 2; }
                            enum both                           { value 3; }
                        }
                        default "both";
                        description "SNMP version";
                    }

                    leaf source-access-list {
                        type leafref {
                            path "../../../../../system/security/snmp/source-access-list/list-name";
                        }
                        description "List name used to validate the source IP address";
                    }

                    leaf-list apply-groups {
                        type leafref {
                            path "../../../../../groups/group/name";
                        }
                        max-elements 8;
                        ordered-by user;
                        description "Apply a configuration group at this level";
                    }

                    leaf-list apply-groups-exclude {
                        type leafref {
                            path "../../../../../groups/group/name";
                        }
                        max-elements 8;
                        ordered-by user;
                        description "Exclude a configuration group at this level";
                    }

                } // list community

            } // container snmp

            container network {
                description "Enter the network context";

                leaf-list apply-groups {
                    type leafref {
                        path "../../../../groups/group/name";
                    }
                    max-elements 8;
                    ordered-by user;
                    description "Apply a configuration group at this level";
                }

                leaf-list apply-groups-exclude {
                    type leafref {
                        path "../../../../groups/group/name";
                    }
                    max-elements 8;
                    ordered-by user;
                    description "Exclude a configuration group at this level";
                }

                container ingress {
                    description "Enter the ingress context";

                    leaf urpf-check {
                        type boolean;
                        default "true";
                        description "Enable unicast RPF check of network ingress traffic";
                    }

                    leaf classification-override {
                        type leafref {
                            path "../../../../../qos/ingress-classification-policy/ingress-classification-policy-name";
                        }
                        description "Short-pipe mode for CoS propagation";
                    }

                    container qos {
                        description "Enter the qos context";

                        leaf network-policy {
                            type leafref {
                                path "../../../../../../qos/network/network-policy-name";
                            }
                            description "Network policy name associated with a VPRN";
                        }

                        leaf fp-redirect-group {
                            type leafref {
                                path "../../../../../../qos/queue-group-templates/ingress/queue-group/ingress-queue-group-name";
                            }
                            description "The forwarding-plane queue group Policy for this VPRN";
                        }

                        leaf instance {
                            type types-services:qos-qgrp-instance-id;
                            description "Forwarding plane ingress queue group instance";
                        }

                    } // container qos

                    container filter {
                        description "Enter the filter context";

                        leaf ip {
                            type leafref {
                                path "../../../../../../filter/ip-filter/filter-name";
                            }
                            description "IPv4 filter policy name";
                        }

                        leaf ipv6 {
                            type leafref {
                                path "../../../../../../filter/ipv6-filter/filter-name";
                            }
                            description "IPv6 filter policy name";
                        }

                    } // container filter

                } // container ingress

            } // container network

            container management {
                presence "Enable the management context";
                description "Enable the management context";

                leaf allow-telnet {
                    type boolean;
                    default "false";
                    description "Allow access to the IPv4 Telnet server";
                }

                leaf allow-telnet6 {
                    type boolean;
                    default "false";
                    description "Allow access to the Telnet IPv6 server";
                }

                leaf allow-ftp {
                    type boolean;
                    default "false";
                    description "Allow access to the FTP server";
                }

                leaf allow-ssh {
                    type boolean;
                    default "false";
                    description "Allow access to the SSH server";
                }

                leaf allow-netconf {
                    type boolean;
                    default "false";
                    description "Allow access to the NETCONF server";
                }

                leaf allow-grpc {
                    type boolean;
                    default "false";
                    description "Allow access to the gRPC server";
                }

                leaf-list apply-groups {
                    type leafref {
                        path "../../../../groups/group/name";
                    }
                    max-elements 8;
                    ordered-by user;
                    description "Apply a configuration group at this level";
                }

                leaf-list apply-groups-exclude {
                    type leafref {
                        path "../../../../groups/group/name";
                    }
                    max-elements 8;
                    ordered-by user;
                    description "Exclude a configuration group at this level";
                }

            } // container management

            uses conf-svc-vprn-dhcp-server;
            uses conf-svc-vprn-isis;
            uses conf-svc-vprn-msdp;
            uses conf-svc-vprn-ospf;
            uses conf-svc-vprn-ospf3;
            uses conf-svc-vprn-radius;
            uses conf-svc-vprn-rip;
            uses conf-svc-vprn-ripng;
            uses conf-svc-vprn-sub-if-subscriber-interface;
            uses conf-svc-vprn-twamp-light;
            uses conf-svc-vprn-vdo-if-video-interface;
        } // list vprn

    } // grouping conf-svc-vprn

}
