submodule nokia-conf-router-mpls {

    yang-version "1.1";

    belongs-to nokia-conf { prefix "conf"; }

    import nokia-sros-yang-extensions     { prefix "sros-ext"; }
    import nokia-types-mpls               { prefix "types-mpls"; }
    import nokia-types-sros               { prefix "types-sros"; }

    include nokia-conf-bfd;
    include nokia-conf-groups;
    include nokia-conf-log;
    include nokia-conf-policy-options;
    include nokia-conf-router;
    include nokia-conf-router-pcep;
    include nokia-conf-routing-options;

    sros-ext:sros-major-release "rel24";
    organization "Nokia";
    contact
        "Nokia SR OS Support
         Web: <http://www.nokia.com>";
    description
        "Nokia YANG Data model to configure mpls protocol on SR OS based routers.

         Copyright 2016 Nokia. All rights reserved. Reproduction of this document
         is authorized on the condition that the foregoing copyright notice is included.

         This nokia-conf-router-mpls YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";
    revision "2019-07-08";

    grouping conf-router-mpls {
        container mpls {
            presence "Enable the mpls context";
            description "Enable the mpls context";

            leaf admin-group-frr {
                type boolean;
                default "false";
                description "Use admin group constraints for FRR path computation";
            }

            leaf admin-state {
                type types-sros:admin-state;
                default "disable";
                description "Administrative state of the MPLS instance";
            }

            leaf bypass-resignal-timer {
                type uint32 {
                    range "1..10080";
                }
                units "minutes";
                description "Resignal timer for bypass";
            }

            leaf cspf-on-loose-hop {
                type boolean;
                default "false";
                description "Calculate CSPF until next loose hop on LSR";
            }

            leaf dynamic-bypass {
                type boolean;
                default "true";
                description "Create dynamic bypass LSPs in FRR";
            }

            leaf exponential-backoff-retry {
                type boolean;
                default "false";
                description "Use exponential back-off timer when retrying an LSP";
            }

            leaf frr-object {
                type boolean;
                default "true";
                description "Signal with fast reroute object";
            }

            leaf hold-timer {
                type uint32 {
                    range "0..1000";
                }
                units "seconds";
                default "1";
                description "Hold timer value";
            }

            leaf least-fill-min-thd {
                type types-sros:percent;
                default "5";
                description "Percentage of the least fill minimum threshold value";
            }

            leaf least-fill-reoptim-thd {
                type types-sros:percent;
                default "10";
                description "Percentage of the least fill reoptimization threshold value";
            }

            leaf logger-event-bundling {
                type boolean;
                sros-ext:auto-restart-to-modify;
                default "false";
                description "Merge and bundle MPLS traps";
            }

            leaf lsp-bsid-block {
                type leafref {
                    path "../../../router/mpls-labels/reserved-label-block/label-block-name";
                }
                sros-ext:auto-restart-to-modify;
                description "Reserved label block for binding SIDs";
            }

            leaf lsp-init-retry-timeout {
                type uint32 {
                    range "10..600";
                }
                units "seconds";
                default "30";
                description "LSP initial retry timeout";
            }

            leaf max-bypass-associations {
                type uint32 {
                    range "100..131072";
                }
                default "1000";
                description "Maximum number of LSPs associated with a bypass tunnel";
            }

            leaf max-bypass-plr-associations {
                type uint32 {
                    range "1..16";
                }
                default "16";
                description "Maximum number of PLRs per RSVP-TE bypass LSP";
            }

            leaf mbb-prefer-current-hops {
                type boolean;
                default "false";
                description "Select preference to use the current hops for Make-Before-Break (MBB)";
            }

            leaf p2mp-resignal-timer {
                type uint32 {
                    range "60..10080";
                }
                units "minutes";
                description "Resignal timer for P2MP LSPs";
            }

            leaf p2mp-s2l-fast-retry {
                type uint32 {
                    range "1..10";
                }
                units "seconds";
                description "Fast retry timer for P2MP S2L paths";
            }

            leaf p2p-active-path-fast-retry {
                type uint32 {
                    range "1..10";
                }
                units "seconds";
                description "Fast retry timer for P2P active paths";
            }

            leaf resignal-timer {
                type uint32 {
                    range "30..10080";
                }
                units "minutes";
                description "Resignal timer for RSVP LSPs";
            }

            leaf retry-on-igp-overload {
                type boolean;
                default "false";
                description "Tear down LSPs when IGP is in overload state";
            }

            leaf secondary-fast-retry-timer {
                type uint32 {
                    range "1..10";
                }
                units "seconds";
                description "Fast retry timer for secondary paths";
            }

            leaf shortcut-local-ttl-propagate {
                type boolean;
                default "true";
                description "Propagate TTL over LSP shortcut for local packets";
            }

            leaf shortcut-transit-ttl-propagate {
                type boolean;
                default "true";
                description "Propagate TTL over LSP shortcut for local packets for transit packets";
            }

            leaf srlg-frr {
                type enumeration {
                    enum loose                          { value 1; }
                    enum strict                         { value 2; }
                }
                description "Use of SRLG constraint for FRR path computation";
            }

            leaf static-lsp-fast-retry {
                type uint32 {
                    range "1..30";
                }
                units "seconds";
                default "30";
                description "Fast retry timer for static LSPs";
            }

            leaf user-srlg-db {
                type boolean;
                default "false";
                description "Enable the use of user SRLG database";
            }

            leaf resignal-on-igp-overload {
                type boolean;
                default "false";
                description "Resignal all RSVP-TE LSPs upon IGP overload";
            }

            leaf strict-ero-nhop-direct-resolution {
                type boolean;
                default "false";
                description "Resolves RSVP-TE LSP ERO to local and host routes only";
            }

            leaf p2mp-ttl-propagate {
                type boolean;
                default "true";
                description "Use uniform mode for TTL propagation for RSVP P2MP LSPs";
            }

            leaf-list apply-groups {
                type leafref {
                    path "../../../groups/group/name";
                }
                max-elements 8;
                ordered-by user;
                description "Apply a configuration group at this level";
            }

            leaf-list apply-groups-exclude {
                type leafref {
                    path "../../../groups/group/name";
                }
                max-elements 8;
                ordered-by user;
                description "Exclude a configuration group at this level";
            }

            container lsp-self-ping {
                description "Enter the lsp-self-ping context";

                leaf interval {
                    type uint32 {
                        range "1..10";
                    }
                    units "seconds";
                    default "1";
                    description "MPLS periodic LSP Self Ping interval";
                }

                leaf rsvp-te {
                    type boolean;
                    default "false";
                    description "Activate LSP Self Ping on RSVP-TE LSPs";
                }

                leaf timeout {
                    type uint32 {
                        range "3..3600";
                    }
                    units "seconds";
                    default "300";
                    description "MPLS LSP Self Ping timeout";
                }

                leaf timeout-action {
                    type enumeration {
                        enum retry                          { value 1; }
                        enum switch                         { value 2; }
                    }
                    default "retry";
                    description "Action taken when LSP Self Ping timer expires";
                }

            } // container lsp-self-ping

            container auto-bandwidth-multipliers {
                description "Enter the auto-bandwidth-multipliers context";

                leaf sample-multiplier {
                    type uint32 {
                        range "1..511";
                    }
                    default "1";
                    description "Collection intervals in a sample interval";
                }

                leaf adjust-multiplier {
                    type uint32 {
                        range "1..16383";
                    }
                    default "288";
                    description "Collection intervals in a sample interval";
                }

            } // container auto-bandwidth-multipliers

            container entropy-label {
                description "Enter the entropy-label context";

                leaf rsvp-te {
                    type boolean;
                    description "Apply entropy labels to RSVP-TE LSPs";
                }

                leaf sr-te {
                    type boolean;
                    description "Apply entropy labels to SR-TE LSPs";
                }

            } // container entropy-label

            container pce-report {
                description "Enter the pce-report context";

                leaf sr-te {
                    type boolean;
                    default "false";
                    description "Allow PCE reporting for all TE LSPs of SR-TE type";
                }

                leaf rsvp-te {
                    type boolean;
                    default "false";
                    description "Allow PCE reporting for all TE LSPs of RSVP-TE type";
                }

            } // container pce-report

            container srlg-database {
                description "Enter the srlg-database context";

                list router-id {
                    key "router-address";
                    description "Enter the router-id list instance";

                    leaf router-address {
                        type types-sros:ipv4-address;
                        description "Router ID for the system";
                    }

                    leaf admin-state {
                        type types-sros:admin-state;
                        default "disable";
                        description "Administrative state of the interface entry";
                    }

                    leaf-list apply-groups {
                        type leafref {
                            path "../../../../../groups/group/name";
                        }
                        max-elements 8;
                        ordered-by user;
                        description "Apply a configuration group at this level";
                    }

                    leaf-list apply-groups-exclude {
                        type leafref {
                            path "../../../../../groups/group/name";
                        }
                        max-elements 8;
                        ordered-by user;
                        description "Exclude a configuration group at this level";
                    }

                    list interface {
                        key "interface-address srlg-group";
                        description "Add a list entry for interface";

                        leaf interface-address {
                            type types-sros:ipv4-address;
                            description "IP address of the interface";
                        }

                        leaf srlg-group {
                            type leafref {
                                path "../../../../../../routing-options/if-attribute/srlg-group/name";
                            }
                            description "SRLG group name";
                        }

                    } // list interface

                } // list router-id

            } // container srlg-database

            container tunnel-table-pref {
                description "Enter the tunnel-table-pref context";

                leaf rsvp-te {
                    type uint32 {
                        range "1..255";
                    }
                    default "7";
                    description "RSVP-TE tunnel table preference";
                }

                leaf sr-te {
                    type uint32 {
                        range "1..255";
                    }
                    default "8";
                    description "SR-TE tunnel table preference";
                }

            } // container tunnel-table-pref

            list interface {
                key "interface-name";
                description "Enter the interface list instance";

                leaf interface-name {
                    type leafref {
                        path "../../../interface/interface-name";
                    }
                    description "Router interface name";
                }

                leaf admin-state {
                    type types-sros:admin-state;
                    default "enable";
                    description "Administrative state of the MPLS interface";
                }

                leaf te-metric {
                    type uint32 {
                        range "1..16777215";
                    }
                    description "TE metric for the interface";
                }

                leaf-list admin-group {
                    type leafref {
                        path "../../../../routing-options/if-attribute/admin-group/group-name";
                    }
                    max-elements 32;
                    description "Administrative groups supported by the interface";
                }

                leaf-list apply-groups {
                    type leafref {
                        path "../../../../groups/group/name";
                    }
                    max-elements 8;
                    ordered-by user;
                    description "Apply a configuration group at this level";
                }

                leaf-list apply-groups-exclude {
                    type leafref {
                        path "../../../../groups/group/name";
                    }
                    max-elements 8;
                    ordered-by user;
                    description "Exclude a configuration group at this level";
                }

                list srlg-group {
                    key "name";
                    max-elements 64;
                    description "Add a list entry for srlg-group";

                    leaf name {
                        type leafref {
                            path "../../../../../routing-options/if-attribute/srlg-group/name";
                        }
                        description "Shared Risk Link Group (SRLG) name";
                    }

                } // list srlg-group

                list label-map {
                    key "in-label";
                    description "Enter the label-map list instance";

                    leaf in-label {
                        type types-sros:mpls-label;
                        description "Match the incoming MPLS label";
                    }

                    leaf admin-state {
                        type types-sros:admin-state;
                        default "disable";
                        description "Administrative state of the label map";
                    }

                    leaf-list apply-groups {
                        type leafref {
                            path "../../../../../groups/group/name";
                        }
                        max-elements 8;
                        ordered-by user;
                        sros-ext:auto-restart-to-modify;
                        description "Apply a configuration group at this level";
                    }

                    leaf-list apply-groups-exclude {
                        type leafref {
                            path "../../../../../groups/group/name";
                        }
                        max-elements 8;
                        ordered-by user;
                        sros-ext:auto-restart-to-modify;
                        description "Exclude a configuration group at this level";
                    }

                    choice label-map-choice {
                        case pop {

                            leaf pop {
                                type empty;
                                sros-ext:immutable;
                                sros-ext:auto-restart-to-modify;
                                description "Pop (remove) the incoming label and forward packet based on service header";
                            }

                        }
                        case swap {

                            container swap {
                                presence "Enable the swap context";
                                description "Enable the swap context";

                                leaf out-label {
                                    type union {
                                        type uint32 {
                                            range "16..1048575";
                                        }
                                        type enumeration {
                                            enum implicit-null-label            { value 3; }
                                        }
                                    }
                                    mandatory true;
                                    description "Push specific label onto the top of the outgoing packet's label stack";
                                }

                                leaf next-hop {
                                    type types-sros:ipv4-unicast-address;
                                    mandatory true;
                                    description "IP address for the next hop";
                                }

                                leaf-list apply-groups {
                                    type leafref {
                                        path "../../../../../../groups/group/name";
                                    }
                                    max-elements 8;
                                    ordered-by user;
                                    description "Apply a configuration group at this level";
                                }

                                leaf-list apply-groups-exclude {
                                    type leafref {
                                        path "../../../../../../groups/group/name";
                                    }
                                    max-elements 8;
                                    ordered-by user;
                                    description "Exclude a configuration group at this level";
                                }

                            } // container swap

                        }
                    }
                } // list label-map

            } // list interface

            list class-forwarding-policy {
                key "policy-name";
                max-elements 15;
                description "Enter the class-forwarding-policy list instance";

                leaf policy-name {
                    type types-sros:named-item;
                    description "Name of class forwarding policy";
                }

                leaf default-set {
                    type uint32 {
                        range "1..6";
                    }
                    default "1";
                    description "Default forwarding set ID";
                }

                leaf-list apply-groups {
                    type leafref {
                        path "../../../../groups/group/name";
                    }
                    max-elements 8;
                    ordered-by user;
                    description "Apply a configuration group at this level";
                }

                leaf-list apply-groups-exclude {
                    type leafref {
                        path "../../../../groups/group/name";
                    }
                    max-elements 8;
                    ordered-by user;
                    description "Exclude a configuration group at this level";
                }

                list fc {
                    key "fc-name";
                    description "Enter the fc list instance";

                    leaf fc-name {
                        type types-sros:fc-name;
                        description "Forwarding class name for LSP";
                    }

                    leaf forwarding-set {
                        type uint32 {
                            range "1..6";
                        }
                        default "1";
                        description "Forwarding set ID for forwarding classes";
                    }

                    leaf-list apply-groups {
                        type leafref {
                            path "../../../../../groups/group/name";
                        }
                        max-elements 8;
                        ordered-by user;
                        description "Apply a configuration group at this level";
                    }

                    leaf-list apply-groups-exclude {
                        type leafref {
                            path "../../../../../groups/group/name";
                        }
                        max-elements 8;
                        ordered-by user;
                        description "Exclude a configuration group at this level";
                    }

                } // list fc

            } // list class-forwarding-policy

            list path {
                key "path-name";
                max-elements 65535;
                description "Enter the path list instance";

                leaf path-name {
                    type types-sros:named-item-64;
                    description "Name for this LSP path";
                }

                leaf admin-state {
                    type types-sros:admin-state;
                    default "disable";
                    description "Administrative state of the path used for LSPs";
                }

                leaf-list apply-groups {
                    type leafref {
                        path "../../../../groups/group/name";
                    }
                    max-elements 8;
                    ordered-by user;
                    sros-ext:auto-restart-to-modify;
                    description "Apply a configuration group at this level";
                }

                leaf-list apply-groups-exclude {
                    type leafref {
                        path "../../../../groups/group/name";
                    }
                    max-elements 8;
                    ordered-by user;
                    sros-ext:auto-restart-to-modify;
                    description "Exclude a configuration group at this level";
                }

                list hop {
                    key "hop-index";
                    max-elements 255;
                    description "Enter the hop list instance";

                    leaf hop-index {
                        type int32 {
                            range "1..1024";
                        }
                        description "Index to identify a particular hop";
                    }

                    leaf-list apply-groups {
                        type leafref {
                            path "../../../../../groups/group/name";
                        }
                        max-elements 8;
                        ordered-by user;
                        description "Apply a configuration group at this level";
                    }

                    leaf-list apply-groups-exclude {
                        type leafref {
                            path "../../../../../groups/group/name";
                        }
                        max-elements 8;
                        ordered-by user;
                        description "Exclude a configuration group at this level";
                    }

                    choice hop-info {
                        mandatory true;
                        case hop-ip-address {

                            leaf ip-address {
                                type types-sros:ip-address;
                                sros-ext:immutable;
                                description "IP address of the transit router";
                            }

                            leaf type {
                                type enumeration {
                                    enum strict                         { value 1; }
                                    enum loose                          { value 2; }
                                }
                                description "Tunnel hop type";
                            }

                        }
                        case hop-sid {

                            leaf sid-label {
                                type uint32 {
                                    range "32..1048575";
                                }
                                description "MPLS label for tunnel hop in the path of an SR-TE LSP";
                            }

                        }
                    }
                } // list hop

            } // list path

            list lsp-template {
                key "template-name";
                max-elements 4096;
                description "Enter the lsp-template list instance";

                leaf template-name {
                    type types-sros:named-item;
                    description "LSP template name";
                }

                leaf type {
                    type enumeration {
                        enum p2mp-rsvp                      { value 1; }
                        enum p2p-rsvp-one-hop               { value 2; }
                        enum p2p-rsvp-mesh                  { value 3; }
                        enum p2p-sr-te-one-hop              { value 4; }
                        enum p2p-sr-te-mesh                 { value 5; }
                        enum p2p-sr-te-pce-init             { value 6; }
                        enum p2p-sr-te-on-demand            { value 8; }
                    }
                    sros-ext:immutable;
                    sros-ext:auto-restart-to-modify;
                    mandatory true;
                    description "LSP template type";
                }

                leaf admin-state {
                    type types-sros:admin-state;
                    default "disable";
                    description "Administrative state of the LSP template";
                }

                leaf backup-class-type {
                    when "not(../type) or ../type = 'p2p-rsvp-one-hop' or ../type = 'p2p-rsvp-mesh'" {
                        description "not allowed for this LSP template type";
                    }
                    type types-mpls:class-type;
                    sros-ext:auto-restart-to-modify;
                    default "0";
                    description "Backup class type for this LSP template";
                }

                leaf bandwidth {
                    when "not(../type) or ../type = 'p2mp-rsvp' or ../type = 'p2p-rsvp-one-hop' or ../type = 'p2p-rsvp-mesh'" {
                        description "not allowed for this LSP template type";
                    }
                    type types-mpls:lsp-bandwidth;
                    default "0";
                    description "Amount of bandwidth reserved for the P2MP instance";
                }

                leaf bgp-shortcut {
                    when "not(../type) or ../type = 'p2p-rsvp-one-hop' or ../type = 'p2p-rsvp-mesh' or ../type = 'p2p-sr-te-one-hop' or ../type = 'p2p-sr-te-mesh' or ../type = 'p2p-sr-te-pce-init' or ../type = 'p2p-sr-te-on-demand'" {
                        description "not allowed for this LSP template type";
                    }
                    type boolean;
                    sros-ext:auto-restart-to-modify;
                    description "Enable/disable use of RSVP LSP for IPv4 BGP routes.";
                }

                leaf bgp-transport-tunnel {
                    when "not(../type) or ../type = 'p2p-rsvp-one-hop' or ../type = 'p2p-rsvp-mesh' or ../type = 'p2p-sr-te-one-hop' or ../type = 'p2p-sr-te-mesh' or ../type = 'p2p-sr-te-pce-init' or ../type = 'p2p-sr-te-on-demand'" {
                        description "not allowed for this LSP template type";
                    }
                    type boolean;
                    sros-ext:auto-restart-to-modify;
                    default "true";
                    description "Allow use of RSVP-TE LSP as transport for tunnel routes";
                }

                leaf binding-sid {
                    when "not(../type) or ../type = 'p2p-sr-te-on-demand'" {
                        description "not allowed for this LSP template type";
                    }
                    type boolean;
                    sros-ext:auto-restart-to-modify;
                    default "false";
                    description "Request to allocate and bind a label";
                }

                leaf default-path {
                    when "not(../type) or ../type = 'p2mp-rsvp' or ../type = 'p2p-rsvp-one-hop' or ../type = 'p2p-rsvp-mesh' or ../type = 'p2p-sr-te-one-hop' or ../type = 'p2p-sr-te-mesh' or ../type = 'p2p-sr-te-pce-init' or ../type = 'p2p-sr-te-on-demand'" {
                        description "not allowed for this LSP template type";
                    }
                    type leafref {
                        path "../../path/path-name";
                    }
                    sros-ext:immutable;
                    sros-ext:auto-restart-to-modify;
                    description "Default path to be used for signaling LSP instances";
                }

                leaf from {
                    when "not(../type) or ../type = 'p2p-rsvp-mesh' or ../type = 'p2p-sr-te-mesh' or ../type = 'p2p-sr-te-on-demand'" {
                        description "not allowed for this LSP template type";
                    }
                    type types-sros:ip-address;
                    sros-ext:auto-restart-to-modify;
                    description "IP address of the ingress router for the LSP template";
                }

                leaf hop-limit {
                    when "not(../type) or ../type = 'p2mp-rsvp' or ../type = 'p2p-rsvp-one-hop' or ../type = 'p2p-rsvp-mesh' or ../type = 'p2p-sr-te-one-hop' or ../type = 'p2p-sr-te-mesh' or ../type = 'p2p-sr-te-on-demand'" {
                        description "not allowed for this LSP template type";
                    }
                    type uint16 {
                        range "2..255";
                    }
                    sros-ext:auto-restart-to-modify;
                    description "Maximum hops for an LSP created using this LSP template";
                }

                leaf ldp-over-rsvp {
                    when "not(../type) or ../type = 'p2p-rsvp-one-hop' or ../type = 'p2p-rsvp-mesh'" {
                        description "not allowed for this LSP template type";
                    }
                    type boolean;
                    sros-ext:auto-restart-to-modify;
                    default "true";
                    description "Include this LSP in LDP over RSVP";
                }

                leaf metric {
                    when "not(../type) or ../type = 'p2p-rsvp-one-hop' or ../type = 'p2p-rsvp-mesh' or ../type = 'p2p-sr-te-one-hop' or ../type = 'p2p-sr-te-mesh' or ../type = 'p2p-sr-te-pce-init' or ../type = 'p2p-sr-te-on-demand'" {
                        description "not allowed for this LSP template type";
                    }
                    type uint32 {
                        range "0..16777215";
                    }
                    sros-ext:auto-restart-to-modify;
                    default "0";
                    description "LSP template metric";
                }

                leaf vprn-auto-bind {
                    when "not(../type) or ../type = 'p2p-rsvp-one-hop' or ../type = 'p2p-rsvp-mesh' or ../type = 'p2p-sr-te-one-hop' or ../type = 'p2p-sr-te-mesh' or ../type = 'p2p-sr-te-pce-init' or ../type = 'p2p-sr-te-on-demand'" {
                        description "not allowed for this LSP template type";
                    }
                    type boolean;
                    sros-ext:auto-restart-to-modify;
                    default "true";
                    description "Include LSP template in auto-bind for VPRN services";
                }

                leaf pce-report {
                    when "not(../type) or ../type = 'p2p-rsvp-one-hop' or ../type = 'p2p-rsvp-mesh' or ../type = 'p2p-sr-te-one-hop' or ../type = 'p2p-sr-te-mesh' or ../type = 'p2p-sr-te-pce-init' or ../type = 'p2p-sr-te-on-demand'" {
                        description "not allowed for this LSP template type";
                    }
                    type types-sros:bool-with-inherit;
                    sros-ext:auto-restart-to-modify;
                    description "Enable reporting modes to PCE for RSVP-TE or SR-TE LSPs";
                }

                leaf entropy-label {
                    when "not(../type) or ../type = 'p2p-rsvp-one-hop' or ../type = 'p2p-rsvp-mesh' or ../type = 'p2p-sr-te-one-hop' or ../type = 'p2p-sr-te-mesh' or ../type = 'p2p-sr-te-pce-init' or ../type = 'p2p-sr-te-on-demand'" {
                        description "not allowed for this LSP template type";
                    }
                    type types-sros:bool-with-inherit;
                    sros-ext:auto-restart-to-modify;
                    description "Entropy label for an LSP template";
                }

                leaf override-tunnel-elc {
                    when "../type = 'p2p-sr-te-pce-init' or ../type = 'p2p-sr-te-on-demand'" {
                        description "not allowed for this LSP type";
                    }
                    type boolean;
                    sros-ext:auto-restart-to-modify;
                    default "false";
                    description "Override any received entropy label capability";
                }

                leaf adaptive {
                    when "not(../type) or ../type = 'p2mp-rsvp' or ../type = 'p2p-rsvp-one-hop' or ../type = 'p2p-rsvp-mesh'" {
                        description "not allowed for this LSP template type";
                    }
                    type boolean;
                    sros-ext:auto-restart-to-modify;
                    default "true";
                    description "Enable make-before-break functionality";
                }

                leaf adspec {
                    when "not(../type) or ../type = 'p2p-rsvp-one-hop' or ../type = 'p2p-rsvp-mesh'" {
                        description "not allowed for this LSP template type";
                    }
                    type boolean;
                    sros-ext:auto-restart-to-modify;
                    default "false";
                    description "Include ADSPEC objects in RSVP messages";
                }

                leaf class-type {
                    when "not(../type) or ../type = 'p2p-rsvp-one-hop' or ../type = 'p2p-rsvp-mesh'" {
                        description "not allowed for this LSP template type";
                    }
                    type types-mpls:class-type;
                    sros-ext:auto-restart-to-modify;
                    default "0";
                    description "Class type for an LSP template";
                }

                leaf least-fill {
                    when "not(../type) or ../type = 'p2p-rsvp-one-hop' or ../type = 'p2p-rsvp-mesh'" {
                        description "not allowed for this LSP template type";
                    }
                    type boolean;
                    sros-ext:auto-restart-to-modify;
                    default "false";
                    description "Enable least-fill path selection for this LSP template";
                }

                leaf load-balancing-weight {
                    when "not(../type) or ../type = 'p2p-rsvp-one-hop' or ../type = 'p2p-rsvp-mesh' or ../type = 'p2p-sr-te-one-hop' or ../type = 'p2p-sr-te-mesh' or ../type = 'p2p-sr-te-pce-init' or ../type = 'p2p-sr-te-on-demand'" {
                        description "not allowed for this LSP template type";
                    }
                    type uint32 {
                        range "1..max";
                    }
                    sros-ext:auto-restart-to-modify;
                    description "Load balancing weight for an MPLS LSP template";
                }

                leaf main-ct-retry-limit {
                    when "not(../type) or ../type = 'p2p-rsvp-one-hop' or ../type = 'p2p-rsvp-mesh'" {
                        description "not allowed for this LSP template type";
                    }
                    type uint32 {
                        range "1..10000";
                    }
                    sros-ext:auto-restart-to-modify;
                    description "Maximum number of retries before reverting to backup CT";
                }

                leaf propagate-admin-group {
                    when "not(../type) or ../type = 'p2mp-rsvp' or ../type = 'p2p-rsvp-one-hop' or ../type = 'p2p-rsvp-mesh'" {
                        description "not allowed for this LSP template type";
                    }
                    type boolean;
                    sros-ext:auto-restart-to-modify;
                    default "false";
                    description "Enable admin groups via session attribute object";
                }

                leaf retry-limit {
                    when "not(../type) or ../type = 'p2mp-rsvp' or ../type = 'p2p-rsvp-one-hop' or ../type = 'p2p-rsvp-mesh' or ../type = 'p2p-sr-te-one-hop' or ../type = 'p2p-sr-te-mesh' or ../type = 'p2p-sr-te-on-demand'" {
                        description "not allowed for this LSP template type";
                    }
                    type uint32 {
                        range "1..10000";
                    }
                    sros-ext:auto-restart-to-modify;
                    description "Number of attempts to re-establish LSP after it fails";
                }

                leaf retry-timer {
                    when "not(../type) or ../type = 'p2mp-rsvp' or ../type = 'p2p-rsvp-one-hop' or ../type = 'p2p-rsvp-mesh' or ../type = 'p2p-sr-te-one-hop' or ../type = 'p2p-sr-te-mesh' or ../type = 'p2p-sr-te-on-demand'" {
                        description "not allowed for this LSP template type";
                    }
                    type uint32 {
                        range "1..600";
                    }
                    units "seconds";
                    sros-ext:auto-restart-to-modify;
                    default "30";
                    description "Time for LSP re-establishment attempts after failure";
                }

                leaf record {
                    when "not(../type) or ../type = 'p2mp-rsvp' or ../type = 'p2p-rsvp-one-hop' or ../type = 'p2p-rsvp-mesh'" {
                        description "not allowed for this LSP template type";
                    }
                    type boolean;
                    sros-ext:auto-restart-to-modify;
                    default "true";
                    description "Enable recording of all hops for this LSP template";
                }

                leaf record-label {
                    when "not(../type) or ../type = 'p2mp-rsvp' or ../type = 'p2p-rsvp-one-hop' or ../type = 'p2p-rsvp-mesh'" {
                        description "not allowed for this LSP template type";
                    }
                    type boolean;
                    sros-ext:auto-restart-to-modify;
                    default "true";
                    description "Enable recording of labels at each node or instance";
                }

                leaf template-id {
                    when "not(../type) or ../type = 'p2p-sr-te-pce-init'" {
                        description "not allowed for this LSP template type";
                    }
                    type union {
                        type uint32 {
                            range "1..max";
                        }
                        type enumeration {
                            enum default                        { value 0; }
                        }
                    }
                    sros-ext:immutable;
                    sros-ext:auto-restart-to-modify;
                    description "Template ID";
                }

                leaf path-computation-method {
                    when "not(../type) or ../type = 'p2mp-rsvp' or ../type = 'p2p-rsvp-one-hop' or ../type = 'p2p-rsvp-mesh' or ../type = 'p2p-sr-te-one-hop' or ../type = 'p2p-sr-te-mesh' or ../type = 'p2p-sr-te-on-demand'" {
                        description "not allowed for this LSP template type";
                    }
                    type enumeration {
                        enum local-cspf                     { value 2; }
                        enum pce                            { value 3; }
                    }
                    sros-ext:auto-restart-to-modify;
                    description "Path computation method";
                }

                leaf family {
                    when "not(../type) or ../type = 'p2p-sr-te-one-hop' or ../type = 'p2p-sr-te-mesh' or ../type = 'p2p-sr-te-on-demand'" {
                        description "not allowed for this LSP template type";
                    }
                    type enumeration {
                        enum ipv4                           { value 1; }
                        enum ipv6                           { value 2; }
                    }
                    sros-ext:auto-restart-to-modify;
                    default "ipv4";
                    description "Address family that specifies template use in SR-TE LSP";
                }

                leaf metric-type {
                    when "not(../type) or ../type = 'p2mp-rsvp' or ../type = 'p2p-rsvp-one-hop' or ../type = 'p2p-rsvp-mesh' or ../type = 'p2p-sr-te-one-hop' or ../type = 'p2p-sr-te-mesh' or ../type = 'p2p-sr-te-on-demand'" {
                        description "not allowed for this LSP template type";
                    }
                    type enumeration {
                        enum igp                            { value 1; }
                        enum te                             { value 2; }
                    }
                    sros-ext:auto-restart-to-modify;
                    default "igp";
                    description "Metric type used for LSP path computation";
                }

                leaf local-sr-protection {
                    when "not(../type) or ../type = 'p2p-sr-te-one-hop' or ../type = 'p2p-sr-te-mesh' or ../type = 'p2p-sr-te-on-demand'" {
                        description "not allowed for this LSP template type";
                    }
                    type enumeration {
                        enum none                           { value 1; }
                        enum preferred                      { value 2; }
                        enum mandatory                      { value 3; }
                    }
                    sros-ext:auto-restart-to-modify;
                    default "preferred";
                    description "Local SR protection preference for LSP path computation";
                }

                leaf label-stack-reduction {
                    when "not(../type) or ../type = 'p2p-sr-te-one-hop' or ../type = 'p2p-sr-te-mesh' or ../type = 'p2p-sr-te-on-demand'" {
                        description "not allowed for this LSP template type";
                    }
                    type boolean;
                    sros-ext:auto-restart-to-modify;
                    default "false";
                    description "Enable label compression for LSP path";
                }

                leaf lsp-self-ping {
                    when "not(../type) or ../type = 'p2p-rsvp-one-hop' or ../type = 'p2p-rsvp-mesh'" {
                        description "not allowed for this LSP template type";
                    }
                    type types-sros:bool-with-inherit;
                    sros-ext:auto-restart-to-modify;
                    description "LSP Self Ping activation status on RSVP-TE LSP template";
                }

                leaf pce-control {
                    when "not(../type) or ../type = 'p2p-sr-te-on-demand'" {
                        description "not allowed for this LSP template type";
                    }
                    type boolean;
                    sros-ext:auto-restart-to-modify;
                    default "false";
                    description "Enable PCE controlled LSP mode of operation";
                }

                leaf fallback-path-computation-method {
                    when "not(../type) or ../type = 'p2p-sr-te-on-demand'" {
                        description "not allowed for this LSP template type";
                    }
                    type enumeration {
                        enum none                           { value 1; }
                        enum local-cspf                     { value 2; }
                    }
                    sros-ext:auto-restart-to-modify;
                    description "Fallback path computation method";
                }

                leaf prefer-transport-frr {
                    when "not(../type) or ../type = 'p2p-sr-te-one-hop' or ../type = 'p2p-sr-te-mesh' or ../type = 'p2p-sr-te-pce-init' or ../type = 'p2p-sr-te-on-demand'" {
                        description "not allowed for this LSP template type";
                    }
                    type boolean;
                    sros-ext:auto-restart-to-modify;
                    default "false";
                    description "Enable prefer transport FRR for LSP template";
                }

                leaf soft-preemption {
                    when "not(../type) or ../type = 'p2mp-rsvp' or ../type = 'p2p-rsvp-one-hop' or ../type = 'p2p-rsvp-mesh'" {
                        description "not allowed for this LSP template type";
                    }
                    type boolean;
                    sros-ext:auto-restart-to-modify;
                    description "Enable soft preemption";
                }

                leaf-list include-admin-group {
                    when "not(../type) or ../type = 'p2mp-rsvp' or ../type = 'p2p-rsvp-one-hop' or ../type = 'p2p-rsvp-mesh' or ../type = 'p2p-sr-te-one-hop' or ../type = 'p2p-sr-te-mesh' or ../type = 'p2p-sr-te-on-demand'" {
                        description "not allowed for this LSP template type";
                    }
                    type leafref {
                        path "../../../../routing-options/if-attribute/admin-group/group-name";
                    }
                    max-elements 32;
                    sros-ext:auto-restart-to-modify;
                    description "Admin group name included when LSP is set up";
                }

                leaf-list exclude-admin-group {
                    when "not(../type) or ../type = 'p2mp-rsvp' or ../type = 'p2p-rsvp-one-hop' or ../type = 'p2p-rsvp-mesh' or ../type = 'p2p-sr-te-one-hop' or ../type = 'p2p-sr-te-mesh' or ../type = 'p2p-sr-te-on-demand'" {
                        description "not allowed for this LSP template type";
                    }
                    type leafref {
                        path "../../../../routing-options/if-attribute/admin-group/group-name";
                    }
                    max-elements 32;
                    sros-ext:auto-restart-to-modify;
                    description "Admin group name excluded when LSP is set up";
                }

                leaf-list apply-groups {
                    type leafref {
                        path "../../../../groups/group/name";
                    }
                    max-elements 8;
                    ordered-by user;
                    sros-ext:auto-restart-to-modify;
                    description "Apply a configuration group at this level";
                }

                leaf-list apply-groups-exclude {
                    type leafref {
                        path "../../../../groups/group/name";
                    }
                    max-elements 8;
                    ordered-by user;
                    sros-ext:auto-restart-to-modify;
                    description "Exclude a configuration group at this level";
                }

                container class-forwarding {
                    when "not(../type) or ../type = 'p2p-rsvp-one-hop' or ../type = 'p2p-rsvp-mesh' or ../type = 'p2p-sr-te-one-hop' or ../type = 'p2p-sr-te-mesh' or ../type = 'p2p-sr-te-pce-init' or ../type = 'p2p-sr-te-on-demand'" {
                        description "not allowed for this LSP template type";
                    }
                    presence "Enable the class-forwarding context";
                    sros-ext:auto-restart-to-modify;
                    description "Enable the class-forwarding context";

                    choice cbf-choice {
                        default "default-lsp-and-fc";
                        case default-lsp-and-fc {

                            leaf default-lsp {
                                status obsolete;
                                type boolean;
                                sros-ext:auto-restart-to-modify;
                                default "false";
                                description "Use the default LSP configuration for specified LSP or LSP template";
                            }

                            leaf-list fc {
                                status obsolete;
                                type enumeration {
                                    enum be                             { value 0; }
                                    enum l2                             { value 1; }
                                    enum af                             { value 2; }
                                    enum l1                             { value 3; }
                                    enum h2                             { value 4; }
                                    enum ef                             { value 5; }
                                    enum h1                             { value 6; }
                                    enum nc                             { value 7; }
                                }
                                max-elements 8;
                                sros-ext:auto-restart-to-modify;
                                description "One or more forwarding classes for LSP instances";
                            }

                        }
                        case forwarding-set {

                            container forwarding-set {
                                sros-ext:auto-restart-to-modify;
                                description "Enter the forwarding-set context";

                                leaf policy {
                                    type leafref {
                                        path "../../../../class-forwarding-policy/policy-name";
                                    }
                                    sros-ext:auto-restart-to-modify;
                                    description "Name for the class based forwarding policy for LSP instances";
                                }

                                leaf set {
                                    type uint32 {
                                        range "1..6";
                                    }
                                    sros-ext:auto-restart-to-modify;
                                    description "Forwarding set ID";
                                }

                            } // container forwarding-set

                        }
                    }
                } // container class-forwarding

                container cspf {
                    status obsolete;
                    when "not(../type) or ../type = 'p2mp-rsvp' or ../type = 'p2p-rsvp-one-hop' or ../type = 'p2p-rsvp-mesh' or ../type = 'p2p-sr-te-one-hop' or ../type = 'p2p-sr-te-mesh' or ../type = 'p2p-sr-te-pce-init' or ../type = 'p2p-sr-te-on-demand'" {
                        description "not allowed for this LSP template type";
                    }
                    sros-ext:auto-restart-to-modify;
                    description "Enter the cspf context";

                    leaf admin-state {
                        status obsolete;
                        type types-sros:admin-state;
                        sros-ext:auto-restart-to-modify;
                        default "disable";
                        description "Administrative state of CSPF for constrained-path LSPs";
                    }

                    leaf use-te-metric {
                        status obsolete;
                        when "not(../../type = 'p2p-sr-te-pce-init')" {
                            description "not allowed for this LSP template type";
                        }
                        type boolean;
                        sros-ext:auto-restart-to-modify;
                        default "false";
                        description "TE metric for the LSP path computation by CSPF";
                    }

                } // container cspf

                container priority {
                    when "not(../type) or ../type = 'p2p-rsvp-one-hop' or ../type = 'p2p-rsvp-mesh' or ../type = 'p2mp-rsvp'" {
                        description "not allowed for this LSP template type";
                    }
                    sros-ext:auto-restart-to-modify;
                    description "Enter the priority context";

                    leaf setup-priority {
                        type types-mpls:priority;
                        sros-ext:auto-restart-to-modify;
                        default "7";
                        description "Setup priority when insufficient bandwidth is available to set up LSP";
                    }

                    leaf hold-priority {
                        type types-mpls:priority;
                        sros-ext:auto-restart-to-modify;
                        default "0";
                        description "Hold priority when insufficient bandwidth is available to set up LSP";
                    }

                } // container priority

                container fast-reroute {
                    when "not(../type) or ../type = 'p2mp-rsvp' or ../type = 'p2p-rsvp-one-hop' or ../type = 'p2p-rsvp-mesh'" {
                        description "not allowed for this LSP template type";
                    }
                    presence "Enable the fast-reroute context";
                    sros-ext:auto-restart-to-modify;
                    description "Enable the fast-reroute context";

                    leaf hop-limit {
                        type uint32 {
                            range "0..255";
                        }
                        default "16";
                        description "Total number of hops a detour or backup LSP can take";
                    }

                    leaf propagate-admin-group {
                        type boolean;
                        default "false";
                        description "Enable admin group constraints on a FRR backup LSP";
                    }

                    leaf frr-method {
                        type types-mpls:frr-method-type;
                        sros-ext:auto-restart-to-modify;
                        default "facility";
                        description "Fast Reroute method for the LSPs that are dynamically created using this LSP template";
                    }

                    leaf node-protect {
                        type boolean;
                        default "false";
                        description "Enable node and link protection for the specified LSP";
                    }

                } // container fast-reroute

                container igp-shortcut {
                    when "not(../type) or ../type = 'p2p-rsvp-one-hop' or ../type = 'p2p-rsvp-mesh' or ../type = 'p2p-sr-te-one-hop' or ../type = 'p2p-sr-te-mesh' or ../type = 'p2p-sr-te-pce-init' or ../type = 'p2p-sr-te-on-demand'" {
                        description "not allowed for this LSP template type";
                    }
                    sros-ext:auto-restart-to-modify;
                    description "Enter the igp-shortcut context";

                    leaf admin-state {
                        type types-sros:admin-state;
                        sros-ext:auto-restart-to-modify;
                        default "enable";
                        description "Administrative state of LSP for shortcut or forwarding";
                    }

                    leaf allow-sr-over-srte {
                        when "not(../../type) or ../../type = 'p2p-sr-te-one-hop' or ../../type = 'p2p-sr-te-mesh' or ../../type = 'p2p-sr-te-pce-init' or ../../type = 'p2p-sr-te-on-demand'" {
                            description "not allowed for this LSP template type";
                        }
                        type boolean;
                        sros-ext:auto-restart-to-modify;
                        default "false";
                        description "Use as eligible SRv4 or SRv6 IGP shortcut";
                    }

                    choice igp-choice {
                        case lfa-type {

                            leaf lfa-type {
                                type enumeration {
                                    enum lfa-protect                    { value 1; }
                                    enum lfa-only                       { value 2; }
                                }
                                sros-ext:auto-restart-to-modify;
                                description "LSP usage in LFA SPF";
                            }

                        }
                        case relative-metric {

                            leaf relative-metric {
                                type int32 {
                                    range "-10..10";
                                }
                                sros-ext:auto-restart-to-modify;
                                description "Shortest IGP cost between the endpoints of the LSP plus the configured offset";
                            }

                        }
                    }
                } // container igp-shortcut

                container max-sr-labels {
                    when "not(../type) or ../type = 'p2p-sr-te-mesh' or ../type = 'p2p-sr-te-one-hop' or ../type = 'p2p-sr-te-pce-init' or ../type = 'p2p-sr-te-on-demand'" {
                        description "not allowed for this LSP template type";
                    }
                    sros-ext:auto-restart-to-modify;
                    description "Enter the max-sr-labels context";

                    leaf label-stack-size {
                        type uint32 {
                            range "1..11";
                        }
                        sros-ext:auto-restart-to-modify;
                        description "Size for the maximum segment routing label stack";
                    }

                    leaf additional-frr-labels {
                        type uint32 {
                            range "0..4";
                        }
                        sros-ext:auto-restart-to-modify;
                        default "1";
                        description "Maximum number of additional overhead labels";
                    }

                } // container max-sr-labels

                list admin-tag {
                    when "not(../type) or ../type = 'p2p-sr-te-mesh' or ../type = 'p2p-sr-te-one-hop' or ../type = 'p2p-rsvp-mesh' or ../type = 'p2p-rsvp-one-hop' or ../type = 'p2p-sr-te-pce-init' or ../type = 'p2p-sr-te-on-demand'" {
                        description "not allowed for this LSP template type";
                    }
                    key "name";
                    max-elements 4;
                    description "Add a list entry for admin-tag";

                    leaf name {
                        type leafref {
                            path "../../../../../routing-options/admin-tags/admin-tag/tag";
                        }
                        description "Name of the admin tags";
                    }

                } // list admin-tag

                list path-profile {
                    when "not(../type) or ../type = 'p2p-sr-te-on-demand'" {
                        description "not allowed for this LSP template type";
                    }
                    key "profile-id";
                    max-elements 5;
                    description "Enter the path-profile list instance";

                    leaf profile-id {
                        type uint32 {
                            range "1..max";
                        }
                        description "Profile ID for the specified LSP";
                    }

                    leaf path-group {
                        type uint32;
                        default "0";
                        description "Path-group ID for the specified LSP";
                    }

                    leaf-list apply-groups {
                        type leafref {
                            path "../../../../../groups/group/name";
                        }
                        max-elements 8;
                        ordered-by user;
                        description "Apply a configuration group at this level";
                    }

                    leaf-list apply-groups-exclude {
                        type leafref {
                            path "../../../../../groups/group/name";
                        }
                        max-elements 8;
                        ordered-by user;
                        description "Exclude a configuration group at this level";
                    }

                } // list path-profile

                container auto-bandwidth {
                    when "not(../type) or ../type = 'p2p-rsvp-mesh' or ../type = 'p2p-rsvp-one-hop'" {
                        description "not allowed for this LSP template type";
                    }
                    presence "Enable the auto-bandwidth context";
                    description "Enable the auto-bandwidth context";

                    leaf max-bandwidth {
                        type types-mpls:lsp-bandwidth;
                        default "100000";
                        description "Maximum bandwidth of auto-bandwidth to request for LSP";
                    }

                    leaf min-bandwidth {
                        type types-mpls:lsp-bandwidth;
                        default "0";
                        description "Minimum bandwidth of auto-bandwidth to request for the LSP";
                    }

                    leaf monitor-bandwidth {
                        type boolean;
                        default "false";
                        description "Collect and display auto-bandwidth measurements for the LSP";
                    }

                    leaf-list apply-groups {
                        type leafref {
                            path "../../../../../groups/group/name";
                        }
                        max-elements 8;
                        ordered-by user;
                        description "Apply a configuration group at this level";
                    }

                    leaf-list apply-groups-exclude {
                        type leafref {
                            path "../../../../../groups/group/name";
                        }
                        max-elements 8;
                        ordered-by user;
                        description "Exclude a configuration group at this level";
                    }

                    list fc {
                        key "fc-name";
                        max-elements 8;
                        description "Enter the fc list instance";

                        leaf fc-name {
                            type types-sros:fc-name;
                            description "Forwarding class name for LSP";
                        }

                        leaf sampling-weight {
                            type types-sros:percent;
                            default "100";
                            description "Forwarding class weight for LSP";
                        }

                        leaf-list apply-groups {
                            type leafref {
                                path "../../../../../../groups/group/name";
                            }
                            max-elements 8;
                            ordered-by user;
                            description "Apply a configuration group at this level";
                        }

                        leaf-list apply-groups-exclude {
                            type leafref {
                                path "../../../../../../groups/group/name";
                            }
                            max-elements 8;
                            ordered-by user;
                            description "Exclude a configuration group at this level";
                        }

                    } // list fc

                    container adjust-down {
                        description "Enter the adjust-down context";

                        leaf percent {
                            type types-sros:percent;
                            default "5";
                            description "Minimum difference in percent";
                        }

                        leaf bw {
                            type types-mpls:lsp-bandwidth;
                            default "0";
                            description "Minimum difference in absolute bandwidth";
                        }

                    } // container adjust-down

                    container adjust-up {
                        description "Enter the adjust-up context";

                        leaf percent {
                            type types-sros:percent;
                            default "5";
                            description "Minimum difference in percent";
                        }

                        leaf bw {
                            type types-mpls:lsp-bandwidth;
                            default "0";
                            description "Minimum difference in absolute bandwidth";
                        }

                    } // container adjust-up

                    container multipliers {
                        description "Enter the multipliers context";

                        leaf sample-multiplier {
                            type uint32 {
                                range "1..511";
                            }
                            description "Multiplier for collection intervals in a sample interval";
                        }

                        leaf adjust-multiplier {
                            type uint32 {
                                range "1..16383";
                            }
                            description "Number of collection intervals in the adjust interval";
                        }

                    } // container multipliers

                    container overflow-limit {
                        presence "Enable the overflow-limit context";
                        description "Enable the overflow-limit context";

                        leaf threshold {
                            type types-sros:percent;
                            default "0";
                            description "Minimum difference in percent between the LSP bandwidth and the sampled data rate";
                        }

                        leaf bw {
                            type types-mpls:lsp-bandwidth {
                                range "1..6400000";
                            }
                            description "Minimum difference in absolute bandwidth";
                        }

                        leaf number {
                            type uint32 {
                                range "1..10";
                            }
                            mandatory true;
                            description "Number of overflow samples to trigger an overflow auto-bandwidth adjustment attempt";
                        }

                    } // container overflow-limit

                    container underflow-limit {
                        presence "Enable the underflow-limit context";
                        description "Enable the underflow-limit context";

                        leaf threshold {
                            type types-sros:percent;
                            default "0";
                            description "Minimum difference in percent between the LSP bandwidth and the sampled data rate";
                        }

                        leaf bw {
                            type types-mpls:lsp-bandwidth {
                                range "1..6400000";
                            }
                            description "Minimum difference in absolute bandwidth";
                        }

                        leaf number {
                            type uint32 {
                                range "1..10";
                            }
                            mandatory true;
                            description "Number of overflow samples to trigger an overflow auto-bandwidth adjustment attempt";
                        }

                    } // container underflow-limit

                } // container auto-bandwidth

                container egress-statistics {
                    when "not(../type) or ../type = 'p2mp-rsvp' or ../type = 'p2p-rsvp-one-hop' or ../type = 'p2p-rsvp-mesh' or ../type = 'p2p-sr-te-mesh' or ../type = 'p2p-sr-te-one-hop' or ../type = 'p2p-sr-te-pce-init' or ../type = 'p2p-sr-te-on-demand'" {
                        description "not allowed for this LSP template type";
                    }
                    presence "Enable the egress-statistics context";
                    sros-ext:auto-restart-to-modify;
                    description "Enable the egress-statistics context";

                    leaf collect-stats {
                        when "not(../../type) or ../../type = 'p2mp-rsvp' or ../../type = 'p2p-rsvp-one-hop' or ../../type = 'p2p-rsvp-mesh' or ../../type = 'p2p-sr-te-one-hop' or ../../type = 'p2p-sr-te-mesh'" {
                            description "not allowed for this lsp-template type";
                        }
                        type boolean;
                        sros-ext:auto-restart-to-modify;
                        default "false";
                        description "Collect LSP statistics";
                    }

                    leaf accounting-policy {
                        when "not(../../type) or ../../type = 'p2mp-rsvp' or ../../type = 'p2p-rsvp-one-hop' or ../../type = 'p2p-rsvp-mesh' or ../../type = 'p2p-sr-te-one-hop' or ../../type = 'p2p-sr-te-mesh'" {
                            description "not allowed for this lsp-template type";
                        }
                        type leafref {
                            path "../../../../../log/accounting-policy/policy-id";
                        }
                        sros-ext:auto-restart-to-modify;
                        description "Accounting policy ID";
                    }

                    leaf stat-mode {
                        type enumeration {
                            enum per-fc                         { value 0; }
                            enum aggregate                      { value 1; }
                        }
                        sros-ext:auto-restart-to-modify;
                        description "Statistics collection mode";
                    }

                } // container egress-statistics

                container bfd {
                    when "not(../type) or ../type = 'p2p-rsvp-one-hop' or ../type = 'p2p-rsvp-mesh' or ../type = 'p2p-sr-te-mesh' or ../type = 'p2p-sr-te-one-hop' or ../type = 'p2p-sr-te-pce-init' or ../type = 'p2p-sr-te-on-demand'" {
                        description "not allowed for this LSP template type";
                    }
                    sros-ext:auto-restart-to-modify;
                    description "Enter the bfd context";

                    leaf bfd-liveness {
                        type boolean;
                        default "false";
                        description "Enable BFD on the RSVP LSP or S-BFD on the SR-TE LSP";
                    }

                    leaf bfd-template {
                        type leafref {
                            path "../../../../../bfd/bfd-template/name";
                        }
                        description "BFD template to be used by LSP BFD sessions";
                    }

                    leaf lsp-ping-interval {
                        when "not(../../type) or ../../type = 'p2p-rsvp-one-hop' or ../../type = 'p2p-rsvp-mesh'" {
                            description "not allowed for this LSP type";
                        }
                        type union {
                            type uint32 {
                                range "60..300";
                            }
                            type enumeration {
                                enum none                           { value 0; }
                            }
                        }
                        units "seconds";
                        default "60";
                        description "Interval for periodic LSP ping for BFD bootstrapping";
                    }

                    leaf failure-action {
                        type enumeration {
                            enum none                           { value 0; }
                            enum down                           { value 1; }
                            enum failover-or-down               { value 2; }
                        }
                        default "none";
                        description "Action to take when LSP BFD session fails";
                    }

                    leaf wait-for-up-timer {
                        when "not(../../type) or ../../type = 'p2p-sr-te-one-hop' or ../../type = 'p2p-sr-te-mesh' or ../../type = 'p2p-sr-te-pce-init' or ../../type = 'p2p-sr-te-on-demand'" {
                            description "not allowed for this LSP template type";
                        }
                        type uint32 {
                            range "1..60";
                        }
                        units "seconds";
                        sros-ext:auto-restart-to-modify;
                        default "4";
                        description "Time to wait for BFD to become operationally available";
                    }

                    leaf return-path-label {
                        when "not(../../type) or ../../type = 'p2p-sr-te-one-hop' or ../../type = 'p2p-sr-te-mesh' or ../../type = 'p2p-sr-te-pce-init' or ../../type = 'p2p-sr-te-on-demand'" {
                            description "not allowed for this LSP template type";
                        }
                        type uint32 {
                            range "32..1048575";
                        }
                        sros-ext:auto-restart-to-modify;
                        description "S-BFD return-path label";
                    }

                } // container bfd

                container pce-associations {
                    sros-ext:auto-restart-to-modify;
                    description "Enter the pce-associations context";

                    list diversity {
                        when "not(../../type) or ../../type = 'p2p-sr-te-on-demand'" {
                            description "not allowed for this Template type";
                        }
                        key "diversity-name";
                        max-elements 5;
                        description "Add a list entry for diversity";

                        leaf diversity-name {
                            type leafref {
                                path "../../../../../../router/pcep/pcc/pce-associations/diversity/assoc-name";
                            }
                            description "Name of the PCE association configured under the PCC";
                        }

                    } // list diversity

                    list policy {
                        when "not(../../type) or ../../type = 'p2p-sr-te-on-demand'" {
                            description "not allowed for this Template type";
                        }
                        key "policy-name";
                        max-elements 5;
                        description "Add a list entry for policy";

                        leaf policy-name {
                            type leafref {
                                path "../../../../../../router/pcep/pcc/pce-associations/policy/assoc-name";
                            }
                            description "Name of the PCE association configured under the PCC";
                        }

                    } // list policy

                } // container pce-associations

            } // list lsp-template

            list lsp {
                key "lsp-name";
                description "Enter the lsp list instance";

                leaf lsp-name {
                    type types-sros:named-item-64;
                    description "Labeled Switch path name";
                }

                leaf type {
                    type enumeration {
                        enum p2p-rsvp                       { value 2; }
                        enum p2p-static-mpls                { value 3; }
                        enum p2p-rsvp-bypass                { value 4; }
                        enum p2mp-rsvp                      { value 5; }
                        enum p2mp-rsvp-auto                 { value 6; }
                        enum p2p-rsvp-mesh                  { value 8; }
                        enum p2p-rsvp-one-hop               { value 9; }
                        enum p2p-sr-te                      { value 10; }
                        enum p2p-sr-te-mesh                 { value 11; }
                        enum p2p-sr-te-one-hop              { value 12; }
                        enum p2p-sr-te-pce-init             { value 13; }
                        enum p2p-sr-te-on-demand            { value 15; }
                    }
                    sros-ext:immutable;
                    mandatory true;
                    description "LSP for bypass protection, point to multipoint, segment routing or MPLS-TP static LSP";
                }

                leaf admin-state {
                    type types-sros:admin-state;
                    default "disable";
                    description "Administrative state of the LSP";
                }

                leaf exclude-node {
                    when "not(../type) or ../type = 'p2p-rsvp-bypass'" {
                        description "not allowed for this LSP type";
                    }
                    type types-sros:ip-address;
                    description "Exclude Routers object to be included in the bypass path message";
                }

                leaf from {
                    when "not(../type) or ../type = 'p2p-rsvp' or ../type = 'p2p-rsvp-bypass' or ../type = 'p2mp-rsvp' or ../type = 'p2p-sr-te'" {
                        description "not allowed for this LSP type";
                    }
                    type types-sros:ip-address;
                    sros-ext:auto-restart-to-modify;
                    description "Source IP address of this LSP";
                }

                leaf to {
                    when "not(../type) or ../type = 'p2p-rsvp' or ../type = 'p2p-rsvp-bypass' or ../type = 'p2p-sr-te'" {
                        description "not allowed for this LSP type";
                    }
                    type types-sros:ip-address;
                    sros-ext:auto-restart-to-modify;
                    description "Destination IP address or the egress router for the LSP";
                }

                leaf hop-limit {
                    when "not(../type) or ../type = 'p2p-rsvp' or ../type = 'p2p-rsvp-bypass' or ../type = 'p2mp-rsvp' or ../type = 'p2p-sr-te'" {
                        description "not allowed for this LSP type";
                    }
                    type uint32 {
                        range "2..255";
                    }
                    default "255";
                    description "Maximum number of hops that an LSP can traverse including ingress and egress routers";
                }

                leaf p2mp-id {
                    when "not(../type) or ../type = 'p2mp-rsvp'" {
                        description "not allowed for this LSP type";
                    }
                    type uint32 {
                        range "1..65535";
                    }
                    description "Unique identifier as Point-to-Multipoint (P2MP) identifier";
                }

                leaf pce-computation {
                    status obsolete;
                    when "not(../type) or ../type = 'p2p-rsvp' or ../type = 'p2p-sr-te'" {
                        description "not allowed for this LSP type";
                    }
                    type boolean;
                    default "false";
                    description "LSP path computation request sent to local CSPF or to PCE";
                }

                leaf pce-control {
                    when "not(../type) or ../type = 'p2p-rsvp' or ../type = 'p2p-sr-te'" {
                        description "not allowed for this LSP type";
                    }
                    type boolean;
                    default "false";
                    description "Enable PCE controlled LSP mode of operation";
                }

                leaf revert-timer {
                    when "not(../type) or ../type = 'p2p-rsvp' or ../type = 'p2p-sr-te'" {
                        description "not allowed for this LSP type";
                    }
                    type uint32 {
                        range "1..4320";
                    }
                    units "minutes";
                    description "Revert timer for the LSP";
                }

                leaf rsvp-resv-style {
                    when "not(../type) or ../type = 'p2p-rsvp' or ../type = 'p2p-rsvp-bypass' or ../type = 'p2mp-rsvp'" {
                        description "not allowed for this LSP type";
                    }
                    type enumeration {
                        enum se                             { value 1; }
                        enum ff                             { value 2; }
                    }
                    default "se";
                    description "Reservation style for RSVP";
                }

                leaf bgp-shortcut {
                    when "not(../type) or ../type = 'p2p-rsvp' or ../type = 'p2p-sr-te'" {
                        description "not allowed for this LSP type";
                    }
                    type boolean;
                    description "Include LSP for BGP routes";
                }

                leaf bgp-transport-tunnel {
                    when "not(../type) or ../type = 'p2p-rsvp' or ../type = 'p2p-sr-te'" {
                        description "not allowed for this LSP type";
                    }
                    type boolean;
                    description "Include LSP as transport LSP for labeled BGP routes";
                }

                leaf ldp-over-rsvp {
                    when "not(../type) or ../type = 'p2p-rsvp'" {
                        description "not allowed for this LSP type";
                    }
                    type boolean;
                    description "Include this LSP in LDP over RSVP";
                }

                leaf metric {
                    when "not(../type) or ../type = 'p2p-rsvp' or ../type = 'p2p-sr-te'" {
                        description "not allowed for this LSP type";
                    }
                    type uint32 {
                        range "0..16777215";
                    }
                    description "LSP metric that forces to a constant value";
                }

                leaf vprn-auto-bind {
                    when "not(../type) or ../type = 'p2p-rsvp' or ../type = 'p2p-sr-te'" {
                        description "not allowed for this LSP type";
                    }
                    type boolean;
                    description "Include this LSP in auto-bind for VPRN services";
                }

                leaf pce-report {
                    when "not(../type) or ../type = 'p2p-rsvp' or ../type = 'p2p-sr-te'" {
                        description "not allowed for this LSP type";
                    }
                    type types-sros:bool-with-inherit;
                    description "Global configuration of reporting to PCE to override";
                }

                leaf entropy-label {
                    when "not(../type) or ../type = 'p2p-rsvp' or ../type = 'p2p-sr-te'" {
                        description "not allowed for this LSP type";
                    }
                    type types-sros:bool-with-inherit;
                    description "Entropy label";
                }

                leaf override-tunnel-elc {
                    when "../type = 'p2p-sr-te'" {
                        description "not allowed for this LSP type";
                    }
                    type boolean;
                    default "false";
                    description "Override any received entropy label capability";
                }

                leaf adaptive {
                    when "not(../type) or ../type = 'p2p-rsvp' or ../type = 'p2p-rsvp-bypass' or ../type = 'p2mp-rsvp'" {
                        description "not allowed for this LSP type";
                    }
                    type boolean;
                    default "true";
                    description "Enable make-before-break functionality";
                }

                leaf adspec {
                    when "not(../type) or ../type = 'p2p-rsvp' or ../type = 'p2p-rsvp-bypass'" {
                        description "not allowed for this LSP type";
                    }
                    type boolean;
                    default "false";
                    description "Include ADSPEC object in RSVP messages";
                }

                leaf binding-sid {
                    when "../type = 'p2p-sr-te'" {
                        description "not allowed for this LSP type";
                    }
                    type types-sros:mpls-label-or-zero;
                    description "Binding SID for the LSP";
                }

                leaf class-type {
                    when "not(../type) or ../type = 'p2p-rsvp'" {
                        description "not allowed for this LSP type";
                    }
                    type types-mpls:class-type;
                    default "0";
                    description "Class type for an LSP";
                }

                leaf least-fill {
                    when "not(../type) or ../type = 'p2p-rsvp'" {
                        description "not allowed for this LSP type";
                    }
                    type boolean;
                    default "false";
                    description "Enable least-fill path selection for this LSP";
                }

                leaf load-balancing-weight {
                    when "not(../type) or ../type = 'p2p-rsvp' or ../type = 'p2p-sr-te'" {
                        description "not allowed for this LSP type";
                    }
                    type uint32 {
                        range "1..max";
                    }
                    description "Load balancing weight for an MPLS LSP";
                }

                leaf main-ct-retry-limit {
                    when "not(../type) or ../type = 'p2p-rsvp'" {
                        description "not allowed for this LSP type";
                    }
                    type uint32 {
                        range "1..10000";
                    }
                    description "Maximum number of retries before reverting to backup CT";
                }

                leaf propagate-admin-group {
                    when "not(../type) or ../type = 'p2p-rsvp' or ../type = 'p2p-rsvp-bypass' or ../type = 'p2mp-rsvp'" {
                        description "not allowed for this LSP type";
                    }
                    type boolean;
                    default "false";
                    description "Enable admin groups via session attribute object";
                }

                leaf retry-limit {
                    when "not(../type) or ../type = 'p2p-rsvp' or ../type = 'p2p-rsvp-bypass' or ../type = 'p2mp-rsvp' or ../type = 'p2p-sr-te'" {
                        description "not allowed for this LSP type";
                    }
                    type uint32 {
                        range "1..10000";
                    }
                    description "Number of attempts to re-establish LSP after it fails";
                }

                leaf retry-timer {
                    when "not(../type) or ../type = 'p2p-rsvp' or ../type = 'p2p-rsvp-bypass' or ../type = 'p2mp-rsvp' or ../type = 'p2p-sr-te'" {
                        description "not allowed for this LSP type";
                    }
                    type uint32 {
                        range "1..600";
                    }
                    units "seconds";
                    default "30";
                    description "Time for LSP re-establishment attempts after failure";
                }

                leaf path-computation-method {
                    when "not(../type) or ../type = 'p2p-rsvp' or ../type = 'p2p-rsvp-bypass' or ../type = 'p2mp-rsvp' or ../type = 'p2p-sr-te'" {
                        description "not allowed for this LSP type";
                    }
                    type enumeration {
                        enum local-cspf                     { value 2; }
                        enum pce                            { value 3; }
                    }
                    description "Path computation method";
                }

                leaf metric-type {
                    when "not(../type) or ../type = 'p2p-rsvp' or ../type = 'p2p-rsvp-bypass' or ../type = 'p2mp-rsvp' or ../type = 'p2p-sr-te'" {
                        description "not allowed for this LSP type";
                    }
                    type enumeration {
                        enum igp                            { value 1; }
                        enum te                             { value 2; }
                    }
                    default "igp";
                    description "Metric type used for LSP path computation";
                }

                leaf local-sr-protection {
                    when "not(../type) or ../type = 'p2p-sr-te'" {
                        description "not allowed for this LSP type";
                    }
                    type enumeration {
                        enum none                           { value 1; }
                        enum preferred                      { value 2; }
                        enum mandatory                      { value 3; }
                    }
                    default "preferred";
                    description "Local SR protection preference for LSP path computation";
                }

                leaf label-stack-reduction {
                    when "not(../type) or ../type = 'p2p-sr-te'" {
                        description "not allowed for this LSP type";
                    }
                    type boolean;
                    default "false";
                    description "Enable/disable label compression for LSP path.";
                }

                leaf lsp-self-ping {
                    when "not(../type) or ../type = 'p2p-rsvp'" {
                        description "not allowed for this LSP type";
                    }
                    type types-sros:bool-with-inherit;
                    description "LSP Self Ping activation status on the RSVP-TE LSP";
                }

                leaf fallback-path-computation-method {
                    when "not(../type) or ../type = 'p2p-sr-te' or ../type = 'p2p-rsvp'" {
                        description "not allowed for this LSP type";
                    }
                    type enumeration {
                        enum none                           { value 1; }
                        enum local-cspf                     { value 2; }
                    }
                    description "Fallback path computation method";
                }

                leaf prefer-transport-frr {
                    when "not(../type) or ../type = 'p2p-sr-te'" {
                        description "not allowed for this LSP type";
                    }
                    type boolean;
                    default "false";
                    description "Enable prefer transport FRR for LSP";
                }

                leaf soft-preemption {
                    when "not(../type) or ../type = 'p2p-rsvp' or ../type = 'p2mp-rsvp'" {
                        description "not allowed for this LSP type";
                    }
                    type boolean;
                    description "Enable soft preemption";
                }

                leaf-list include-admin-group {
                    when "not(../type) or ../type = 'p2p-rsvp' or ../type = 'p2p-rsvp-bypass' or ../type = 'p2mp-rsvp' or ../type = 'p2p-sr-te'" {
                        description "not allowed for this LSP type";
                    }
                    type leafref {
                        path "../../../../routing-options/if-attribute/admin-group/group-name";
                    }
                    max-elements 32;
                    description "Admin group name included when LSP is set up";
                }

                leaf-list exclude-admin-group {
                    when "not(../type) or ../type = 'p2p-rsvp' or ../type = 'p2p-rsvp-bypass' or ../type = 'p2mp-rsvp' or ../type = 'p2p-sr-te'" {
                        description "not allowed for this LSP type";
                    }
                    type leafref {
                        path "../../../../routing-options/if-attribute/admin-group/group-name";
                    }
                    max-elements 32;
                    description "Name of admin group excluded when LSP is set up";
                }

                leaf-list apply-groups {
                    type leafref {
                        path "../../../../groups/group/name";
                    }
                    max-elements 8;
                    ordered-by user;
                    description "Apply a configuration group at this level";
                }

                leaf-list apply-groups-exclude {
                    type leafref {
                        path "../../../../groups/group/name";
                    }
                    max-elements 8;
                    ordered-by user;
                    description "Exclude a configuration group at this level";
                }

                container class-forwarding {
                    when "not(../type) or ../type = 'p2p-rsvp' or ../type = 'p2p-sr-te'" {
                        description "not allowed for this LSP type";
                    }
                    presence "Enable the class-forwarding context";
                    description "Enable the class-forwarding context";

                    choice cbf-choice {
                        default "default-lsp-and-fc";
                        case default-lsp-and-fc {

                            leaf default-lsp {
                                status obsolete;
                                type boolean;
                                default "false";
                                description "Use the default LSP configuration for specified LSP or LSP template";
                            }

                            leaf-list fc {
                                status obsolete;
                                type enumeration {
                                    enum be                             { value 0; }
                                    enum l2                             { value 1; }
                                    enum af                             { value 2; }
                                    enum l1                             { value 3; }
                                    enum h2                             { value 4; }
                                    enum ef                             { value 5; }
                                    enum h1                             { value 6; }
                                    enum nc                             { value 7; }
                                }
                                max-elements 8;
                                description "One or more forwarding classes for LSP instances";
                            }

                        }
                        case forwarding-set {

                            container forwarding-set {
                                description "Enter the forwarding-set context";

                                leaf policy {
                                    type leafref {
                                        path "../../../../class-forwarding-policy/policy-name";
                                    }
                                    description "Name for the class based forwarding policy for LSP instances";
                                }

                                leaf set {
                                    type uint32 {
                                        range "1..6";
                                    }
                                    description "Forwarding set ID";
                                }

                            } // container forwarding-set

                        }
                    }
                } // container class-forwarding

                container cspf {
                    status obsolete;
                    when "not(../type) or ../type = 'p2p-rsvp' or ../type = 'p2p-rsvp-bypass' or ../type = 'p2mp-rsvp' or ../type = 'p2p-sr-te'" {
                        description "not allowed for this LSP type";
                    }
                    presence "Enable the cspf context";
                    description "Enable the cspf context";

                    leaf use-te-metric {
                        status obsolete;
                        type boolean;
                        default "false";
                        description "TE metric to the LSP path computation by CSPF";
                    }

                } // container cspf

                container igp-shortcut {
                    when "not(../type) or ../type = 'p2p-rsvp' or ../type = 'p2p-sr-te'" {
                        description "not allowed for this LSP type";
                    }
                    description "Enter the igp-shortcut context";

                    leaf admin-state {
                        type types-sros:admin-state;
                        description "Administrative state of LSP for shortcut or forwarding";
                    }

                    leaf allow-sr-over-srte {
                        when "not(../../type) or ../../type = 'p2p-sr-te'" {
                            description "not allowed for this LSP type";
                        }
                        type boolean;
                        default "false";
                        description "Use as eligible SRv4 or SRv6 IGP shortcut";
                    }

                    choice igp-choice {
                        case lfa-type {

                            leaf lfa-type {
                                type enumeration {
                                    enum lfa-protect                    { value 1; }
                                    enum lfa-only                       { value 2; }
                                }
                                description "LSP usage in LFA SPF";
                            }

                        }
                        case relative-metric {

                            leaf relative-metric {
                                type int32 {
                                    range "-10..10";
                                }
                                description "Shortest IGP cost between the endpoints of the LSP plus the configured offset";
                            }

                        }
                    }
                } // container igp-shortcut

                container fast-reroute {
                    when "not(../type) or ../type = 'p2p-rsvp' or ../type = 'p2mp-rsvp'" {
                        description "not allowed for this LSP type";
                    }
                    presence "Enable the fast-reroute context";
                    description "Enable the fast-reroute context";

                    leaf hop-limit {
                        type uint32 {
                            range "0..255";
                        }
                        default "16";
                        description "Total number of hops a detour or backup LSP can take";
                    }

                    leaf propagate-admin-group {
                        type boolean;
                        default "false";
                        description "Enable admin group constraints on a FRR backup LSP";
                    }

                    leaf frr-method {
                        type types-mpls:frr-method-type;
                        description "Fast Reroute method";
                    }

                    leaf node-protect {
                        type boolean;
                        description "Enable node and link protection for the specified LSP";
                    }

                } // container fast-reroute

                container max-sr-labels {
                    when "not(../type) or ../type = 'p2p-sr-te'" {
                        description "not allowed for this LSP type";
                    }
                    description "Enter the max-sr-labels context";

                    leaf label-stack-size {
                        type uint32 {
                            range "1..11";
                        }
                        description "Maximum label stack size";
                    }

                    leaf additional-frr-labels {
                        type uint32 {
                            range "0..4";
                        }
                        default "1";
                        description "Value for the maximum additional overhead labels";
                    }

                } // container max-sr-labels

                list admin-tag {
                    when "not(../type) or ../type = 'p2p-rsvp' or ../type = 'p2p-sr-te'" {
                        description "not allowed for this LSP type";
                    }
                    key "name";
                    max-elements 4;
                    description "Add a list entry for admin-tag";

                    leaf name {
                        type leafref {
                            path "../../../../../routing-options/admin-tags/admin-tag/tag";
                        }
                        description "Name of the admin tags";
                    }

                } // list admin-tag

                container auto-bandwidth {
                    when "not(../type) or ../type = 'p2p-rsvp'" {
                        description "not allowed for this LSP type";
                    }
                    presence "Enable the auto-bandwidth context";
                    description "Enable the auto-bandwidth context";

                    leaf max-bandwidth {
                        type types-mpls:lsp-bandwidth;
                        default "100000";
                        description "Maximum bandwidth of auto-bandwidth to request for LSP";
                    }

                    leaf min-bandwidth {
                        type types-mpls:lsp-bandwidth;
                        default "0";
                        description "Minimum bandwidth of auto-bandwidth to request for the LSP";
                    }

                    leaf monitor-bandwidth {
                        type boolean;
                        default "false";
                        description "Collect and display auto-bandwidth measurements for the LSP";
                    }

                    leaf-list apply-groups {
                        type leafref {
                            path "../../../../../groups/group/name";
                        }
                        max-elements 8;
                        ordered-by user;
                        description "Apply a configuration group at this level";
                    }

                    leaf-list apply-groups-exclude {
                        type leafref {
                            path "../../../../../groups/group/name";
                        }
                        max-elements 8;
                        ordered-by user;
                        description "Exclude a configuration group at this level";
                    }

                    list fc {
                        key "fc-name";
                        max-elements 8;
                        description "Enter the fc list instance";

                        leaf fc-name {
                            type types-sros:fc-name;
                            description "Forwarding class name for LSP";
                        }

                        leaf sampling-weight {
                            type types-sros:percent;
                            default "100";
                            description "Forwarding class weight for LSP";
                        }

                        leaf-list apply-groups {
                            type leafref {
                                path "../../../../../../groups/group/name";
                            }
                            max-elements 8;
                            ordered-by user;
                            description "Apply a configuration group at this level";
                        }

                        leaf-list apply-groups-exclude {
                            type leafref {
                                path "../../../../../../groups/group/name";
                            }
                            max-elements 8;
                            ordered-by user;
                            description "Exclude a configuration group at this level";
                        }

                    } // list fc

                    container adjust-down {
                        description "Enter the adjust-down context";

                        leaf percent {
                            type types-sros:percent;
                            default "5";
                            description "Minimum difference in percent";
                        }

                        leaf bw {
                            type types-mpls:lsp-bandwidth;
                            default "0";
                            description "Minimum difference in absolute bandwidth";
                        }

                    } // container adjust-down

                    container adjust-up {
                        description "Enter the adjust-up context";

                        leaf percent {
                            type types-sros:percent;
                            default "5";
                            description "Minimum difference in percent";
                        }

                        leaf bw {
                            type types-mpls:lsp-bandwidth;
                            default "0";
                            description "Minimum difference in absolute bandwidth";
                        }

                    } // container adjust-up

                    container multipliers {
                        description "Enter the multipliers context";

                        leaf sample-multiplier {
                            type uint32 {
                                range "1..511";
                            }
                            description "Multiplier for collection intervals in a sample interval";
                        }

                        leaf adjust-multiplier {
                            type uint32 {
                                range "1..16383";
                            }
                            description "Number of collection intervals in the adjust interval";
                        }

                    } // container multipliers

                    container overflow-limit {
                        presence "Enable the overflow-limit context";
                        description "Enable the overflow-limit context";

                        leaf threshold {
                            type types-sros:percent;
                            default "0";
                            description "Minimum difference in percent between the LSP bandwidth and the sampled data rate";
                        }

                        leaf bw {
                            type types-mpls:lsp-bandwidth {
                                range "1..6400000";
                            }
                            description "Minimum difference in absolute bandwidth";
                        }

                        leaf number {
                            type uint32 {
                                range "1..10";
                            }
                            mandatory true;
                            description "Number of overflow samples to trigger an overflow auto-bandwidth adjustment attempt";
                        }

                    } // container overflow-limit

                    container underflow-limit {
                        presence "Enable the underflow-limit context";
                        description "Enable the underflow-limit context";

                        leaf threshold {
                            type types-sros:percent;
                            default "0";
                            description "Minimum difference in percent between the LSP bandwidth and the sampled data rate";
                        }

                        leaf bw {
                            type types-mpls:lsp-bandwidth {
                                range "1..6400000";
                            }
                            description "Minimum difference in absolute bandwidth";
                        }

                        leaf number {
                            type uint32 {
                                range "1..10";
                            }
                            mandatory true;
                            description "Number of overflow samples to trigger an overflow auto-bandwidth adjustment attempt";
                        }

                    } // container underflow-limit

                    container use-last-adj-bw {
                        presence "Enable the use-last-adj-bw context";
                        description "Enable the use-last-adj-bw context";

                        leaf secondary-retry-limit {
                            type types-mpls:retry-limit;
                            default "5";
                            description "Maximum number of retry limits for secondary paths";
                        }

                    } // container use-last-adj-bw

                } // container auto-bandwidth

                container egress-statistics {
                    when "../type = 'p2p-rsvp' or ../type = 'p2mp-rsvp' or not(../type) or ../type = 'p2p-sr-te'" {
                        description "not allowed for this LSP type";
                    }
                    presence "Enable the egress-statistics context";
                    description "Enable the egress-statistics context";

                    leaf collect-stats {
                        when "not(../../type) or ../../type = 'p2p-rsvp' or ../../type = 'p2mp-rsvp' or ../../type = 'p2p-sr-te'" {
                            description "not allowed for this LSP type";
                        }
                        type boolean;
                        default "false";
                        description "Collect LSP statistics";
                    }

                    leaf accounting-policy {
                        when "not(../../type) or ../../type = 'p2p-rsvp' or ../../type = 'p2mp-rsvp' or ../../type = 'p2p-sr-te'" {
                            description "not allowed for this LSP type";
                        }
                        type leafref {
                            path "../../../../../log/accounting-policy/policy-id";
                        }
                        description "Accounting policy ID";
                    }

                    leaf admin-state {
                        when "not(../../type) or ../../type = 'p2p-rsvp' or ../../type = 'p2mp-rsvp' or ../../type = 'p2p-sr-te'" {
                            description "not allowed for this LSP type";
                        }
                        type types-sros:admin-state;
                        default "disable";
                        description "Administrative state of statistics for the LSP";
                    }

                    leaf stat-mode {
                        type enumeration {
                            enum per-fc                         { value 0; }
                            enum aggregate                      { value 1; }
                        }
                        sros-ext:auto-restart-to-modify;
                        description "Statistics collection mode";
                    }

                    leaf-list apply-groups {
                        type leafref {
                            path "../../../../../groups/group/name";
                        }
                        max-elements 8;
                        ordered-by user;
                        description "Apply a configuration group at this level";
                    }

                    leaf-list apply-groups-exclude {
                        type leafref {
                            path "../../../../../groups/group/name";
                        }
                        max-elements 8;
                        ordered-by user;
                        description "Exclude a configuration group at this level";
                    }

                } // container egress-statistics


                container bfd {
                    when "not(../type) or ../type = 'p2p-rsvp' or ../type = 'p2p-sr-te'" {
                        description "not allowed for this LSP type";
                    }
                    description "Enter the bfd context";

                    leaf bfd-liveness {
                        type boolean;
                        default "false";
                        description "Enable BFD on the RSVP LSP or S-BFD on the SR-TE LSP";
                    }

                    leaf bfd-template {
                        type leafref {
                            path "../../../../../bfd/bfd-template/name";
                        }
                        description "BFD template to be used by LSP BFD sessions";
                    }

                    leaf lsp-ping-interval {
                        when "not(../../type) or ../../type = 'p2p-rsvp'" {
                            description "not allowed for this LSP type";
                        }
                        type union {
                            type uint32 {
                                range "60..300";
                            }
                            type enumeration {
                                enum none                           { value 0; }
                            }
                        }
                        units "seconds";
                        default "60";
                        description "Interval for periodic LSP ping for BFD bootstrapping";
                    }

                    leaf failure-action {
                        type enumeration {
                            enum none                           { value 0; }
                            enum down                           { value 1; }
                            enum failover                       { value 2; }
                            enum failover-or-down               { value 3; }
                        }
                        default "none";
                        description "Action when LSP BFD fails on the RSVP SR-TE LSP";
                    }

                    leaf wait-for-up-timer {
                        when "not(../../type) or ../../type = 'p2p-sr-te' or ../../type = 'p2p-rsvp'" {
                            description "not allowed for this LSP type";
                        }
                        type uint32 {
                            range "1..60";
                        }
                        units "seconds";
                        default "4";
                        description "Time to wait for BFD to become operationally available";
                    }

                    leaf return-path-label {
                        when "../../type = 'p2p-sr-te'" {
                            description "not allowed for this LSP type";
                        }
                        type uint32 {
                            range "32..1048575";
                        }
                        description "S-BFD return-path label";
                    }

                } // container bfd

                list path-profile {
                    when "not(../type) or ../type = 'p2p-rsvp' or ../type = 'p2p-sr-te'" {
                        description "not allowed for this LSP type";
                    }
                    key "profile-id";
                    max-elements 5;
                    description "Enter the path-profile list instance";

                    leaf profile-id {
                        type uint32 {
                            range "1..max";
                        }
                        description "Profile ID for the specified LSP";
                    }

                    leaf path-group {
                        type uint32;
                        default "0";
                        description "Path-group ID for the specified LSP";
                    }

                    leaf-list apply-groups {
                        type leafref {
                            path "../../../../../groups/group/name";
                        }
                        max-elements 8;
                        ordered-by user;
                        description "Apply a configuration group at this level";
                    }

                    leaf-list apply-groups-exclude {
                        type leafref {
                            path "../../../../../groups/group/name";
                        }
                        max-elements 8;
                        ordered-by user;
                        description "Exclude a configuration group at this level";
                    }

                } // list path-profile

                container pce-associations {
                    description "Enter the pce-associations context";

                    list diversity {
                        when "not(../../type) or ../../type = 'p2p-rsvp' or ../../type = 'p2p-sr-te'" {
                            description "not allowed for this LSP type";
                        }
                        key "diversity-name";
                        max-elements 5;
                        description "Add a list entry for diversity";

                        leaf diversity-name {
                            type leafref {
                                path "../../../../../../router/pcep/pcc/pce-associations/diversity/assoc-name";
                            }
                            description "Name of the PCE association configured under the PCC";
                        }

                    } // list diversity

                    list policy {
                        when "not(../../type) or ../../type = 'p2p-rsvp' or ../../type = 'p2p-sr-te'" {
                            description "not allowed for this LSP type";
                        }
                        key "policy-name";
                        max-elements 5;
                        description "Add a list entry for policy";

                        leaf policy-name {
                            type leafref {
                                path "../../../../../../router/pcep/pcc/pce-associations/policy/assoc-name";
                            }
                            description "Name of the PCE association configured under the PCC";
                        }

                    } // list policy

                } // container pce-associations

                list primary {
                    when "not(../type) or ../type = 'p2p-rsvp' or ../type = 'p2p-rsvp-bypass' or ../type = 'p2p-sr-te'" {
                        description "not allowed for this LSP type";
                    }
                    key "path-name";
                    max-elements 1;
                    description "Enter the primary list instance";

                    leaf path-name {
                        type leafref {
                            path "../../../path/path-name";
                        }
                        description "Path name";
                    }

                    leaf admin-state {
                        type types-sros:admin-state;
                        default "enable";
                        description "Administrative state of the LSP path";
                    }

                    leaf adaptive {
                        when "not(../../type) or ../../type = 'p2p-rsvp' or ../../type = 'p2p-rsvp-bypass' or ../../type = 'p2mp-rsvp'" {
                            description "not allowed for this LSP type";
                        }
                        type boolean;
                        description "Enable make-before-break functionality";
                    }

                    leaf bandwidth {
                        when "not(../../type) or ../../type = 'p2p-rsvp' or ../../type = 'p2mp-rsvp' or ../../type = 'p2p-sr-te'" {
                            description "not allowed for this LSP type";
                        }
                        type types-mpls:lsp-bandwidth;
                        default "0";
                        description "Amount of bandwidth to be reserved";
                    }

                    leaf hop-limit {
                        when "not(../../type) or ../../type = 'p2p-rsvp' or ../../type = 'p2p-rsvp-bypass' or ../../type = 'p2mp-rsvp' or ../../type = 'p2p-sr-te'" {
                            description "not allowed for this LSP type";
                        }
                        type uint32 {
                            range "2..255";
                        }
                        description "Total number of hops that an LSP traverses";
                    }

                    leaf record {
                        when "not(../../type) or ../../type = 'p2p-rsvp' or ../../type = 'p2p-rsvp-bypass' or ../../type = 'p2mp-rsvp'" {
                            description "not allowed for this LSP type";
                        }
                        type boolean;
                        default "true";
                        description "Enable recording of all hops that an LSP path traverses";
                    }

                    leaf record-label {
                        when "not(../../type) or ../../type = 'p2p-rsvp' or ../../type = 'p2p-rsvp-bypass' or ../../type = 'p2mp-rsvp'" {
                            description "not allowed for this LSP type";
                        }
                        type boolean;
                        default "true";
                        description "Enable recording of labels at each node or instance";
                    }

                    leaf class-type {
                        when "not(../../type) or ../../type = 'p2p-rsvp'" {
                            description "not allowed for this LSP type";
                        }
                        type types-mpls:class-type;
                        description "Class-type";
                    }

                    leaf backup-class-type {
                        when "not(../../type) or ../../type = 'p2p-rsvp'" {
                            description "not allowed for this LSP type";
                        }
                        type types-mpls:class-type;
                        description "Class-type for the LSP or LSP path";
                    }

                    leaf-list apply-groups {
                        type leafref {
                            path "../../../../../groups/group/name";
                        }
                        max-elements 8;
                        ordered-by user;
                        description "Apply a configuration group at this level";
                    }

                    leaf-list apply-groups-exclude {
                        type leafref {
                            path "../../../../../groups/group/name";
                        }
                        max-elements 8;
                        ordered-by user;
                        description "Exclude a configuration group at this level";
                    }

                    container priority {
                        when "not(../../type) or ../../type = 'p2p-rsvp' or ../../type = 'p2p-sr-te'" {
                            description "not allowed for this LSP type";
                        }
                        description "Enter the priority context";

                        leaf setup-priority {
                            type types-mpls:priority;
                            default "7";
                            description "Priority when insufficient bandwidth for LSP setup";
                        }

                        leaf hold-priority {
                            type types-mpls:priority;
                            default "0";
                            description "Priority of an LSP session at preemption action";
                        }

                    } // container priority

                    container include-admin-group {
                        when "not(../../type) or ../../type = 'p2p-rsvp' or ../../type = 'p2p-rsvp-bypass' or ../../type = 'p2p-sr-te'" {
                            description "not allowed for this LSP type";
                        }
                        presence "Enable the include-admin-group context";
                        description "Enable the include-admin-group context";

                        leaf-list group {
                            type leafref {
                                path "../../../../../../routing-options/if-attribute/admin-group/group-name";
                            }
                            min-elements 1;
                            max-elements 32;
                            description "Groups that are included when LSP path is setup";
                        }

                    } // container include-admin-group

                    container exclude-admin-group {
                        when "not(../../type) or ../../type = 'p2p-rsvp' or ../../type = 'p2p-rsvp-bypass' or ../../type = 'p2p-sr-te'" {
                            description "not allowed for this LSP type";
                        }
                        presence "Enable the exclude-admin-group context";
                        description "Enable the exclude-admin-group context";

                        leaf-list group {
                            type leafref {
                                path "../../../../../../routing-options/if-attribute/admin-group/group-name";
                            }
                            min-elements 1;
                            max-elements 32;
                            description "Groups to exclude when the LSP path is setup";
                        }

                    } // container exclude-admin-group

                    container bfd {
                        when "not(../../type) or ../../type = 'p2p-rsvp' or ../../type = 'p2p-sr-te'" {
                            description "not allowed for this LSP type";
                        }
                        description "Enter the bfd context";

                        leaf bfd-liveness {
                            type boolean;
                            default "false";
                            description "Enable BFD on the RSVP LSP or S-BFD on the SR-TE LSP";
                        }

                        leaf bfd-template {
                            type leafref {
                                path "../../../../../../bfd/bfd-template/name";
                            }
                            description "BFD template to be used by LSP BFD sessions";
                        }

                        leaf lsp-ping-interval {
                            when "not(../../../type) or ../../../type = 'p2p-rsvp'" {
                                description "not allowed for this LSP type";
                            }
                            type union {
                                type uint32 {
                                    range "60..300";
                                }
                                type enumeration {
                                    enum none                           { value 0; }
                                }
                            }
                            units "seconds";
                            default "60";
                            description "Interval for periodic LSP ping for BFD bootstrapping";
                        }

                        leaf wait-for-up-timer {
                            when "not(../../../type) or ../../../type = 'p2p-sr-te' or ../../../type = 'p2p-rsvp'" {
                                description "not allowed for this LSP type";
                            }
                            type uint32 {
                                range "1..60";
                            }
                            units "seconds";
                            default "4";
                            description "Time to wait for BFD to become operationally available";
                        }

                        leaf return-path-label {
                            when "../../../type = 'p2p-sr-te'" {
                                description "not allowed for this LSP type";
                            }
                            type uint32 {
                                range "32..1048575";
                            }
                            description "S-BFD return-path label";
                        }

                    } // container bfd

                } // list primary

                list secondary {
                    when "not(../type) or ../type = 'p2p-rsvp' or ../type = 'p2p-sr-te'" {
                        description "not allowed for this LSP type";
                    }
                    key "path-name";
                    max-elements 8;
                    description "Enter the secondary list instance";

                    leaf path-name {
                        type leafref {
                            path "../../../path/path-name";
                        }
                        description "Path name";
                    }

                    leaf admin-state {
                        type types-sros:admin-state;
                        default "enable";
                        description "Administrative state of the LSP path";
                    }

                    leaf adaptive {
                        when "not(../../type) or ../../type = 'p2p-rsvp' or ../../type = 'p2p-rsvp-bypass' or ../../type = 'p2mp-rsvp'" {
                            description "not allowed for this LSP type";
                        }
                        type boolean;
                        description "Enable make-before-break functionality";
                    }

                    leaf bandwidth {
                        when "not(../../type) or ../../type = 'p2p-rsvp' or ../../type = 'p2mp-rsvp' or ../../type = 'p2p-sr-te'" {
                            description "not allowed for this LSP type";
                        }
                        type types-mpls:lsp-bandwidth;
                        default "0";
                        description "Amount of bandwidth to be reserved";
                    }

                    leaf hop-limit {
                        when "not(../../type) or ../../type = 'p2p-rsvp' or ../../type = 'p2p-rsvp-bypass' or ../../type = 'p2mp-rsvp' or ../../type = 'p2p-sr-te'" {
                            description "not allowed for this LSP type";
                        }
                        type uint32 {
                            range "2..255";
                        }
                        description "Total number of hops that an LSP traverses";
                    }

                    leaf record {
                        when "not(../../type) or ../../type = 'p2p-rsvp' or ../../type = 'p2p-rsvp-bypass' or ../../type = 'p2mp-rsvp'" {
                            description "not allowed for this LSP type";
                        }
                        type boolean;
                        default "true";
                        description "Enable recording of all hops that an LSP path traverses";
                    }

                    leaf record-label {
                        when "not(../../type) or ../../type = 'p2p-rsvp' or ../../type = 'p2p-rsvp-bypass' or ../../type = 'p2mp-rsvp'" {
                            description "not allowed for this LSP type";
                        }
                        type boolean;
                        default "true";
                        description "Enable recording of labels at each node or instance";
                    }

                    leaf class-type {
                        when "not(../../type) or ../../type = 'p2p-rsvp'" {
                            description "not allowed for this LSP type";
                        }
                        type types-mpls:class-type;
                        description "Class-type";
                    }

                    leaf path-preference {
                        when "not(../../type) or ../../type = 'p2p-rsvp' or ../../type = 'p2p-sr-te'" {
                            description "not allowed for this LSP type";
                        }
                        type int32 {
                            range "1..255";
                        }
                        default "255";
                        description "Path preference for the secondary standby path";
                    }

                    leaf srlg {
                        when "not(../../type) or ../../type = 'p2p-rsvp' or ../../type = 'p2p-sr-te'" {
                            description "not allowed for this LSP type";
                        }
                        type boolean;
                        default "false";
                        description "Use SRLG constraint in secondary path computation for an LSP at the head-end LER";
                    }

                    leaf standby {
                        when "not(../../type) or ../../type = 'p2p-rsvp' or ../../type = 'p2p-sr-te'" {
                            description "not allowed for this LSP type";
                        }
                        type boolean;
                        default "false";
                        description "Keep secondary path indefinitely in hot standby state";
                    }

                    leaf-list apply-groups {
                        type leafref {
                            path "../../../../../groups/group/name";
                        }
                        max-elements 8;
                        ordered-by user;
                        description "Apply a configuration group at this level";
                    }

                    leaf-list apply-groups-exclude {
                        type leafref {
                            path "../../../../../groups/group/name";
                        }
                        max-elements 8;
                        ordered-by user;
                        description "Exclude a configuration group at this level";
                    }

                    container priority {
                        when "not(../../type) or ../../type = 'p2p-rsvp' or ../../type = 'p2p-sr-te'" {
                            description "not allowed for this LSP type";
                        }
                        description "Enter the priority context";

                        leaf setup-priority {
                            type types-mpls:priority;
                            default "7";
                            description "Priority when insufficient bandwidth for LSP setup";
                        }

                        leaf hold-priority {
                            type types-mpls:priority;
                            default "0";
                            description "Priority of an LSP session at preemption action";
                        }

                    } // container priority

                    container include-admin-group {
                        when "not(../../type) or ../../type = 'p2p-rsvp' or ../../type = 'p2p-sr-te'" {
                            description "not allowed for this LSP type";
                        }
                        presence "Enable the include-admin-group context";
                        description "Enable the include-admin-group context";

                        leaf-list group {
                            type leafref {
                                path "../../../../../../routing-options/if-attribute/admin-group/group-name";
                            }
                            min-elements 1;
                            max-elements 32;
                            description "Groups that are included when LSP path is setup";
                        }

                    } // container include-admin-group

                    container exclude-admin-group {
                        when "not(../../type) or ../../type = 'p2p-rsvp' or ../../type = 'p2p-sr-te'" {
                            description "not allowed for this LSP type";
                        }
                        presence "Enable the exclude-admin-group context";
                        description "Enable the exclude-admin-group context";

                        leaf-list group {
                            type leafref {
                                path "../../../../../../routing-options/if-attribute/admin-group/group-name";
                            }
                            min-elements 1;
                            max-elements 32;
                            description "Groups to exclude when the LSP path is setup";
                        }

                    } // container exclude-admin-group

                    container bfd {
                        when "not(../../type) or ../../type = 'p2p-rsvp' or ../../type = 'p2p-sr-te'" {
                            description "not allowed for this LSP type";
                        }
                        description "Enter the bfd context";

                        leaf bfd-liveness {
                            type boolean;
                            default "false";
                            description "Enable BFD on the RSVP LSP or S-BFD on the SR-TE LSP";
                        }

                        leaf bfd-template {
                            type leafref {
                                path "../../../../../../bfd/bfd-template/name";
                            }
                            description "BFD template to be used by LSP BFD sessions";
                        }

                        leaf lsp-ping-interval {
                            when "not(../../../type) or ../../../type = 'p2p-rsvp'" {
                                description "not allowed for this LSP type";
                            }
                            type union {
                                type uint32 {
                                    range "60..300";
                                }
                                type enumeration {
                                    enum none                           { value 0; }
                                }
                            }
                            units "seconds";
                            default "60";
                            description "Interval for periodic LSP ping for BFD bootstrapping";
                        }

                        leaf wait-for-up-timer {
                            when "not(../../../type) or ../../../type = 'p2p-sr-te' or ../../../type = 'p2p-rsvp'" {
                                description "not allowed for this LSP type";
                            }
                            type uint32 {
                                range "1..60";
                            }
                            units "seconds";
                            default "4";
                            description "Time to wait for BFD to become operationally available";
                        }

                        leaf return-path-label {
                            when "../../../type = 'p2p-sr-te'" {
                                description "not allowed for this LSP type";
                            }
                            type uint32 {
                                range "32..1048575";
                            }
                            description "S-BFD return-path label";
                        }

                    } // container bfd

                } // list secondary

                list primary-p2mp-instance {
                    when "not(../type) or ../type = 'p2mp-rsvp'" {
                        description "not allowed for this LSP type";
                    }
                    key "instance-name";
                    max-elements 1;
                    description "Enter the primary-p2mp-instance list instance";

                    leaf instance-name {
                        type types-sros:named-item;
                        description "P2MP LSP instance name";
                    }

                    leaf admin-state {
                        type types-sros:admin-state;
                        default "enable";
                        description "Administrative state of the LSP path";
                    }

                    leaf adaptive {
                        when "not(../../type) or ../../type = 'p2p-rsvp' or ../../type = 'p2p-rsvp-bypass' or ../../type = 'p2mp-rsvp'" {
                            description "not allowed for this LSP type";
                        }
                        type boolean;
                        description "Enable make-before-break functionality";
                    }

                    leaf bandwidth {
                        when "not(../../type) or ../../type = 'p2p-rsvp' or ../../type = 'p2mp-rsvp' or ../../type = 'p2p-sr-te'" {
                            description "not allowed for this LSP type";
                        }
                        type types-mpls:lsp-bandwidth;
                        default "0";
                        description "Amount of bandwidth to be reserved";
                    }

                    leaf hop-limit {
                        when "not(../../type) or ../../type = 'p2p-rsvp' or ../../type = 'p2p-rsvp-bypass' or ../../type = 'p2mp-rsvp' or ../../type = 'p2p-sr-te'" {
                            description "not allowed for this LSP type";
                        }
                        type uint32 {
                            range "2..255";
                        }
                        description "Total number of hops that an LSP traverses";
                    }

                    leaf record {
                        when "not(../../type) or ../../type = 'p2p-rsvp' or ../../type = 'p2p-rsvp-bypass' or ../../type = 'p2mp-rsvp'" {
                            description "not allowed for this LSP type";
                        }
                        type boolean;
                        default "true";
                        description "Enable recording of all hops that an LSP path traverses";
                    }

                    leaf record-label {
                        when "not(../../type) or ../../type = 'p2p-rsvp' or ../../type = 'p2p-rsvp-bypass' or ../../type = 'p2mp-rsvp'" {
                            description "not allowed for this LSP type";
                        }
                        type boolean;
                        default "true";
                        description "Enable recording of labels at each node or instance";
                    }

                    leaf-list apply-groups {
                        type leafref {
                            path "../../../../../groups/group/name";
                        }
                        max-elements 8;
                        ordered-by user;
                        description "Apply a configuration group at this level";
                    }

                    leaf-list apply-groups-exclude {
                        type leafref {
                            path "../../../../../groups/group/name";
                        }
                        max-elements 8;
                        ordered-by user;
                        description "Exclude a configuration group at this level";
                    }

                    container priority {
                        when "not(../../type) or ../../type = 'p2mp-rsvp'" {
                            description "not allowed for this LSP type";
                        }
                        description "Enter the priority context";

                        leaf setup-priority {
                            type types-mpls:priority;
                            default "7";
                            description "Priority when insufficient bandwidth for LSP setup";
                        }

                        leaf hold-priority {
                            type types-mpls:priority;
                            default "0";
                            description "Hold priority when not enough bandwidth for LSP setup";
                        }

                    } // container priority

                    container include-admin-group {
                        when "not(../../type) or ../../type = 'p2mp-rsvp'" {
                            description "not allowed for this LSP type";
                        }
                        presence "Enable the include-admin-group context";
                        description "Enable the include-admin-group context";

                        leaf-list group {
                            type leafref {
                                path "../../../../../../routing-options/if-attribute/admin-group/group-name";
                            }
                            min-elements 1;
                            max-elements 32;
                            description "Groups that are included when LSP path is setup";
                        }

                    } // container include-admin-group

                    container exclude-admin-group {
                        when "not(../../type) or ../../type = 'p2mp-rsvp'" {
                            description "not allowed for this LSP type";
                        }
                        presence "Enable the exclude-admin-group context";
                        description "Enable the exclude-admin-group context";

                        leaf-list group {
                            type leafref {
                                path "../../../../../../routing-options/if-attribute/admin-group/group-name";
                            }
                            min-elements 1;
                            max-elements 32;
                            description "Groups to exclude when the LSP path is setup";
                        }

                    } // container exclude-admin-group

                    list s2l-path {
                        when "not(../../type) or ../../type = 'p2mp-rsvp'" {
                            description "not allowed for this LSP type";
                        }
                        key "path-name to";
                        max-elements 650;
                        description "Enter the s2l-path list instance";

                        leaf path-name {
                            type leafref {
                                path "../../../../path/path-name";
                            }
                            description "P2MP LSP name";
                        }

                        leaf to {
                            type types-sros:ip-address;
                            description "System IP address of the egress router";
                        }

                        leaf admin-state {
                            type types-sros:admin-state;
                            default "enable";
                            description "Administrative state of the S2L sub-LSP for a P2MP LSP";
                        }

                        leaf-list apply-groups {
                            type leafref {
                                path "../../../../../../groups/group/name";
                            }
                            max-elements 8;
                            ordered-by user;
                            description "Apply a configuration group at this level";
                        }

                        leaf-list apply-groups-exclude {
                            type leafref {
                                path "../../../../../../groups/group/name";
                            }
                            max-elements 8;
                            ordered-by user;
                            description "Exclude a configuration group at this level";
                        }

                    } // list s2l-path

                } // list primary-p2mp-instance

            } // list lsp

            list auto-lsp {
                key "template-name";
                max-elements 500;
                description "Enter the auto-lsp list instance";

                leaf template-name {
                    type leafref {
                        path "../../lsp-template/template-name";
                    }
                    description "LSP template name";
                }

                leaf-list apply-groups {
                    type leafref {
                        path "../../../../groups/group/name";
                    }
                    max-elements 8;
                    ordered-by user;
                    description "Apply a configuration group at this level";
                }

                leaf-list apply-groups-exclude {
                    type leafref {
                        path "../../../../groups/group/name";
                    }
                    max-elements 8;
                    ordered-by user;
                    description "Exclude a configuration group at this level";
                }

                choice auto-lsp-choice {
                    case one-hop {

                        leaf one-hop {
                            type boolean;
                            default "false";
                            description "Enable one-hop point-to-point LSP automatic signaling";
                        }

                    }
                    case policy {

                        leaf-list policy {
                            type leafref {
                                path "../../../../policy-options/policy-statement/name";
                            }
                            max-elements 5;
                            ordered-by user;
                            description "Peer prefix policy name";
                        }

                    }
                }
            } // list auto-lsp

            list static-lsp {
                key "lsp-name";
                max-elements 1000;
                description "Enter the static-lsp list instance";

                leaf lsp-name {
                    type types-sros:named-item-64;
                    description "Labeled Switch path name";
                }

                leaf metric {
                    type uint32 {
                        range "1..16777215";
                    }
                    sros-ext:auto-restart-to-modify;
                    description "MPLS static LSP metric to select an LSP";
                }

                leaf admin-state {
                    type types-sros:admin-state;
                    default "disable";
                    description "Administrative state of the static LSP";
                }

                leaf to {
                    type types-sros:ipv4-unicast-address;
                    sros-ext:auto-restart-to-modify;
                    description "Destination IP address or the egress router for the LSP";
                }

                leaf-list apply-groups {
                    type leafref {
                        path "../../../../groups/group/name";
                    }
                    max-elements 8;
                    ordered-by user;
                    sros-ext:auto-restart-to-modify;
                    description "Apply a configuration group at this level";
                }

                leaf-list apply-groups-exclude {
                    type leafref {
                        path "../../../../groups/group/name";
                    }
                    max-elements 8;
                    ordered-by user;
                    sros-ext:auto-restart-to-modify;
                    description "Exclude a configuration group at this level";
                }

                container push {
                    presence "Enable the push context";
                    description "Enable the push context";

                    leaf out-label {
                        type union {
                            type uint32 {
                                range "16..1048575";
                            }
                            type enumeration {
                                enum implicit-null-label            { value 3; }
                            }
                        }
                        mandatory true;
                        description "Push specific label onto the top of the outgoing packet's label stack";
                    }

                    leaf next-hop {
                        type types-sros:ipv4-unicast-address;
                        mandatory true;
                        description "IP address for the next hop";
                    }

                    leaf-list apply-groups {
                        type leafref {
                            path "../../../../../groups/group/name";
                        }
                        max-elements 8;
                        ordered-by user;
                        description "Apply a configuration group at this level";
                    }

                    leaf-list apply-groups-exclude {
                        type leafref {
                            path "../../../../../groups/group/name";
                        }
                        max-elements 8;
                        ordered-by user;
                        description "Exclude a configuration group at this level";
                    }

                } // container push

            } // list static-lsp

            container forwarding-policies {
                presence "Enable the forwarding-policies context";
                description "Enable the forwarding-policies context";

                leaf admin-state {
                    type types-sros:admin-state;
                    default "disable";
                    description "Administrative state of MPLS forwarding policies";
                }

                leaf reserved-label-block {
                    type leafref {
                        path "../../../mpls-labels/reserved-label-block/label-block-name";
                    }
                    sros-ext:auto-restart-to-modify;
                    description "Reserved label block";
                }

                leaf-list apply-groups {
                    type leafref {
                        path "../../../../groups/group/name";
                    }
                    max-elements 8;
                    ordered-by user;
                    description "Apply a configuration group at this level";
                }

                leaf-list apply-groups-exclude {
                    type leafref {
                        path "../../../../groups/group/name";
                    }
                    max-elements 8;
                    ordered-by user;
                    description "Exclude a configuration group at this level";
                }

                list forwarding-policy {
                    key "policy-name";
                    max-elements 65536;
                    description "Enter the forwarding-policy list instance";

                    leaf policy-name {
                        type types-sros:named-item-64;
                        description "Forwarding policy name";
                    }

                    leaf admin-state {
                        type types-sros:admin-state;
                        default "disable";
                        description "Administrative state of the MPLS forwarding policy";
                    }

                    leaf binding-label {
                        type types-sros:mpls-label-or-zero;
                        sros-ext:auto-restart-to-modify;
                        description "Binding label";
                    }

                    leaf endpoint {
                        type types-sros:ip-unicast-address;
                        sros-ext:auto-restart-to-modify;
                        description "Configure endpoint address.";
                    }

                    leaf revert-timer {
                        type uint32 {
                            range "1..600";
                        }
                        units "seconds";
                        description "Revert timer";
                    }

                    leaf preference {
                        type uint32 {
                            range "1..255";
                        }
                        sros-ext:auto-restart-to-modify;
                        default "255";
                        description "Preference number";
                    }

                    leaf metric {
                        type uint32 {
                            range "1..16777215";
                        }
                        description "Metric of an MPLS forwarding policy";
                    }

                    leaf tunnel-table-pref {
                        type uint32 {
                            range "1..255";
                        }
                        default "255";
                        description "Tunnel table preference";
                    }

                    leaf-list apply-groups {
                        type leafref {
                            path "../../../../../groups/group/name";
                        }
                        max-elements 8;
                        ordered-by user;
                        description "Apply a configuration group at this level";
                    }

                    leaf-list apply-groups-exclude {
                        type leafref {
                            path "../../../../../groups/group/name";
                        }
                        max-elements 8;
                        ordered-by user;
                        description "Exclude a configuration group at this level";
                    }

                    list next-hop-group {
                        key "index";
                        max-elements 32;
                        description "Enter the next-hop-group list instance";

                        leaf index {
                            type uint32 {
                                range "1..32";
                            }
                            description "Index for next hop group";
                        }

                        leaf admin-state {
                            type types-sros:admin-state;
                            default "disable";
                            description "Administrative state of NHG in MPLS forwarding policy";
                        }

                        leaf resolution-type {
                            type enumeration {
                                enum direct                         { value 1; }
                                enum indirect                       { value 2; }
                            }
                            sros-ext:immutable;
                            mandatory true;
                            description "Resolution type for next hop group";
                        }

                        leaf load-balancing-weight {
                            type uint32 {
                                range "1..max";
                            }
                            description "Load balancing weight of an NHG entry";
                        }

                        leaf-list apply-groups {
                            type leafref {
                                path "../../../../../../groups/group/name";
                            }
                            max-elements 8;
                            ordered-by user;
                            description "Apply a configuration group at this level";
                        }

                        leaf-list apply-groups-exclude {
                            type leafref {
                                path "../../../../../../groups/group/name";
                            }
                            max-elements 8;
                            ordered-by user;
                            description "Exclude a configuration group at this level";
                        }

                        container primary-next-hop {
                            presence "Enable the primary-next-hop context";
                            description "Enable the primary-next-hop context";

                            leaf next-hop {
                                type types-sros:ip-unicast-address;
                                description "Next hop address";
                            }

                            leaf-list apply-groups {
                                type leafref {
                                    path "../../../../../../../groups/group/name";
                                }
                                max-elements 8;
                                ordered-by user;
                                description "Apply a configuration group at this level";
                            }

                            leaf-list apply-groups-exclude {
                                type leafref {
                                    path "../../../../../../../groups/group/name";
                                }
                                max-elements 8;
                                ordered-by user;
                                description "Exclude a configuration group at this level";
                            }

                            list pushed-labels {
                                key "index";
                                max-elements 10;
                                description "Enter the pushed-labels list instance";

                                leaf index {
                                    type uint32 {
                                        range "1..10";
                                    }
                                    description "Index for push label";
                                }

                                leaf label {
                                    type uint32 {
                                        range "1..1048575";
                                    }
                                    mandatory true;
                                    description "Label value";
                                }

                                leaf-list apply-groups {
                                    type leafref {
                                        path "../../../../../../../../groups/group/name";
                                    }
                                    max-elements 8;
                                    ordered-by user;
                                    description "Apply a configuration group at this level";
                                }

                                leaf-list apply-groups-exclude {
                                    type leafref {
                                        path "../../../../../../../../groups/group/name";
                                    }
                                    max-elements 8;
                                    ordered-by user;
                                    description "Exclude a configuration group at this level";
                                }

                            } // list pushed-labels

                        } // container primary-next-hop

                        container backup-next-hop {
                            presence "Enable the backup-next-hop context";
                            description "Enable the backup-next-hop context";

                            leaf next-hop {
                                type types-sros:ip-unicast-address;
                                description "Next hop address";
                            }

                            leaf-list apply-groups {
                                type leafref {
                                    path "../../../../../../../groups/group/name";
                                }
                                max-elements 8;
                                ordered-by user;
                                description "Apply a configuration group at this level";
                            }

                            leaf-list apply-groups-exclude {
                                type leafref {
                                    path "../../../../../../../groups/group/name";
                                }
                                max-elements 8;
                                ordered-by user;
                                description "Exclude a configuration group at this level";
                            }

                            list pushed-labels {
                                key "index";
                                max-elements 10;
                                description "Enter the pushed-labels list instance";

                                leaf index {
                                    type uint32 {
                                        range "1..10";
                                    }
                                    description "Index for push label";
                                }

                                leaf label {
                                    type uint32 {
                                        range "1..1048575";
                                    }
                                    mandatory true;
                                    description "Label value";
                                }

                                leaf-list apply-groups {
                                    type leafref {
                                        path "../../../../../../../../groups/group/name";
                                    }
                                    max-elements 8;
                                    ordered-by user;
                                    description "Apply a configuration group at this level";
                                }

                                leaf-list apply-groups-exclude {
                                    type leafref {
                                        path "../../../../../../../../groups/group/name";
                                    }
                                    max-elements 8;
                                    ordered-by user;
                                    description "Exclude a configuration group at this level";
                                }

                            } // list pushed-labels

                        } // container backup-next-hop

                    } // list next-hop-group

                    container ingress-statistics {
                        presence "Enable the ingress-statistics context";
                        description "Enable the ingress-statistics context";

                        leaf admin-state {
                            type types-sros:admin-state;
                            default "disable";
                            description "Administrative state of egress or ingress statistics";
                        }

                        leaf-list apply-groups {
                            type leafref {
                                path "../../../../../../groups/group/name";
                            }
                            max-elements 8;
                            ordered-by user;
                            description "Apply a configuration group at this level";
                        }

                        leaf-list apply-groups-exclude {
                            type leafref {
                                path "../../../../../../groups/group/name";
                            }
                            max-elements 8;
                            ordered-by user;
                            description "Exclude a configuration group at this level";
                        }

                    } // container ingress-statistics

                    container egress-statistics {
                        presence "Enable the egress-statistics context";
                        description "Enable the egress-statistics context";

                        leaf admin-state {
                            type types-sros:admin-state;
                            default "disable";
                            description "Administrative state of egress or ingress statistics";
                        }

                        leaf-list apply-groups {
                            type leafref {
                                path "../../../../../../groups/group/name";
                            }
                            max-elements 8;
                            ordered-by user;
                            description "Apply a configuration group at this level";
                        }

                        leaf-list apply-groups-exclude {
                            type leafref {
                                path "../../../../../../groups/group/name";
                            }
                            max-elements 8;
                            ordered-by user;
                            description "Exclude a configuration group at this level";
                        }

                    } // container egress-statistics

                } // list forwarding-policy

            } // container forwarding-policies

            container pce-init-lsp {
                presence "Enable the pce-init-lsp context";
                description "Enable the pce-init-lsp context";

                leaf-list apply-groups {
                    type leafref {
                        path "../../../../groups/group/name";
                    }
                    max-elements 8;
                    ordered-by user;
                    description "Apply a configuration group at this level";
                }

                leaf-list apply-groups-exclude {
                    type leafref {
                        path "../../../../groups/group/name";
                    }
                    max-elements 8;
                    ordered-by user;
                    description "Exclude a configuration group at this level";
                }

                container sr-te {
                    presence "Enable the sr-te context";
                    description "Enable the sr-te context";

                    leaf admin-state {
                        type types-sros:admin-state;
                        default "disable";
                        description "Administrative state of SR-TE PCE-initiated LSP support";
                    }

                } // container sr-te

            } // container pce-init-lsp

            container ingress-statistics {
                description "Enter the ingress-statistics context";

                list lsp {
                    key "sender lsp-name";
                    description "Enter the lsp list instance";

                    leaf sender {
                        type types-sros:ip-unicast-address;
                        description "Sender address";
                    }

                    leaf lsp-name {
                        type types-sros:named-item-64;
                        description "LSP name";
                    }

                    leaf collect-stats {
                        type boolean;
                        default "false";
                        description "Collect statistics";
                    }

                    leaf accounting-policy {
                        type leafref {
                            path "../../../../../log/accounting-policy/policy-id";
                        }
                        description "Accounting policy ID";
                    }

                    leaf admin-state {
                        type types-sros:admin-state;
                        default "disable";
                        description "Administrative state of statistics for the LSP";
                    }

                    leaf stat-mode {
                        type enumeration {
                            enum per-fc                         { value 0; }
                            enum aggregate                      { value 1; }
                        }
                        sros-ext:auto-restart-to-modify;
                        description "Stat mode";
                    }

                    leaf-list apply-groups {
                        type leafref {
                            path "../../../../../groups/group/name";
                        }
                        max-elements 8;
                        ordered-by user;
                        description "Apply a configuration group at this level";
                    }

                    leaf-list apply-groups-exclude {
                        type leafref {
                            path "../../../../../groups/group/name";
                        }
                        max-elements 8;
                        ordered-by user;
                        description "Exclude a configuration group at this level";
                    }

                } // list lsp

                list p2mp-template-lsp {
                    key "sender rsvp-session-name";
                    description "Enter the p2mp-template-lsp list instance";

                    leaf sender {
                        type types-sros:ip-unicast-address;
                        description "Sender address";
                    }

                    leaf rsvp-session-name {
                        type types-sros:named-item-64;
                        description "RSVP session name";
                    }

                    leaf collect-stats {
                        type boolean;
                        sros-ext:auto-restart-to-modify;
                        default "false";
                        description "Collect statistics";
                    }

                    leaf accounting-policy {
                        type leafref {
                            path "../../../../../log/accounting-policy/policy-id";
                        }
                        sros-ext:auto-restart-to-modify;
                        description "Accounting policy ID";
                    }

                    leaf admin-state {
                        type types-sros:admin-state;
                        default "disable";
                        description "Administrative state of statistics for the LSP";
                    }

                    leaf stat-mode {
                        type enumeration {
                            enum per-fc                         { value 0; }
                            enum aggregate                      { value 1; }
                        }
                        sros-ext:auto-restart-to-modify;
                        description "Stat mode";
                    }

                    leaf max-stats {
                        type uint32 {
                            range "1..8191";
                        }
                        sros-ext:auto-restart-to-modify;
                        default "8191";
                        description "Maximum number of statistic indices";
                    }

                    leaf-list apply-groups {
                        type leafref {
                            path "../../../../../groups/group/name";
                        }
                        max-elements 8;
                        ordered-by user;
                        sros-ext:auto-restart-to-modify;
                        description "Apply a configuration group at this level";
                    }

                    leaf-list apply-groups-exclude {
                        type leafref {
                            path "../../../../../groups/group/name";
                        }
                        max-elements 8;
                        ordered-by user;
                        sros-ext:auto-restart-to-modify;
                        description "Exclude a configuration group at this level";
                    }

                } // list p2mp-template-lsp

                list p2p-template-lsp {
                    key "sender rsvp-session-name";
                    description "Enter the p2p-template-lsp list instance";

                    leaf sender {
                        type types-sros:ip-unicast-address;
                        description "Sender address";
                    }

                    leaf rsvp-session-name {
                        type types-sros:named-item-64;
                        description "RSVP session name";
                    }

                    leaf collect-stats {
                        type boolean;
                        sros-ext:auto-restart-to-modify;
                        default "false";
                        description "Collect statistics";
                    }

                    leaf accounting-policy {
                        type leafref {
                            path "../../../../../log/accounting-policy/policy-id";
                        }
                        sros-ext:auto-restart-to-modify;
                        description "Accounting policy ID";
                    }

                    leaf admin-state {
                        type types-sros:admin-state;
                        default "disable";
                        description "Administrative state of statistics for the LSP";
                    }

                    leaf stat-mode {
                        type enumeration {
                            enum per-fc                         { value 0; }
                            enum aggregate                      { value 1; }
                        }
                        sros-ext:auto-restart-to-modify;
                        description "Stat mode";
                    }

                    leaf max-stats {
                        type uint32 {
                            range "1..8191";
                        }
                        sros-ext:auto-restart-to-modify;
                        default "8191";
                        description "Maximum number of statistic indices";
                    }

                    leaf-list apply-groups {
                        type leafref {
                            path "../../../../../groups/group/name";
                        }
                        max-elements 8;
                        ordered-by user;
                        sros-ext:auto-restart-to-modify;
                        description "Apply a configuration group at this level";
                    }

                    leaf-list apply-groups-exclude {
                        type leafref {
                            path "../../../../../groups/group/name";
                        }
                        max-elements 8;
                        ordered-by user;
                        sros-ext:auto-restart-to-modify;
                        description "Exclude a configuration group at this level";
                    }

                } // list p2p-template-lsp

            } // container ingress-statistics

            container aux-stats {
                presence "Enable the aux-stats context";
                description "Enable the aux-stats context";

                leaf sr {
                    type boolean;
                    default "false";
                    description "Traffic type count in MPLS statistics table";
                }

            } // container aux-stats

            container sr-te-resignal {
                description "Enter the sr-te-resignal context";

                leaf resignal-timer {
                    type uint32 {
                        range "30..10080";
                    }
                    units "minutes";
                    description "Resignal timer for SR-TE LSPs";
                }

                leaf resignal-on-igp-event {
                    type boolean;
                    default "false";
                    description "Re-optimize SR-TE LSPs upon IGP link events";
                }

                leaf resignal-on-igp-overload {
                    type boolean;
                    default "false";
                    description "Enable resignaling of SR-TE LSPs upon IGP overload";
                }

            } // container sr-te-resignal

            container lsp-history {
                presence "Enable the lsp-history context";
                description "Enable the lsp-history context";

                leaf admin-state {
                    type types-sros:admin-state;
                    default "enable";
                    description "Administrative state of LSP history recording";
                }

            } // container lsp-history

        } // container mpls

    } // grouping conf-router-mpls

}
