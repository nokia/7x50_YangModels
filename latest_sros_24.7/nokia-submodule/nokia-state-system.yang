submodule nokia-state-system {

    yang-version "1.1";

    belongs-to nokia-state { prefix "state"; }

    import ietf-inet-types                { prefix "inet"; }
    import ietf-yang-types                { prefix "yang"; }
    import nokia-sros-yang-extensions     { prefix "sros-ext"; }
    import nokia-types-card               { prefix "types-card"; }
    import nokia-types-lldp               { prefix "types-lldp"; }
    import nokia-types-log                { prefix "types-log"; }
    import nokia-types-operation          { prefix "types-operation"; }
    import nokia-types-qos                { prefix "types-qos"; }
    import nokia-types-sros               { prefix "types-sros"; }
    import nokia-types-system             { prefix "types-system"; }

    include nokia-state-sfm;
    include nokia-state-system-bluetooth;
    include nokia-state-system-bootup;
    include nokia-state-system-cron;
    include nokia-state-system-licensing;
    include nokia-state-system-ptp;
    include nokia-state-system-script-control;
    include nokia-state-system-security;
    include nokia-state-system-telemetry;
    include nokia-state-system-time;

    sros-ext:sros-major-release "rel24";
    organization "Nokia";
    contact
        "Nokia SR OS Support
         Web: <http://www.nokia.com>";
    description
        "Nokia YANG Data model with operational state for system parameters on SR OS based routers.

         Copyright 2016 Nokia. All rights reserved. Reproduction of this document
         is authorized on the condition that the foregoing copyright notice is included.

         This nokia-state-system YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";
    revision "2024-08-23";

    grouping state-system {
        container system {
            description "Enter the system context";

            leaf oper-name {
                type types-sros:named-item-64;
                description "The administrative name that is used by the system.";
            }

            leaf base-mac-address {
                type yang:mac-address;
                description
                    "Indicates the base system ethernet MAC address. Special purpose
                     MAC addresses used by the system software are constructed as
                     offsets from this base address.";
            }

            leaf platform {
                type types-sros:description;
                description
                    "Indicates the model type of the chassis used in
                     this Nokia SROS system.  Chassis types are
                     distinguished by their backplane type.";
            }

            leaf chassis-topology {
                type enumeration {
                    enum standalone                     { value 1; }
                    enum extended                       { value 2; }
                }
                description
                    "Indicates the inter-chassis topology mode in which the system
                     is operating.

                     It indicates how multiple chassis are arrange and operate
                     together as a single system.

                     A value of 'standalone' indicates that the system is comprised
                     of a single physical router chassis.

                     A value of 'extended' (for a 7950 XRS based system) indicates
                     that two router chassis are connected together in a
                     'back-to-back' topology with no additional switch fabric
                     chassis. An extended chassis topology is comprised of two
                     XRS-20 chassis and is also known as an XRS-40 system.";
            }

            leaf kernel-version {
                type string;
                description "Indicates the version of the operating kernel.";
            }

            leaf fabric-speed {
                type enumeration {
                    enum speed-6g                       { value 1; }
                    enum speed-10g                      { value 2; }
                    enum speed-s4                       { value 3; }
                    enum speed-s5                       { value 4; }
                }
                description "Indicates the system fabric speed.";
            }

            leaf temperature-status {
                type enumeration {
                    enum ok                             { value 1; }
                    enum over-temp                      { value 2; }
                }
                description
                    "Indicates the over temperature state of the system.

                     ok        - all physical router chassis are below
                                 the temperature threshold.
                     over-temp - at least one physical router chassis is
                                 above the temperature threshold.";
            }

            leaf fp-generation-fp2 {
                type boolean;
                description "Whether the system contains at least one FP2 based line card.";
            }

            leaf fp-generation-fp3 {
                type boolean;
                description "Whether the system contains at least one FP3 based line card.";
            }

            leaf fp-generation-fp4 {
                type boolean;
                description "Whether the system contains at least one FP4 based line card.";
            }

            leaf fp-generation-vfp {
                type boolean;
                description "Whether the system contains at least one VFP based line card.";
            }

            leaf fp-generation-fp5 {
                type boolean;
                description "Whether the system contains at least one FP5 based line card.";
            }

            leaf system-profile {
                type enumeration {
                    enum none                           { value 0; }
                    enum profile-a                      { value 1; }
                    enum profile-b                      { value 2; }
                }
                description "Configured system profile.";
            }

            leaf active-cpm-slot {
                type types-card:cpm-card-slot;
                description "The value indicates which CPM is in active state.";
            }

            leaf up-time {
                type uint64;
                units "milliseconds";
                description "System uptime";
            }

            leaf current-time {
                type yang:date-and-time;
                description "Current system time.";
            }

            leaf reboot-required {
                type boolean;
                description
                    "The value indicates if a condition exists on the node
                     that requires a manually triggered reboot.";
            }

            leaf reboot-required-reason {
                type bits {
                    bit upgrade-asl-change             { position 0; }
                    bit fp-resource-policy-change      { position 1; }
                    bit bof-configuration-change       { position 2; }
                    bit ptp-configuration-change       { position 3; }
                    bit fp-options-change              { position 4; }
                    bit fp-resource-alloc-change       { position 5; }
                    bit fp-cam-alloc-change            { position 6; }
                }
                description
                    "The value specifies a bitmask that identifies the
                     reason(s) why a reboot is required.";
            }

            leaf boot-good-exec-status {
                type types-system:script-state;
                description
                    "The results of executing the CLI script file specified
                     in 'boot-good-exec'.";
            }

            leaf boot-bad-exec-status {
                type types-system:script-state;
                description
                    "The results of executing the CLI script file specified
                     in 'boot-bad-exec'.";
            }

            container alarms {
                description "Enter the alarms context";

                list active {
                    key "raised-time index";
                    description "Enter the active list instance";

                    leaf raised-time {
                        type yang:date-and-time;
                        description "Date and time when the alarm was raised";
                    }

                    leaf index {
                        type uint32;
                        description "Monotonically increasing index of entries in the alarm list";
                    }

                    leaf severity {
                        type types-log:severity-level;
                        description "ITU perceived severity value";
                    }

                    leaf resource {
                        type string {
                            length "0..80";
                        }
                        description "The affected resource in the system (e.g. Fan 1)";
                    }

                    leaf details {
                        type string {
                            length "0..255";
                        }
                        description "A textual description of the alarm";
                    }

                    container alarm-id {
                        description "Enter the alarm-id context";

                        leaf full-id {
                            type string;
                            description "Compound format of the alarm-id";
                        }

                        container id-components {
                            description "Enter the id-components context";

                            leaf application {
                                type types-log:application-state;
                                description "Identifier for the SR OS application associated with the alarm type";
                            }

                            leaf raising-event-id {
                                type types-log:log-event-id;
                                description "Log event id of the raising log event associated with the alarm type";
                            }

                            leaf alarm-sub-id {
                                type uint32;
                                description "Used to distinguish multiple alarm types that are associated with a single event-id";
                            }

                        } // container id-components

                    } // container alarm-id

                } // list active

                list cleared {
                    key "cleared-time index";
                    description "Enter the cleared list instance";

                    leaf cleared-time {
                        type yang:date-and-time;
                        description "Date and time when the alarm was cleared";
                    }

                    leaf index {
                        type uint32;
                        description "Monotonically increasing index of entries in the alarm list";
                    }

                    leaf severity {
                        type types-log:severity-level;
                        description "ITU perceived severity value";
                    }

                    leaf resource {
                        type string {
                            length "0..80";
                        }
                        description "The affected resource in the system (e.g. Fan 1)";
                    }

                    leaf subject {
                        status obsolete;
                        type string {
                            length "0..32";
                        }
                        description "Affected object for the event (e.g. interface name or port identifier)";
                    }

                    leaf details {
                        type string {
                            length "0..255";
                        }
                        description "A textual description of the alarm";
                    }

                    container alarm-id {
                        description "Enter the alarm-id context";

                        leaf full-id {
                            type string;
                            description "Compound format of the alarm-id";
                        }

                        container id-components {
                            description "Enter the id-components context";

                            leaf application {
                                type types-log:application-state;
                                description "Identifier for the SR OS application associated with the alarm type";
                            }

                            leaf raising-event-id {
                                type types-log:log-event-id;
                                description "Log event id of the raising log event associated with the alarm type";
                            }

                            leaf alarm-sub-id {
                                type uint32;
                                description "Used to distinguish multiple alarm types that are associated with a single event-id";
                            }

                        } // container id-components

                    } // container alarm-id

                } // list cleared

            } // container alarms

            container crypto-module {
                description "Enter the crypto-module context";

                leaf crypto-module-version {
                    type string;
                    description "Indicates the version of the cryptographic module.";
                }

                leaf fips-provider-version {
                    type string;
                    description "Indicates the version of the Federal Information Processing Standards (FIPS) provider.";
                }

                leaf entropy-source-version {
                    type string;
                    description "Indicates the version of the entropy source.";
                }

            } // container crypto-module

            list alarm-contact-input {
                key "input-pin-number";
                description "Enter the alarm-contact-input list instance";

                leaf input-pin-number {
                    type int32 {
                        range "1..4";
                    }
                    description "Alarm contact input pin";
                }

                leaf input-status {
                    type enumeration {
                        enum no-alarm                       { value 1; }
                        enum alarm                          { value 2; }
                    }
                    description
                        "Current input status of the alarm contact input.

                         Values:
                            alarm    - Input pin is triggered (not at the normal state)
                            no-alarm - Input pin is not triggered (at the normal state)";
                }

                leaf last-status-changed {
                    type yang:date-and-time;
                    description "Time that the input pin last changed status.";
                }

            } // list alarm-contact-input

            container fp {
                description "Enter the fp context";

                container options {
                    description "Enter the options context";

                    container qos {
                        description "Enter the qos context";

                        container dscp-transparency {
                            description "Enter the dscp-transparency context";

                            leaf oper-state {
                                type types-sros:enabled-disabled;
                                description "Indicates the DSCP transparency option operational state.";
                            }

                        } // container dscp-transparency

                        container fc-4-profile {
                            description "Enter the fc-4-profile context";

                            leaf oper-state {
                                type types-sros:enabled-disabled;
                                description "Indicates the fc-4-profile option operational state.";
                            }

                        } // container fc-4-profile

                        container mac-classification-criteria {
                            description "Enter the mac-classification-criteria context";

                            leaf oper-state {
                                type types-sros:enabled-disabled;
                                description "Indicates the QOS mac classification criteria operational state.";
                            }

                        } // container mac-classification-criteria

                        container ipv6-classification-criteria {
                            description "Enter the ipv6-classification-criteria context";

                            leaf oper-state {
                                type types-sros:enabled-disabled;
                                description "Indicates the QOS ipv6 classification criteria operational state.";
                            }

                        } // container ipv6-classification-criteria

                        container bum-policers {
                            description "Enter the bum-policers context";

                            leaf oper-state {
                                type types-sros:enabled-disabled;
                                description "Indicates the QOS bum policers operational state.";
                            }

                        } // container bum-policers

                        container shared-policer {
                            description "Enter the shared-policer context";

                            leaf oper-state {
                                type types-sros:enabled-disabled;
                                description "Indicates the QOS shared policer operational state.";
                            }

                        } // container shared-policer

                    } // container qos

                    container mpls {
                        description "Enter the mpls context";

                        container entropy-label {
                            description "Enter the entropy-label context";

                            leaf oper-state {
                                type types-sros:enabled-disabled;
                                description "Indicates the entropy label option operational state.";
                            }

                        } // container entropy-label

                        container fast-switchover {
                            status obsolete;
                            description "Enter the fast-switchover context";

                            leaf oper-state {
                                status obsolete;
                                type types-sros:enabled-disabled;
                                description "Indicates the MPLS fast switchover option operational state.";
                            }

                        } // container fast-switchover

                    } // container mpls

                    container service {
                        description "Enter the service context";

                        container ces {
                            description "Enter the ces context";

                            leaf oper-state {
                                type types-sros:enabled-disabled;
                                description "Indicates the CES service option operational state.";
                            }

                        } // container ces

                        container ring-aps {
                            description "Enter the ring-aps context";

                            leaf oper-state {
                                type types-sros:enabled-disabled;
                                description "Indicates the ring-aps option operational state.";
                            }

                        } // container ring-aps

                        container vpls-evpn-mpls {
                            description "Enter the vpls-evpn-mpls context";

                            leaf oper-state {
                                type types-sros:enabled-disabled;
                                description "Indicates the VPLS-EVPN-MPLS option operational state.";
                            }

                        } // container vpls-evpn-mpls

                    } // container service

                    container mac-filter {
                        status obsolete;
                        description "Enter the mac-filter context";

                        container outer-vlan-priority {
                            status obsolete;
                            description "Enter the outer-vlan-priority context";

                            leaf oper-state {
                                status obsolete;
                                type types-sros:enabled-disabled;
                                description
                                    "Indicates the MAC filter outer VLAN priority option operational state.
                                     This leaf was deprecated in release 22.2 on Nokia SROS series";
                            }

                        } // container outer-vlan-priority

                    } // container mac-filter

                    container router {
                        description "Enter the router context";

                        container ecmp {
                            status obsolete;
                            description "Enter the ecmp context";

                            leaf oper-state {
                                status obsolete;
                                type types-sros:enabled-disabled;
                                description "Indicates the router ECMP option operational state.";
                            }

                        } // container ecmp

                    } // container router

                    container ethernet {
                        description "Enter the ethernet context";

                        container dot1x-host-authentication {
                            description "Enter the dot1x-host-authentication context";

                            leaf oper-state {
                                type types-sros:enabled-disabled;
                                description "Indicates the dot1x-host-authentication operational state.";
                            }

                        } // container dot1x-host-authentication

                    } // container ethernet

                    container ip-filter {
                        description "Enter the ip-filter context";

                        container pbr-redirect {
                            description "Enter the pbr-redirect context";

                            leaf oper-state {
                                type types-sros:enabled-disabled;
                                description "Indicates the pbr-redirect operational state.";
                            }

                        } // container pbr-redirect

                        container stats-collection {
                            description "Enter the stats-collection context";

                            leaf oper-state {
                                type types-sros:enabled-disabled;
                                description "Indicates the stats-collection operational state.";
                            }

                        } // container stats-collection

                    } // container ip-filter

                    container ipv6-filter {
                        description "Enter the ipv6-filter context";

                        container egress {
                            description "Enter the egress context";

                            leaf oper-state {
                                type types-sros:enabled-disabled;
                                description "Indicates the egress ipv6-filter operational state.";
                            }

                        } // container egress

                        container dst-ip-lsb {
                            description "Enter the dst-ip-lsb context";

                            leaf oper-state {
                                type types-sros:enabled-disabled;
                                description "Indicates the dst-ip-lsb operational state.";
                            }

                        } // container dst-ip-lsb

                        container dst-port {
                            description "Enter the dst-port context";

                            leaf oper-state {
                                type types-sros:enabled-disabled;
                                description "Indicates the dst-port operational state.";
                            }

                        } // container dst-port

                        container flow-label {
                            description "Enter the flow-label context";

                            leaf oper-state {
                                type types-sros:enabled-disabled;
                                description "Indicates the flow-label operational state.";
                            }

                        } // container flow-label

                        container next-header {
                            description "Enter the next-header context";

                            leaf oper-state {
                                type types-sros:enabled-disabled;
                                description "Indicates the next-header operational state.";
                            }

                        } // container next-header

                        container pbr-redirect {
                            description "Enter the pbr-redirect context";

                            leaf oper-state {
                                type types-sros:enabled-disabled;
                                description "Indicates the pbr-redirect operational state.";
                            }

                        } // container pbr-redirect

                        container src-port {
                            description "Enter the src-port context";

                            leaf oper-state {
                                type types-sros:enabled-disabled;
                                description "Indicates the src-port operational state.";
                            }

                        } // container src-port

                        container stats-collection {
                            description "Enter the stats-collection context";

                            leaf oper-state {
                                type types-sros:enabled-disabled;
                                description "Indicates the stats-collection operational state.";
                            }

                        } // container stats-collection

                        container tcp-flags {
                            description "Enter the tcp-flags context";

                            leaf oper-state {
                                type types-sros:enabled-disabled;
                                description "Indicates the tcp-flags operational state.";
                            }

                        } // container tcp-flags

                    } // container ipv6-filter


                    container lpm-allocation {
                        status obsolete;
                        description "Enter the lpm-allocation context";

                        container scale-option-1 {
                            status obsolete;
                            description "Enter the scale-option-1 context";

                            leaf oper-state {
                                status obsolete;
                                type types-sros:enabled-disabled;
                                description
                                    "Indicates the scale-option-1 operational state.

                                     This leaf was obsoleted in release 22.2. It was replaced by
                                     system/fp/resource-allocation/lpm/scale-option/oper-state when
                                     key option is 1.";
                            }

                        } // container scale-option-1

                        container scale-option-2 {
                            status obsolete;
                            description "Enter the scale-option-2 context";

                            leaf oper-state {
                                status obsolete;
                                type types-sros:enabled-disabled;
                                description
                                    "Indicates the scale-option-2 operational state.

                                     This leaf was obsoleted in release 22.2. It was replaced by
                                     system/fp/resource-allocation/lpm/scale-option/oper-state when
                                     key option is 2.";
                            }

                        } // container scale-option-2

                        container scale-option-3 {
                            status obsolete;
                            description "Enter the scale-option-3 context";

                            leaf oper-state {
                                status obsolete;
                                type types-sros:enabled-disabled;
                                description
                                    "Indicates the scale-option-3 operational state.

                                     This leaf was obsoleted in release 22.2. It was replaced by
                                     system/fp/resource-allocation/lpm/scale-option/oper-state when
                                     key option is 3.";
                            }

                        } // container scale-option-3

                    } // container lpm-allocation

                } // container options

                container resource-allocation {
                    description "Enter the resource-allocation context";

                    leaf oper-g8032-sap {
                        status obsolete;
                        type uint32 {
                            range "0..4096";
                        }
                        description
                            "Operational Max G8032 SAP entries
                             This leaf was deprecated in release 21.10 on Nokia SROS series
                             It has been replaced by /system/fp/resource-alloction/fec/system-wide/oper-paired.";
                    }

                    container egress-encap {
                        description "Enter the egress-encap context";

                        leaf oper-port-vlan-translation {
                            type enumeration {
                                enum 2k                             { value 1; }
                                enum 4k                             { value 2; }
                                enum 8k                             { value 3; }
                                enum 16k                            { value 4; }
                            }
                            description
                                "Indicates the operational number of egress encapsulated port VLAN
                                 translation entries that have been allocated for the given FP.";
                        }

                        leaf oper-routed {
                            type enumeration {
                                enum 4k                             { value 1; }
                                enum 8k                             { value 2; }
                                enum 12k                            { value 3; }
                            }
                            description
                                "Indicates the operational number of egress encapsulated routable
                                 entries that have been allocated for the given FP.";
                        }

                    } // container egress-encap

                    container filter {
                        description "Enter the filter context";

                        leaf oper-ipv6-number {
                            type uint32 {
                                range "0|2|4|6|8|10";
                            }
                            description "Operational ipv6 filter resource allocated.";
                        }

                        container ingress {
                            description "Enter the ingress context";

                            container ip-filter {
                                description "Enter the ip-filter context";

                                container actions {
                                    description "Enter the actions context";

                                    container drop {
                                        description "Enter the drop context";

                                        leaf oper-state {
                                            type types-sros:enabled-disabled;
                                            description "Indicates the action drop operational state.";
                                        }

                                    } // container drop

                                    container fc {
                                        description "Enter the fc context";

                                        leaf oper-state {
                                            type types-sros:enabled-disabled;
                                            description "Indicates the action fc operational state.";
                                        }

                                    } // container fc

                                    container log {
                                        description "Enter the log context";

                                        leaf oper-state {
                                            type types-sros:enabled-disabled;
                                            description "Indicates the log action operational state.";
                                        }

                                    } // container log

                                    container mirror {
                                        description "Enter the mirror context";

                                        leaf oper-state {
                                            type types-sros:enabled-disabled;
                                            description "Indicates the mirror action operational state.";
                                        }

                                    } // container mirror

                                    container redirect {
                                        description "Enter the redirect context";

                                        leaf oper-state {
                                            type types-sros:enabled-disabled;
                                            description "Indicates the action redirect operational state.";
                                        }

                                    } // container redirect

                                    container stats-collection {
                                        description "Enter the stats-collection context";

                                        leaf oper-state {
                                            type types-sros:enabled-disabled;
                                            description "Indicates the filter statistics collection operational state.";
                                        }

                                    } // container stats-collection

                                } // container actions

                                container match-criteria {
                                    description "Enter the match-criteria context";

                                    container dscp {
                                        description "Enter the dscp context";

                                        leaf oper-state {
                                            type types-sros:enabled-disabled;
                                            description "Indicates the dscp operational state.";
                                        }

                                    } // container dscp

                                    container dst-ip {
                                        description "Enter the dst-ip context";

                                        leaf oper-state {
                                            type types-sros:enabled-disabled;
                                            description "Indicates the destination ip address operational state.";
                                        }

                                    } // container dst-ip

                                    container dst-port {
                                        description "Enter the dst-port context";

                                        leaf oper-state {
                                            type types-sros:enabled-disabled;
                                            description "Indicates the destination port operational state.";
                                        }

                                    } // container dst-port

                                    container icmp-code {
                                        description "Enter the icmp-code context";

                                        leaf oper-state {
                                            type types-sros:enabled-disabled;
                                            description "Indicates the icmp-code operational state.";
                                        }

                                    } // container icmp-code

                                    container icmp-type {
                                        description "Enter the icmp-type context";

                                        leaf oper-state {
                                            type types-sros:enabled-disabled;
                                            description "Indicates the icmp-type operational state.";
                                        }

                                    } // container icmp-type

                                    container protocol {
                                        description "Enter the protocol context";

                                        leaf oper-state {
                                            type types-sros:enabled-disabled;
                                            description "Indicates the protocol operational state.";
                                        }

                                    } // container protocol

                                    container src-ip {
                                        description "Enter the src-ip context";

                                        leaf oper-state {
                                            type types-sros:enabled-disabled;
                                            description "Indicates the source ip address operational state.";
                                        }

                                    } // container src-ip

                                    container src-port {
                                        description "Enter the src-port context";

                                        leaf oper-state {
                                            type types-sros:enabled-disabled;
                                            description "Indicates the source port operational state.";
                                        }

                                    } // container src-port

                                    container tcp-flags {
                                        description "Enter the tcp-flags context";

                                        leaf oper-state {
                                            type types-sros:enabled-disabled;
                                            description "Indicates the tcp flags operational state.";
                                        }

                                    } // container tcp-flags

                                    container tcp-flags-ext {
                                        description "Enter the tcp-flags-ext context";

                                        leaf oper-state {
                                            type types-sros:enabled-disabled;
                                            description "Indicates the tcp flags ext operational state.";
                                        }

                                    } // container tcp-flags-ext

                                } // container match-criteria

                            } // container ip-filter

                            container ipv6-filter {
                                description "Enter the ipv6-filter context";

                                container actions {
                                    description "Enter the actions context";

                                    container drop {
                                        description "Enter the drop context";

                                        leaf oper-state {
                                            type types-sros:enabled-disabled;
                                            description "Indicates the action drop operational state.";
                                        }

                                    } // container drop

                                    container fc {
                                        description "Enter the fc context";

                                        leaf oper-state {
                                            type types-sros:enabled-disabled;
                                            description "Indicates the action fc operational state.";
                                        }

                                    } // container fc

                                    container log {
                                        description "Enter the log context";

                                        leaf oper-state {
                                            type types-sros:enabled-disabled;
                                            description "Indicates the log action operational state.";
                                        }

                                    } // container log

                                    container mirror {
                                        description "Enter the mirror context";

                                        leaf oper-state {
                                            type types-sros:enabled-disabled;
                                            description "Indicates the mirror action operational state.";
                                        }

                                    } // container mirror

                                    container redirect {
                                        description "Enter the redirect context";

                                        leaf oper-state {
                                            type types-sros:enabled-disabled;
                                            description "Indicates the action redirect operational state.";
                                        }

                                    } // container redirect

                                    container stats-collection {
                                        description "Enter the stats-collection context";

                                        leaf oper-state {
                                            type types-sros:enabled-disabled;
                                            description "Indicates the filter statistics collection operational state.";
                                        }

                                    } // container stats-collection

                                } // container actions

                                container match-criteria {
                                    description "Enter the match-criteria context";

                                    container dscp {
                                        description "Enter the dscp context";

                                        leaf oper-state {
                                            type types-sros:enabled-disabled;
                                            description "Indicates the dscp operational state.";
                                        }

                                    } // container dscp

                                    container dst-ip-lsb {
                                        description "Enter the dst-ip-lsb context";

                                        leaf oper-state {
                                            type types-sros:enabled-disabled;
                                            description "Indicates the destination ip least significant bit operational state.";
                                        }

                                    } // container dst-ip-lsb

                                    container dst-ip-msb {
                                        description "Enter the dst-ip-msb context";

                                        leaf oper-state {
                                            type types-sros:enabled-disabled;
                                            description "Indicates the destination ip most significant bit operational state.";
                                        }

                                    } // container dst-ip-msb

                                    container dst-port {
                                        description "Enter the dst-port context";

                                        leaf oper-state {
                                            type types-sros:enabled-disabled;
                                            description "Indicates the destination port operational state.";
                                        }

                                    } // container dst-port

                                    container flow-label {
                                        description "Enter the flow-label context";

                                        leaf oper-state {
                                            type types-sros:enabled-disabled;
                                            description "Indicates the flow-label operational state.";
                                        }

                                    } // container flow-label

                                    container icmp-code {
                                        description "Enter the icmp-code context";

                                        leaf oper-state {
                                            type types-sros:enabled-disabled;
                                            description "Indicates the icmp-code operational state.";
                                        }

                                    } // container icmp-code

                                    container icmp-type {
                                        description "Enter the icmp-type context";

                                        leaf oper-state {
                                            type types-sros:enabled-disabled;
                                            description "Indicates the icmp-type operational state.";
                                        }

                                    } // container icmp-type

                                    container next-header {
                                        description "Enter the next-header context";

                                        leaf oper-state {
                                            type types-sros:enabled-disabled;
                                            description "Indicates the next-header operational state.";
                                        }

                                    } // container next-header

                                    container src-ip-lsb {
                                        description "Enter the src-ip-lsb context";

                                        leaf oper-state {
                                            type types-sros:enabled-disabled;
                                            description "Indicates the source ip least significant bit operational state.";
                                        }

                                    } // container src-ip-lsb

                                    container src-ip-msb {
                                        description "Enter the src-ip-msb context";

                                        leaf oper-state {
                                            type types-sros:enabled-disabled;
                                            description "Indicates the source ip most significant bit operational state.";
                                        }

                                    } // container src-ip-msb

                                    container src-port {
                                        description "Enter the src-port context";

                                        leaf oper-state {
                                            type types-sros:enabled-disabled;
                                            description "Indicates the source port operational state.";
                                        }

                                    } // container src-port

                                    container tcp-flags {
                                        description "Enter the tcp-flags context";

                                        leaf oper-state {
                                            type types-sros:enabled-disabled;
                                            description "Indicates the tcp flags operational state.";
                                        }

                                    } // container tcp-flags

                                    container tcp-flags-ext {
                                        description "Enter the tcp-flags-ext context";

                                        leaf oper-state {
                                            type types-sros:enabled-disabled;
                                            description "Indicates the tcp flags ext operational state.";
                                        }

                                    } // container tcp-flags-ext

                                } // container match-criteria

                            } // container ipv6-filter

                        } // container ingress

                        container egress {
                            description "Enter the egress context";

                            container ip-filter {
                                description "Enter the ip-filter context";

                                container actions {
                                    description "Enter the actions context";

                                    container drop {
                                        description "Enter the drop context";

                                        leaf oper-state {
                                            type types-sros:enabled-disabled;
                                            description "Indicates the action drop operational state.";
                                        }

                                    } // container drop

                                    container stats-collection {
                                        description "Enter the stats-collection context";

                                        leaf oper-state {
                                            type types-sros:enabled-disabled;
                                            description "Indicates the filter statistics collection operational state.";
                                        }

                                    } // container stats-collection

                                } // container actions

                                container match-criteria {
                                    description "Enter the match-criteria context";

                                    container dscp {
                                        description "Enter the dscp context";

                                        leaf oper-state {
                                            type types-sros:enabled-disabled;
                                            description "Indicates the dscp operational state.";
                                        }

                                    } // container dscp

                                    container dst-ip {
                                        description "Enter the dst-ip context";

                                        leaf oper-state {
                                            type types-sros:enabled-disabled;
                                            description "Indicates the destination ip address operational state.";
                                        }

                                    } // container dst-ip

                                    container dst-port {
                                        description "Enter the dst-port context";

                                        leaf oper-state {
                                            type types-sros:enabled-disabled;
                                            description "Indicates the destination port operational state.";
                                        }

                                    } // container dst-port

                                    container icmp-code {
                                        description "Enter the icmp-code context";

                                        leaf oper-state {
                                            type types-sros:enabled-disabled;
                                            description "Indicates the icmp-code operational state.";
                                        }

                                    } // container icmp-code

                                    container icmp-type {
                                        description "Enter the icmp-type context";

                                        leaf oper-state {
                                            type types-sros:enabled-disabled;
                                            description "Indicates the icmp-type operational state.";
                                        }

                                    } // container icmp-type

                                    container protocol {
                                        description "Enter the protocol context";

                                        leaf oper-state {
                                            type types-sros:enabled-disabled;
                                            description "Indicates the protocol operational state.";
                                        }

                                    } // container protocol

                                    container src-ip {
                                        description "Enter the src-ip context";

                                        leaf oper-state {
                                            type types-sros:enabled-disabled;
                                            description "Indicates the source ip address operational state.";
                                        }

                                    } // container src-ip

                                    container src-port {
                                        description "Enter the src-port context";

                                        leaf oper-state {
                                            type types-sros:enabled-disabled;
                                            description "Indicates the source port operational state.";
                                        }

                                    } // container src-port

                                    container tcp-flags {
                                        description "Enter the tcp-flags context";

                                        leaf oper-state {
                                            type types-sros:enabled-disabled;
                                            description "Indicates the tcp flags operational state.";
                                        }

                                    } // container tcp-flags

                                    container tcp-flags-ext {
                                        description "Enter the tcp-flags-ext context";

                                        leaf oper-state {
                                            type types-sros:enabled-disabled;
                                            description "Indicates the tcp flags ext operational state.";
                                        }

                                    } // container tcp-flags-ext

                                } // container match-criteria

                            } // container ip-filter

                            container ipv6-filter {
                                description "Enter the ipv6-filter context";

                                container actions {
                                    description "Enter the actions context";

                                    container drop {
                                        description "Enter the drop context";

                                        leaf oper-state {
                                            type types-sros:enabled-disabled;
                                            description "Indicates the action drop operational state.";
                                        }

                                    } // container drop

                                    container stats-collection {
                                        description "Enter the stats-collection context";

                                        leaf oper-state {
                                            type types-sros:enabled-disabled;
                                            description "Indicates the filter statistics collection operational state.";
                                        }

                                    } // container stats-collection

                                } // container actions

                                container match-criteria {
                                    description "Enter the match-criteria context";

                                    container dscp {
                                        description "Enter the dscp context";

                                        leaf oper-state {
                                            type types-sros:enabled-disabled;
                                            description "Indicates the dscp operational state.";
                                        }

                                    } // container dscp

                                    container dst-ip-lsb {
                                        description "Enter the dst-ip-lsb context";

                                        leaf oper-state {
                                            type types-sros:enabled-disabled;
                                            description "Indicates the destination ip least significant bit operational state.";
                                        }

                                    } // container dst-ip-lsb

                                    container dst-ip-msb {
                                        description "Enter the dst-ip-msb context";

                                        leaf oper-state {
                                            type types-sros:enabled-disabled;
                                            description "Indicates the destination ip most significant bit operational state.";
                                        }

                                    } // container dst-ip-msb

                                    container dst-port {
                                        description "Enter the dst-port context";

                                        leaf oper-state {
                                            type types-sros:enabled-disabled;
                                            description "Indicates the destination port operational state.";
                                        }

                                    } // container dst-port

                                    container flow-label {
                                        description "Enter the flow-label context";

                                        leaf oper-state {
                                            type types-sros:enabled-disabled;
                                            description "Indicates the flow-label operational state.";
                                        }

                                    } // container flow-label

                                    container icmp-code {
                                        description "Enter the icmp-code context";

                                        leaf oper-state {
                                            type types-sros:enabled-disabled;
                                            description "Indicates the icmp-code operational state.";
                                        }

                                    } // container icmp-code

                                    container icmp-type {
                                        description "Enter the icmp-type context";

                                        leaf oper-state {
                                            type types-sros:enabled-disabled;
                                            description "Indicates the icmp-type operational state.";
                                        }

                                    } // container icmp-type

                                    container next-header {
                                        description "Enter the next-header context";

                                        leaf oper-state {
                                            type types-sros:enabled-disabled;
                                            description "Indicates the next-header operational state.";
                                        }

                                    } // container next-header

                                    container src-ip-lsb {
                                        description "Enter the src-ip-lsb context";

                                        leaf oper-state {
                                            type types-sros:enabled-disabled;
                                            description "Indicates the source ip least significant bit operational state.";
                                        }

                                    } // container src-ip-lsb

                                    container src-ip-msb {
                                        description "Enter the src-ip-msb context";

                                        leaf oper-state {
                                            type types-sros:enabled-disabled;
                                            description "Indicates the source ip most significant bit operational state.";
                                        }

                                    } // container src-ip-msb

                                    container src-port {
                                        description "Enter the src-port context";

                                        leaf oper-state {
                                            type types-sros:enabled-disabled;
                                            description "Indicates the source port operational state.";
                                        }

                                    } // container src-port

                                    container tcp-flags {
                                        description "Enter the tcp-flags context";

                                        leaf oper-state {
                                            type types-sros:enabled-disabled;
                                            description "Indicates the tcp flags operational state.";
                                        }

                                    } // container tcp-flags

                                    container tcp-flags-ext {
                                        description "Enter the tcp-flags-ext context";

                                        leaf oper-state {
                                            type types-sros:enabled-disabled;
                                            description "Indicates the tcp flags ext operational state.";
                                        }

                                    } // container tcp-flags-ext

                                } // container match-criteria

                            } // container ipv6-filter

                        } // container egress

                    } // container filter

                    container statistics {
                        description "Enter the statistics context";

                        container policer {
                            description "Enter the policer context";

                            leaf oper-banks {
                                type uint32 {
                                    range "0|1|2|4";
                                }
                                description "Operational policer stats resource allocated.";
                            }

                            leaf oper-dedicated-fc-policers {
                                type uint32 {
                                    range "0..10816";
                                }
                                description
                                    "Operational value of number of stats allocated for dedicated
                                     fc policers";
                            }

                        } // container policer

                        container filter {
                            description "Enter the filter context";

                            leaf oper-ingress-banks {
                                type uint32 {
                                    range "0..4";
                                }
                                description "Operational ingress filter stats resource allocated.";
                            }

                            leaf oper-egress-banks {
                                type uint32 {
                                    range "0..4";
                                }
                                description "Operational egress filter stats resource allocated.";
                            }

                        } // container filter

                    } // container statistics

                    list pool {
                        key "pool-id";
                        description "Enter the pool list instance";

                        leaf pool-id {
                            type uint32 {
                                range "1..2";
                            }
                            description "Pool identifier";
                        }

                        container lag-bundle {
                            description "Enter the lag-bundle context";

                            leaf oper-reserved-member-count {
                                type uint32;
                                description "Indicates the operational member count reserved for the lag-bundle.";
                            }

                        } // container lag-bundle

                    } // list pool

                    container fec {
                        description "Enter the fec context";

                        container system-wide {
                            description "Enter the system-wide context";

                            leaf oper-unpaired {
                                type uint32;
                                description "Indicates the operational number of system-wide unpaired FEC space.";
                            }

                            leaf oper-paired {
                                type uint32 {
                                    range "0..8192";
                                }
                                description "Indicates the operational number of paired FEC space.";
                            }

                        } // container system-wide

                    } // container fec

                    container lpm {
                        description "Enter the lpm context";

                        list scale-option {
                            key "option";
                            description "Enter the scale-option list instance";

                            leaf option {
                                type uint32 {
                                    range "1..4";
                                }
                                description "Unique LPM (FIB) scale option";
                            }

                            leaf oper-state {
                                type types-sros:enabled-disabled;
                                description "Indicates the operational state of the LPM scale option.";
                            }

                        } // list scale-option

                    } // container lpm

                    container policer-and-statistics-override {
                        description "Enter the policer-and-statistics-override context";

                        leaf oper-state {
                            type types-sros:oper-state;
                            description "Oper state of policer-and-statistics override.";
                        }

                        list bank {
                            key "bank-name";
                            description "Enter the bank list instance";

                            leaf bank-name {
                                type enumeration {
                                    enum dual-mode-16k-bank-1           { value 1; }
                                    enum dual-mode-16k-bank-2           { value 2; }
                                    enum dual-mode-16k-bank-3           { value 3; }
                                    enum dual-mode-16k-bank-4           { value 4; }
                                    enum dual-mode-16k-bank-5           { value 5; }
                                    enum dual-mode-16k-bank-6           { value 6; }
                                }
                                description "Bank name";
                            }

                            container application {
                                description "Enter the application context";

                                leaf oper-group {
                                    type int32 {
                                        range "1..3";
                                    }
                                    description "Specifies the operational group.";
                                }

                                leaf oper-binding {
                                    type enumeration {
                                        enum policer                        { value 1; }
                                        enum statistics                     { value 2; }
                                    }
                                    description "Specifies the operational binding.";
                                }

                            } // container application

                        } // list bank

                        container application-group {
                            description "Enter the application-group context";

                            list group {
                                key "group-id";
                                description "Enter the group list instance";

                                leaf policer-admin-total {
                                    type uint32;
                                    description "Indicates the admin value of total number of policers in the application group.";
                                }

                                leaf policer-oper-total {
                                    type uint32;
                                    description "Indicates the oper value of total number of policers in the application group.";
                                }

                                leaf policer-admin-alloc {
                                    type uint32;
                                    description "Indicates the admin value of allocated number of policers in the application group.";
                                }

                                leaf policer-oper-alloc {
                                    type uint32;
                                    description "Indicates the oper value of allocated number of policers in the application group.";
                                }

                                leaf group-id {
                                    type uint32 {
                                        range "1..3";
                                    }
                                    description "Application group ID";
                                }

                                container policers {
                                    description "Enter the policers context";

                                    list application {
                                        key "application-id";
                                        description "Enter the application list instance";

                                        leaf application-id {
                                            type enumeration {
                                                enum per-fc-unicast-broadcast-unknown-multicast { value 1; }
                                                enum per-fc-unicast-multipoint      { value 2; }
                                                enum per-fc                         { value 3; }
                                                enum per-2-fc-unicast-multipoint    { value 4; }
                                                enum per-4-fc-unicast-multipoint    { value 5; }
                                                enum per-2-fc                       { value 6; }
                                                enum per-4-fc                       { value 7; }
                                                enum aggregate-policers             { value 8; }
                                                enum shared-policers                { value 9; }
                                            }
                                            description "FC policer type";
                                        }

                                        leaf oper-scale {
                                            type int32 {
                                                range "-1..96";
                                            }
                                            description "Indicates the scale of the application.";
                                        }

                                    } // list application

                                } // container policers

                                container statistics {
                                    description "Enter the statistics context";

                                    list application {
                                        key "application-id";
                                        description "Enter the application list instance";

                                        leaf application-id {
                                            type enumeration {
                                                enum aggregate-policers             { value 8; }
                                                enum shared-policers                { value 9; }
                                                enum fc-policers                    { value 10; }
                                            }
                                            description "FC policer type";
                                        }

                                        leaf oper-scale {
                                            type int32 {
                                                range "-1..96";
                                            }
                                            description "Indicates the scale of the application.";
                                        }

                                    } // list application

                                } // container statistics

                            } // list group

                        } // container application-group

                    } // container policer-and-statistics-override

                    container segment-routing-v6 {
                        description "Enter the segment-routing-v6 context";

                        container tunnel-termination {
                            description "Enter the tunnel-termination context";

                            leaf oper-entries {
                                type uint32 {
                                    range "256|1024|2048";
                                }
                                description
                                    "Operational value of the maximum number of
                                     SRv6 tunnel termination TCAM entries on the system.";
                            }

                        } // container tunnel-termination

                    } // container segment-routing-v6

                } // container resource-allocation

            } // container fp

            container grpc {
                description "Enter the grpc context";

                leaf oper-state {
                    type types-sros:oper-state;
                    description "Operational state of gRPC server.";
                }

                leaf oper-down-reason {
                    type enumeration {
                        enum admin-down                     { value 1; }
                        enum listen-port-unavailable        { value 2; }
                        enum active-delay-on-boot           { value 3; }
                    }
                    description "The reason due to which gRPC server is operationally down.";
                }

                container gnoi {
                    description "Enter the gnoi context";

                    container system {
                        description "Enter the system context";

                        list pending-reboot {
                            key "sub-component";
                            description "Enter the pending-reboot list instance";

                            leaf sub-component {
                                type string;
                                description "Object of Reboot or Cancel Reboot RPC.";
                            }

                            leaf oper-state {
                                type types-sros:oper-state;
                                description "Operational state of reboot procedure.";
                            }

                            leaf reboot-delay {
                                type uint32;
                                units "seconds";
                                description "Time left until reboot.";
                            }

                            leaf last-reboot-message {
                                type string;
                                description "Reason for reboot or for cancelation of any outstanding reboot.";
                            }

                            leaf reboot-count {
                                type uint32;
                                description "Number of reboots since active.";
                            }

                        } // list pending-reboot

                    } // container system

                } // container gnoi

                list connection {
                    key "address port";
                    description "Enter the connection list instance";

                    leaf address {
                        type types-sros:ip-address;
                        description "IP address of gRPC client.";
                    }

                    leaf port {
                        type inet:port-number;
                        description "Protocol port number of gRPC client.";
                    }

                    leaf router-instance {
                        type types-sros:router-instance;
                        description "The value indicates the routing context of a connection.";
                    }

                    leaf grpc-tunnel {
                        type leafref {
                            path "../../../grpc-tunnel/tunnel/name";
                        }
                        description "The value indicates the gRPC-Tunnel used as transport of a connection.";
                    }

                    leaf establishment-time {
                        type yang:date-and-time;
                        description "The value indicates the time of connection establishment.";
                    }

                    leaf active-rpc-count {
                        type yang:gauge64;
                        description "The value indicates the active number of RPC on this connection.";
                    }

                    leaf total-rpc-count {
                        type yang:counter64;
                        description
                            "The value indicates the total number of RPC on this connection
                             since establishment time.";
                    }

                    leaf rx-bytes {
                        type yang:counter64;
                        units "bytes";
                        description "The value indicates the total number of bytes received over this connection.";
                    }

                    leaf tx-bytes {
                        type yang:counter64;
                        units "bytes";
                        description "The value indicates the total number of bytes sent over this connection.";
                    }

                    leaf qos {
                        type types-qos:dscp-name;
                        description
                            "Operational DSCP value of the connection. Only first Subscribe RPC with qos
                             field specified can alter connection DSCP value. DSCP value is reset to
                             sgt-qos default after last Subscribe RPC on connection is terminated.";
                    }

                    container last-finished-rpc {
                        description "Enter the last-finished-rpc context";

                        leaf name {
                            type types-sros:named-item;
                            description "The value indicates the name of a RPC.";
                        }

                        leaf service-name {
                            type types-sros:named-item;
                            description "The value indicates the name of a RPC service.";
                        }

                        leaf duration {
                            type types-sros:time-duration-64;
                            units "milliseconds";
                            description "The value indicates duration of a RPC in milliseconds.";
                        }

                        leaf finish-time {
                            type yang:date-and-time;
                            description "The value indicates the time of a RPC finish.";
                        }

                        leaf error-rpc-status {
                            type string {
                                length "1..256";
                            }
                            description "The value indicates the error message in a RPC status.";
                        }

                    } // container last-finished-rpc

                } // list connection

                list rpc {
                    key "rpc-id";
                    description "Enter the rpc list instance";

                    leaf rpc-id {
                        type uint32;
                        description
                            "The value of this object uniquely identifies a RPC.
                             Id is auto-generated by the system.";
                    }

                    leaf name {
                        type types-sros:named-item;
                        description "The value indicates the name of a RPC.";
                    }

                    leaf service-name {
                        type types-sros:named-item;
                        description "The value indicates the name of a RPC service.";
                    }

                    leaf establishment-time {
                        type yang:date-and-time;
                        description "The value indicates the time of a RPC establishment.";
                    }

                    leaf address {
                        type types-sros:ip-address;
                        description "IP address of gRPC client who sent a RPC.";
                    }

                    leaf port {
                        type inet:port-number;
                        description "Protocol port number of gRPC client who sent a RPC.";
                    }

                    leaf grpc-tunnel {
                        type leafref {
                            path "../../../grpc-tunnel/tunnel/name";
                        }
                        description "The value indicates the gRPC-Tunnel used as transport of a RPC.";
                    }

                    leaf user-name {
                        type types-sros:named-item;
                        description "The name of the user who sent a RPC.";
                    }

                    leaf session-id {
                        type uint32;
                        description
                            "The session-id of the user who sent a RPC.
                             Id is auto-generated by the system.";
                    }

                } // list rpc

                container supported-services {
                    description "Enter the supported-services context";

                    leaf gnmi-version {
                        type string {
                            length "1..10";
                        }
                        description "Indicates the version of gNMI service provided by gRPC server.";
                    }

                    leaf gnoi-cert-mgmt-version {
                        type string {
                            length "1..10";
                        }
                        description "Indicates the version of gNOI CertificateManagement service provided by gRPC server.";
                    }

                    leaf gnoi-file-version {
                        type string {
                            length "1..10";
                        }
                        description "Indicates the version of gNOI File service provided by gRPC server.";
                    }

                    leaf gnoi-system-version {
                        type string {
                            length "1..10";
                        }
                        description "Indicates the version of gNOI System service provided by gRPC server.";
                    }

                    leaf md-cli-version {
                        type string {
                            length "1..10";
                        }
                        description "Indicates the version of MD-CLI service provided by gRPC server.";
                    }

                    leaf rib-api-version {
                        type string {
                            length "1..10";
                        }
                        description "Indicates the version of RibApi service provided by gRPC server.";
                    }

                } // container supported-services

            } // container grpc

            container grpc-tunnel {
                description "Enter the grpc-tunnel context";

                list tunnel {
                    key "name";
                    description "Enter the tunnel list instance";

                    leaf name {
                        type types-sros:named-item;
                        description "Tunnel name";
                    }

                    leaf oper-state {
                        type types-sros:oper-state;
                        description "Operational state of tunnel.";
                    }

                    leaf oper-down-reason {
                        type string {
                            length "1..256";
                        }
                        description "The reason due to which tunnel is operationally down.";
                    }

                    leaf oper-target-name {
                        type string {
                            length "1..422";
                        }
                        description "Operational target string to be sent in tunnel capability message.";
                    }

                    container statistics {
                        description "Enter the statistics context";

                        list destination {
                            key "address port";
                            description "Enter the destination list instance";

                            leaf address {
                                type union {
                                    type types-sros:ip-address;
                                    type types-sros:fully-qualified-domain-name;
                                }
                                description "Address of the destination within the destination group";
                            }

                            leaf port {
                                type types-sros:tcp-udp-port-non-zero;
                                description "TCP port number for the destination";
                            }

                            leaf oper-state {
                                type types-sros:oper-state;
                                description "Operational state of destination.";
                            }

                            leaf last-oper-down-reason {
                                type string {
                                    length "1..256";
                                }
                                description
                                    "The reason due to which connection to destination
                                     was operationally down.";
                            }

                            leaf oper-router-instance {
                                type types-sros:router-instance;
                                description "Operational routing context of a connection.";
                            }

                            leaf last-oper-change {
                                type yang:date-and-time;
                                description "The time when the operational state of this destination last changed.";
                            }

                            leaf connection-attempts {
                                type uint64;
                                description "Number of tried connections towards this destination.";
                            }

                        } // list destination

                        list session {
                            key "tag";
                            description "Enter the session list instance";

                            leaf tag {
                                type int32;
                                description
                                    "The value of this object uniquely identifies session in a tunnel.
                                     Tag is auto-generated by the gRPC-Tunnel server.";
                            }

                            leaf establishment-time {
                                type yang:date-and-time;
                                description "The value indicates the time of a session establishment.";
                            }

                            leaf target-type {
                                type string {
                                    length "1..64";
                                }
                                description "The value indicates requested target-type of the session.";
                            }

                            leaf local-source-port {
                                type types-sros:tcp-udp-port-non-zero;
                                description
                                    "The value indicates source protocol TCP port number of the session
                                     connection towards target aplication.";
                            }

                            leaf rx-bytes {
                                type yang:counter64;
                                units "bytes";
                                description "The value indicates the total number of bytes received over this session.";
                            }

                            leaf tx-bytes {
                                type yang:counter64;
                                units "bytes";
                                description "The value indicates the total number of bytes sent over this session.";
                            }

                        } // list session

                    } // container statistics

                } // list tunnel

            } // container grpc-tunnel

            container management-interface {
                description "Enter the management-interface context";

                leaf configuration-oper-mode {
                    type enumeration {
                        enum syncing                        { value 0; }
                        enum classic                        { value 1; }
                        enum model-driven                   { value 2; }
                        enum mixed                          { value 3; }
                    }
                    description
                        "The operational state of the management interface
                         configuration mode of the system.";
                }

                leaf last-mode-switch {
                    type yang:date-and-time;
                    description "The time the last configuration mode changed for the system.";
                }

                leaf last-mode-switch-reason {
                    type enumeration {
                        enum boot                           { value 0; }
                        enum manual                         { value 1; }
                        enum validation                     { value 2; }
                    }
                    description
                        "The reason a mode switch occurred. It could be one of
                         boot, manual, or validation.";
                }

                leaf last-mode-switch-duration {
                    type uint32;
                    units "milliseconds";
                    description
                        "The duration, in milliseconds, the last configuration mode
                         change took to activate.";
                }

                leaf primary-schema-path {
                    status obsolete;
                    type types-system:schema-path-state-type;
                    description
                        "Location of schema files derived from primary-image.
                         This leaf was obsoleted in release 24.3.";
                }

                leaf secondary-schema-path {
                    status obsolete;
                    type types-system:schema-path-state-type;
                    description
                        "Location of schema files derived from secondary-image.
                         This leaf was obsoleted in release 24.3.";
                }

                leaf tertiary-schema-path {
                    status obsolete;
                    type types-system:schema-path-state-type;
                    description
                        "Location of schema files derived from tertiary-image.
                         This leaf was obsoleted in release 24.3.";
                }

                leaf oper-schema-path {
                    type types-system:schema-path-state-type;
                    description "Operational location of schema files used by the system.";
                }

                container cli {
                    description "Enter the cli context";

                    container classic-cli {
                        description "Enter the classic-cli context";

                        container rollback {
                            description "Enter the rollback context";

                            container save {
                                description "Enter the save context";

                                leaf last-save-result {
                                    type types-system:action-result;
                                    description "The result of the last rollback save action.";
                                }

                                leaf last-save-completion-time {
                                    type yang:date-and-time;
                                    description
                                        "The time when the last rollback save was
                                         completed on the system.";
                                }

                            } // container save

                            container revert {
                                description "Enter the revert context";

                                leaf last-revert-index {
                                    type uint32 {
                                        range "0..199";
                                    }
                                    description "The last rollback checkpoint file reverted on the system.";
                                }

                                leaf last-revert-checkpoint-file {
                                    type types-sros:url;
                                    description "The filepath or file-URL of the last reverted rollback file.";
                                }

                                leaf revert-in-progress {
                                    type boolean;
                                    description "Indicates if a rollback revert is currently in progress.";
                                }

                                leaf last-revert-initiated-user {
                                    type types-sros:named-item-or-empty;
                                    description "The name of a system user who initiated the last rollback rescue revert.";
                                }

                                leaf last-revert-result {
                                    type types-system:action-result-with-interrupted;
                                    description "The result of the last rollback start action.";
                                }

                                leaf last-revert-initiated-time {
                                    type yang:date-and-time;
                                    description
                                        "The time when the last rescue rollback file revert
                                         on the system was initiated.";
                                }

                                leaf last-revert-completion-time {
                                    type yang:date-and-time;
                                    description
                                        "The time when the last rescue rollback file revert
                                         was completed on the system.";
                                }

                            } // container revert

                            container delete {
                                description "Enter the delete context";

                                leaf last-delete-result {
                                    type types-system:action-result;
                                    description "The result of the last rollback file delete action.";
                                }

                            } // container delete

                            container rescue {
                                description "Enter the rescue context";

                                leaf rescue-file-saved {
                                    type boolean;
                                    description
                                        "Indicates whether a rollback rescue file specified by rescue location
                                         and suffix '.rc' is present.";
                                }

                                container save {
                                    description "Enter the save context";

                                    leaf last-save-result {
                                        type types-system:action-result;
                                        description "The result of the last rollback save action.";
                                    }

                                    leaf last-save-completion-time {
                                        type yang:date-and-time;
                                        description
                                            "The time when the last rollback save was
                                             completed on the system.";
                                    }

                                } // container save

                                container revert {
                                    description "Enter the revert context";

                                    leaf rescue-in-progress {
                                        type boolean;
                                        description "Indicates if a rollback rescue revert is currently in progress.";
                                    }

                                    leaf last-revert-initiated-user {
                                        type types-sros:named-item-or-empty;
                                        description "The name of a system user who initiated the last rollback rescue revert.";
                                    }

                                    leaf last-revert-result {
                                        type types-system:action-result-with-interrupted;
                                        description "The result of the last rollback start action.";
                                    }

                                    leaf last-revert-initiated-time {
                                        type yang:date-and-time;
                                        description
                                            "The time when the last rescue rollback file revert
                                             on the system was initiated.";
                                    }

                                    leaf last-revert-completion-time {
                                        type yang:date-and-time;
                                        description
                                            "The time when the last rescue rollback file revert
                                             was completed on the system.";
                                    }

                                } // container revert

                                container delete {
                                    description "Enter the delete context";

                                    leaf last-delete-result {
                                        type types-system:action-result;
                                        description "The result of the last rollback file delete action.";
                                    }

                                } // container delete

                            } // container rescue

                            list rollback-file {
                                key "checkpoint-index";
                                description "Enter the rollback-file list instance";

                                leaf checkpoint-index {
                                    type uint32 {
                                        range "0..199";
                                    }
                                    description "Specifies the index of the rollback checkpoint file.";
                                }

                                leaf suffix {
                                    type types-sros:named-item;
                                    description "Specifies the suffix of the rollback checkpoint file.";
                                }

                                leaf creation-time {
                                    type yang:date-and-time;
                                    description "Indicates the timestamp of the creation time.";
                                }

                                leaf release {
                                    type types-sros:named-item;
                                    description
                                        "Indicates the version number of the software running on the
                                         system when the rollback file is saved.";
                                }

                                leaf user {
                                    type types-sros:named-item;
                                    description "Indicates the name of a system user who saved this rollback file.";
                                }

                                leaf comment {
                                    type types-sros:display-string;
                                    description "Specifies a user provided comment related to a rollback checkpoint file.";
                                }

                            } // list rollback-file

                        } // container rollback

                    } // container classic-cli

                } // container cli

                container netconf {
                    description "Enter the netconf context";

                    leaf oper-state {
                        type types-sros:oper-state;
                        description "operational state";
                    }

                    leaf oper-down-reason {
                        type enumeration {
                            enum admin-down                     { value 1; }
                            enum no-connected-client            { value 2; }
                            enum active-delay-on-boot           { value 3; }
                        }
                        description "The reason why the NETCONF server is operationally down";
                    }

                    container statistics {
                        description "Enter the statistics context";

                        leaf requests {
                            type yang:counter32;
                            description
                                "total number of NETCONF requests which have been accepted and processed by the NETCONF
                                 server.";
                        }

                        leaf get-requests {
                            type yang:counter32;
                            description
                                "total number of get NETCONF requests which have been accepted and processed by the
                                 NETCONF server.";
                        }

                        leaf get-config-requests {
                            type yang:counter32;
                            description
                                "total number of get-config NETCONF requests which have been accepted and
                                 processed by the NETCONF server.";
                        }

                        leaf edit-config-requests {
                            type yang:counter32;
                            description
                                "total number of edit-config NETCONF requests which have been accepted and
                                 processed by the NETCONF server.";
                        }

                        leaf close-requests {
                            type yang:counter32;
                            description
                                "total number of close-session NETCONF requests which have been accepted and processed
                                 by the NETCONF server.";
                        }

                        leaf kill-requests {
                            type yang:counter32;
                            description
                                "total number of kill-session NETCONF requests which have been accepted and processed
                                 by the NETCONF server.";
                        }

                        leaf responses {
                            type yang:counter32;
                            description
                                "total number of NETCONF responses which have been generated and sent by the NETCONF
                                 server.";
                        }

                        leaf error-responses {
                            type yang:counter32;
                            description
                                "total number of NETCONF error responses which have been generated and sent by the
                                 NETCONF server.";
                        }

                        leaf copy-config-requests {
                            type yang:counter32;
                            description
                                "total number of copy-config NETCONF requests which have been accepted and
                                 processed by the NETCONF server.";
                        }

                        leaf del-config-requests {
                            type yang:counter32;
                            description
                                "total number of delete-config NETCONF requests which have been accepted and
                                 processed by the NETCONF server.";
                        }

                        leaf validate-requests {
                            type yang:counter32;
                            description
                                "total number of validate NETCONF requests which have been accepted and
                                 processed by the NETCONF server.";
                        }

                        leaf failed-edit-cfg-reqs {
                            type yang:counter32;
                            description
                                "total number of edit-config NETCONF requests which have failed because of
                                 locks taken by other NETCONF sessions.";
                        }

                        leaf failed-lock-reqs {
                            type yang:counter32;
                            description
                                "total number of lock NETCONF requests which have failed because of
                                 locks taken by other NETCONF sessions.";
                        }

                        leaf lock-requests {
                            type yang:counter32;
                            description
                                "total number of lock NETCONF requests which have been accepted and
                                 processed by the NETCONF server.";
                        }

                        leaf unlock-requests {
                            type yang:counter32;
                            description
                                "total number of unlock NETCONF requests which have been accepted
                                 and processed by the NETCONF server.";
                        }

                        leaf commit-requests {
                            type yang:counter32;
                            description
                                "total number of commit NETCONF requests which have been accepted
                                 and processed by the NETCONF server.";
                        }

                        leaf discard-requests {
                            type yang:counter32;
                            description
                                "total number of discard change NETCONF requests which have been accepted
                                 and processed by the NETCONF server.";
                        }

                        leaf create-subscription-requests {
                            type yang:counter32;
                            description
                                "total number of create subscription NETCONF requests which have been accepted
                                 and processed by the NETCONF server.";
                        }

                        leaf get-schema-requests {
                            type yang:counter32;
                            description
                                "total number of get-schema NETCONF requests which have been accepted
                                 and processed by the NETCONF server.";
                        }

                        leaf get-data-requests {
                            type yang:counter32;
                            description
                                "total number of get-data NETCONF requests which have been accepted
                                 and processed by the NETCONF server.";
                        }

                        leaf action-requests {
                            type yang:counter32;
                            description
                                "total number of action NETCONF requests which have been accepted
                                 and processed by the NETCONF server.";
                        }

                        leaf in-bad-hellos {
                            type yang:counter32;
                            description "total number of bad NETCONF hello messages which have been received by the NETCONF server.";
                        }

                        leaf dropped-sessions {
                            type yang:counter32;
                            description "total number of dropped NETCONF sessions.";
                        }

                        leaf last-oper-change {
                            type types-sros:date-time;
                            description "time of last change of operational state of NETCONF server.";
                        }

                    } // container statistics

                    container notifications {
                        description "Enter the notifications context";

                        list subscription {
                            key "session-id";
                            description "Enter the subscription list instance";

                            leaf session-id {
                                type uint32;
                                description "The id of the NETCONF session.";
                            }

                            leaf stream {
                                type string;
                                description "The name of the event stream the session is subscribed to.";
                            }

                            leaf connection-ip {
                                type types-sros:ip-address;
                                description "Connection ip address.";
                            }

                            leaf user {
                                type types-sros:named-item;
                                description "Name of the user.";
                            }

                        } // list subscription

                    } // container notifications

                } // container netconf

                container operations {
                    description "Enter the operations context";

                    leaf oldest-operation-id {
                        type types-operation:operation-id;
                        description "Oldest ID assigned to operation currently tracked in the system.";
                    }

                    leaf newest-operation-id {
                        type types-operation:operation-id;
                        description "Most recently assigned operation ID.";
                    }

                    list operation {
                        key "operation-id";
                        description "Enter the operation list instance";

                        leaf operation-id {
                            type types-operation:operation-id;
                            description "ID assigned to the operation.";
                        }

                        leaf asynchronous {
                            type types-operation:operation-asynchronous;
                            description "Indicates whether the operation execution happened asynchronously or synchronously.";
                        }

                        leaf status {
                            type types-operation:operation-status;
                            description "Status of operation's execution.";
                        }

                        leaf secondary-status {
                            type enumeration {
                                enum terminating                    { value 0; }
                            }
                            description "Describes short-lasting operation status transitions.";
                        }

                        leaf-list error-message {
                            type types-operation:operation-message;
                            description "Error messages reported during execution of the operation.";
                        }

                        leaf-list warning-message {
                            type types-operation:operation-message;
                            description "Warning messages reported during execution of the operation.";
                        }

                        leaf-list info-message {
                            type types-operation:operation-message;
                            description "Info messages reported during execution of the operation.";
                        }

                        leaf start-time {
                            type types-operation:operation-timestamp;
                            description "Time when the operation started its execution.";
                        }

                        leaf end-time {
                            type types-operation:operation-timestamp;
                            description "Time when the operation ended its execution.";
                        }

                        leaf request-path {
                            type types-operation:operation-path;
                            description "Path identifying the operation in xpath format.";
                        }

                        leaf results-path {
                            type types-operation:operation-path;
                            description "Path where the operation's results are stored in xpath format.";
                        }

                        leaf session-id {
                            type uint32;
                            description "ID of the session that initiated the operation.";
                        }

                        leaf user {
                            type string;
                            description "Name of the user who initiated the operation.";
                        }

                        container execution-timeout {
                            description "Enter the execution-timeout context";

                            leaf time {
                                type yang:date-and-time;
                                description "Time when the operation's execution will timeout and be stopped.";
                            }

                            leaf remaining {
                                type uint32;
                                units "seconds";
                                description "Time remaining until operation's execution timeout.";
                            }

                        } // container execution-timeout

                        container retention-timeout {
                            description "Enter the retention-timeout context";

                            leaf time {
                                type yang:date-and-time;
                                description "Time when the operation's data will be erased from the system.";
                            }

                            leaf remaining {
                                type uint32;
                                units "seconds";
                                description "Time remaining until operation's retention timeout.";
                            }

                        } // container retention-timeout

                    } // list operation

                    container next-execution-timeout {
                        description "Enter the next-execution-timeout context";

                        leaf operation-id {
                            type types-operation:operation-id;
                            description "ID assigned to the operation to expire execution timer next.";
                        }

                        leaf time {
                            type yang:date-and-time;
                            description "Time when the operation's execution will timeout and be stopped.";
                        }

                        leaf remaining {
                            type uint32;
                            units "seconds";
                            description "Time remaining until operation's execution timeout.";
                        }

                    } // container next-execution-timeout

                    container next-retention-timeout {
                        description "Enter the next-retention-timeout context";

                        leaf operation-id {
                            type types-operation:operation-id;
                            description "ID assigned to the operation to expire retention timer next.";
                        }

                        leaf time {
                            type yang:date-and-time;
                            description "Time when the operation's data will be erased from the system.";
                        }

                        leaf remaining {
                            type uint32;
                            units "seconds";
                            description "Time when the operation's data will be erased from the system.";
                        }

                    } // container next-retention-timeout

                } // container operations

                container remote-management {
                    description "Enter the remote-management context";

                    leaf last-registration-status {
                        type types-system:remote-mgmt-registration-status;
                        description "Last result of registration attempt.";
                    }

                    leaf last-registration-time {
                        type types-sros:date-time;
                        description "Last time the client tried to register.";
                    }

                    leaf oper-state {
                        type types-sros:oper-state;
                        description "Administrative state of registration.";
                    }

                    leaf oper-down-reason {
                        type enumeration {
                            enum unknown                        { value 0; }
                            enum admin-down                     { value 1; }
                            enum no-manager                     { value 2; }
                            enum active-delay-on-boot           { value 3; }
                        }
                    }

                    leaf last-hello-time {
                        type types-sros:date-time;
                        description "Last time the remote-management client tried to register.";
                    }

                    container statistics {
                        description "Enter the statistics context";

                        leaf sent-registrations {
                            type yang:counter64;
                            description "The number of registrations sent.";
                        }

                        leaf failed-registrations {
                            type yang:counter64;
                            description "The number of registrations failed.";
                        }

                        leaf cancelled-registrations {
                            type yang:counter64;
                            description "The number of registrations cancelled.";
                        }

                    } // container statistics

                    list manager {
                        key "manager-name";
                        description "Enter the manager list instance";

                        leaf manager-name {
                            type types-sros:named-item-64;
                            description "Remote management manager name";
                        }

                        leaf last-registration-status {
                            type types-system:remote-mgmt-registration-status;
                            description "Last result of registration attempt.";
                        }

                        leaf last-registration-time {
                            type types-sros:date-time;
                            description "Last time the client tried to register.";
                        }

                        leaf oper-state {
                            type types-sros:oper-state;
                            description "Administrative state of registration.";
                        }

                        leaf oper-down-reason {
                            type enumeration {
                                enum unknown                        { value 0; }
                                enum admin-down                     { value 1; }
                                enum no-transport-type              { value 2; }
                                enum no-source-address              { value 3; }
                                enum invalid-manager-address        { value 4; }
                                enum registration-failed            { value 5; }
                                enum active-delay-on-boot           { value 6; }
                            }
                        }

                        leaf oper-client-tls-profile {
                            type types-sros:named-item-64;
                            description "Operational TLS client profile.";
                        }

                        leaf oper-transport-type {
                            type enumeration {
                                enum tls                            { value 1; }
                                enum unsecured                      { value 2; }
                            }
                            description "Operational transport method.";
                        }

                        leaf oper-connection-timeout {
                            type uint32;
                            units "seconds";
                            description "Operational manager response timeout.";
                        }

                        leaf oper-router-instance {
                            type types-sros:router-instance-base-management-vprn-loose;
                            description "router-instance used to connect to the manager";
                        }

                        leaf oper-device-name {
                            type types-sros:named-item-64;
                            description "Identifier of this device.";
                        }

                        leaf oper-device-label {
                            type types-sros:named-item-64;
                            description "Label of this device.";
                        }

                        leaf oper-source-address {
                            type types-sros:ip-address;
                            description "Source IP address used to provide access to management of this device.";
                        }

                        leaf oper-source-port {
                            type types-sros:tcp-udp-port;
                            description "Source TCP port used to provide access to management of this device.";
                        }

                        container statistics {
                            description "Enter the statistics context";

                            leaf sent-registrations {
                                type yang:counter64;
                                description "The number of registrations sent.";
                            }

                            leaf failed-registrations {
                                type yang:counter64;
                                description "The number of registrations failed.";
                            }

                            leaf cancelled-registrations {
                                type yang:counter64;
                                description "The number of registrations cancelled.";
                            }

                        } // container statistics

                    } // list manager

                } // container remote-management

                list active-sessions {
                    key "session-id";
                    description "Enter the active-sessions list instance";

                    leaf session-id {
                        type types-system:user-session-id;
                        description
                            "Represents unique session identifier.
                             The value is auto-generated by the system.";
                    }

                    leaf username {
                        type types-sros:named-item;
                        description "The name of the user who initiated session.";
                    }

                    leaf from {
                        type union {
                            type types-sros:ip-address;
                            type enumeration {
                                enum none                           { value -1; }
                                enum console                        { value 1; }
                                enum cron-ehs                       { value 2; }
                            }
                        }
                        description
                            "Indicates the session origin. Source IP address
                             is returned for non-console sessions.";
                    }

                    leaf session-type {
                        type enumeration {
                            enum classic-cli                    { value 1; }
                            enum grpc                           { value 2; }
                            enum md-cli                         { value 3; }
                            enum netconf                        { value 4; }
                            enum snmp                           { value 5; }
                            enum system                         { value 6; }
                        }
                        description "Identifies the management interface used to initiate the session.";
                    }

                    leaf session-mode {
                        type enumeration {
                            enum global                         { value 1; }
                            enum exclusive                      { value 2; }
                            enum private                        { value 3; }
                            enum private-exclusive              { value 4; }
                            enum read-only                      { value 5; }
                        }
                        description
                            "Indicates the candidate configuration mode.

                             Multiple global sessions are allowed to make configuration
                             changes at the same time. If a global session is taken,
                             exclusive mode is unavailable.

                             Exclusive mode blocks any other session from making
                             configuration changes.";
                    }

                    leaf idle-time {
                        type types-sros:time-duration;
                        units "seconds";
                        description
                            "Indicates the session's idle time.

                             For CLI sessions, the idle time is the period of time
                             after the last key press. For NETCONF, it is the period of time
                             since session creation. Idle time is not tracked for gRPC sessions.";
                    }

                    leaf scratchpad-count {
                        type uint32;
                        description "Number of scratchpads in use for session";
                    }

                    list locked-datastores {
                        key "region-name datastore-name";
                        description "Enter the locked-datastores list instance";

                        leaf region-name {
                            type types-sros:configuration-region;
                            description "The name of region locked within the command tree.";
                        }

                        leaf datastore-name {
                            type types-sros:datastore-name;
                            description "The name of the locked datastore.";
                        }

                    } // list locked-datastores

                } // list active-sessions

                container snmp {
                    description "Enter the snmp context";

                    leaf engine-boots {
                        type uint32;
                        description
                            "The number of times the SNMP engine has re-booted/re-initialized
                             since the SNMP Engine ID was last configured.";
                    }

                    leaf oper-state {
                        type types-sros:oper-state;
                        description
                            "When oper-state a value of 'in-service', the SNMP daemon
                             will receive SNMP requests from external SNMP managers.
                             When oper-state has a value of 'out-of-service', the SNMP
                             daemon is suspended and will not receive SNMP requests
                             from external SNMP managers.";
                    }

                    container statistics {
                        description "Enter the statistics context";

                        leaf in-packets {
                            type yang:zero-based-counter32;
                            description
                                "indicates the total number of messages delivered to the SNMP
                                 entity from the transport service.";
                        }

                        leaf in-gets {
                            type yang:zero-based-counter32;
                            description
                                "indicates the total number of SNMP Get-Request PDUs which have
                                 been accepted and processed by the SNMP protocol entity.";
                        }

                        leaf in-getnexts {
                            type yang:zero-based-counter32;
                            description
                                "indicates the total number of SNMP Get-Next PDUs which have
                                 been accepted and processed by the SNMP protocol entity.";
                        }

                        leaf in-getbulks {
                            type yang:zero-based-counter32;
                            description
                                "indicates the total number of SNMP Get-Next PDUs which have
                                 been accepted and processed by the SNMP protocol entity.";
                        }

                        leaf in-sets {
                            type yang:zero-based-counter32;
                            description
                                "indicates the total number of SNMP Set-Request PDUs which have
                                 been accepted and processed by the SNMP protocol entity.";
                        }

                        leaf out-packets {
                            type yang:zero-based-counter32;
                            description
                                "indicates the total number of SNMP Messages which were passed
                                 from the SNMP protocol entity to the transport service.";
                        }

                        leaf out-get-responses {
                            type yang:zero-based-counter32;
                            description
                                "indicates the total number of SNMP Get-Response PDUs which have
                                 been generated by the SNMP protocol entity.";
                        }

                        leaf out-traps {
                            type yang:zero-based-counter32;
                            description
                                "indicates the total number of SNMP Trap PDUs which have been
                                 generated by the SNMP protocol entity.";
                        }

                        leaf variables-requested {
                            type yang:zero-based-counter32;
                            description
                                "indicates the total number of MIB objects which have been
                                 retrieved successfully by the SNMP protocol entity as the result
                                 of receiving valid SNMP Get-Request and Get-Next PDUs.";
                        }

                        leaf variables-sets {
                            type yang:zero-based-counter32;
                            description
                                "indicates the total number of MIB objects which have been altered
                                 successfully by the SNMP protocol entity as the result of receiving
                                 valid SNMP Set-Request PDUs.";
                        }

                        leaf failed-sets {
                            type yang:zero-based-counter32;
                            description
                                "indicates the total number of SNMP set requests which have failed
                                 due to another management interface (such as NETCONF) exclusively
                                 reserving the system resources.";
                        }

                    } // container statistics

                    container streaming {
                        description "Enter the streaming context";

                        leaf dump-table-requests {
                            type yang:zero-based-counter32;
                            description
                                "indicates the total number of streaming snmp dump request PDUs
                                 which have been accepted and processed by the Nokia 5620 Service
                                 Aware Manager (SAM) streaming protocol.";
                        }

                        leaf get-many-requests {
                            type yang:zero-based-counter32;
                            description
                                "indicates the total number of streaming get many request PDUs
                                 which have been accepted and processed by the Nokia 5620 Service
                                 Aware Manager (SAM) streaming protocol entity.";
                        }

                        leaf responses {
                            type yang:zero-based-counter32;
                            description
                                "indicates the total number of streaming response PDUs which
                                 have been generated by the Nokia 5620 Service Aware Manager
                                 (SAM) streaming protocol entity.";
                        }

                    } // container streaming

                } // container snmp

                list configuration-region {
                    key "region-name";
                    description "Enter the configuration-region list instance";

                    leaf region-name {
                        type types-sros:configuration-region;
                        description "The name of the datastore.";
                    }

                    container config-save {
                        description "Enter the config-save context";

                        leaf last-saved-config {
                            type types-sros:display-string;
                            description
                                "The location and name of the file to which the configuration
                                 was last saved.";
                        }

                        leaf last-saved-time {
                            type yang:date-and-time;
                            description "The date and time when the current configuration was last saved.";
                        }

                    } // container config-save

                    list datastore {
                        key "ds-name";
                        description "Enter the datastore list instance";

                        leaf ds-name {
                            type types-sros:datastore-name;
                            description "The name of the datastore.";
                        }

                        leaf changes-since-last-save {
                            type boolean;
                            description "Indicates if the configuration was changed since the last save.";
                        }

                        leaf user-last-modified {
                            type string {
                                length "1..65";
                            }
                            description "The last user who modified the configuration.";
                        }

                        leaf time-last-modified {
                            type yang:date-and-time;
                            description "The date and time when the running configuration was last modified.";
                        }

                        leaf locked {
                            type boolean;
                            description
                                "Indicates if lock to the datastore is held by any session.

                                 The datastore is considered as locked if exclusive session is held
                                 by any user or NETCONF lock RPC was used on the datastore.";
                        }

                    } // list datastore

                    container commit-history {
                        description "Enter the commit-history context";

                        list commit-id {
                            key "id";
                            description "Enter the commit-id list instance";

                            leaf id {
                                type uint32 {
                                    range "1..max";
                                }
                                description "Record ID in the commit history";
                            }

                            leaf timestamp {
                                type yang:date-and-time;
                            }

                            leaf user {
                                type types-sros:named-item;
                                description "The name of the user who initiated commit.";
                            }

                            leaf type {
                                type enumeration {
                                    enum md-cli                         { value 0; }
                                    enum netconf                        { value 1; }
                                    enum grpc                           { value 2; }
                                    enum system                         { value 3; }
                                    enum database-initialization        { value 4; }
                                    enum issu                           { value 5; }
                                    enum cron-ehs                       { value 6; }
                                }
                            }

                            leaf from {
                                type union {
                                    type types-sros:ip-address;
                                    type enumeration {
                                        enum console                        { value 1; }
                                        enum cron-ehs                       { value 2; }
                                    }
                                }
                                description
                                    "Indicates the commit origin. Source IP address
                                     is returned for non-console sessions.";
                            }

                            leaf location {
                                type types-sros:cflash-and-url;
                            }

                            leaf increment-location {
                                type types-sros:cflash-and-url;
                            }

                            leaf comment {
                                type string {
                                    length "1..2048";
                                }
                            }

                            leaf log {
                                type string {
                                    length "1..512";
                                }
                            }

                        } // list commit-id

                    } // container commit-history

                } // list configuration-region

            } // container management-interface

            container thresholds {
                description "Enter the thresholds context";

                list cflash-cap-alarm-percent {
                    key "cflash-id";
                    description "Enter the cflash-cap-alarm-percent list instance";

                    leaf cflash-id {
                        type types-sros:thresholds-cflash-url;
                        description "cflash device name monitored for capacity";
                    }

                    leaf rmon-alarm-id {
                        type uint32;
                        description
                            "An index that uniquely identifies an entry in the alarm
                             table.  Each such entry defines a diagnostic sample at a
                             particular interval for an object on the device.";
                    }

                    leaf alarm-value {
                        type int32;
                        description
                            "Specifies the value of the statistic during the last sampling
                             period.";
                    }

                    leaf variable-oid {
                        type string {
                            length "1..255";
                        }
                        description
                            "Specifies the object identifier of the particular variable
                             to be sampled.";
                    }

                    leaf rising-rmon-event-id {
                        type uint32;
                        description
                            "Specifies the index of the eventEntry that is used when a
                             rising threshold is crossed.";
                    }

                    leaf rising-event-last-time-sent {
                        type types-sros:time-interval;
                        description
                            "The value of sysUpTime at the time rising event
                             entry last generated an event.  If this entry has
                             not generated any events, this value will be
                             zero.";
                    }

                    leaf falling-rmon-event-id {
                        type uint32;
                        description
                            "Specifies the index of the eventEntry that is used when a
                             falling threshold is crossed.";
                    }

                    leaf falling-event-last-time-sent {
                        type types-sros:time-interval;
                        description
                            "The value of sysUpTime at the time falling event
                             entry last generated an event.  If this entry has
                             not generated any events, this value will be
                             zero.";
                    }

                } // list cflash-cap-alarm-percent

                list cflash-cap-warn-percent {
                    key "cflash-id";
                    description "Enter the cflash-cap-warn-percent list instance";

                    leaf cflash-id {
                        type types-sros:thresholds-cflash-url;
                        description "cflash device name monitored for capacity";
                    }

                    leaf rmon-alarm-id {
                        type uint32;
                        description
                            "An index that uniquely identifies an entry in the alarm
                             table.  Each such entry defines a diagnostic sample at a
                             particular interval for an object on the device.";
                    }

                    leaf alarm-value {
                        type int32;
                        description
                            "Specifies the value of the statistic during the last sampling
                             period.";
                    }

                    leaf variable-oid {
                        type string {
                            length "1..255";
                        }
                        description
                            "Specifies the object identifier of the particular variable
                             to be sampled.";
                    }

                    leaf rising-rmon-event-id {
                        type uint32;
                        description
                            "Specifies the index of the eventEntry that is used when a
                             rising threshold is crossed.";
                    }

                    leaf rising-event-last-time-sent {
                        type types-sros:time-interval;
                        description
                            "The value of sysUpTime at the time rising event
                             entry last generated an event.  If this entry has
                             not generated any events, this value will be
                             zero.";
                    }

                    leaf falling-rmon-event-id {
                        type uint32;
                        description
                            "Specifies the index of the eventEntry that is used when a
                             falling threshold is crossed.";
                    }

                    leaf falling-event-last-time-sent {
                        type types-sros:time-interval;
                        description
                            "The value of sysUpTime at the time falling event
                             entry last generated an event.  If this entry has
                             not generated any events, this value will be
                             zero.";
                    }

                } // list cflash-cap-warn-percent

                container kb-memory-use-alarm {
                    description "Enable the kb-memory-use-alarm context";

                    leaf rmon-alarm-id {
                        type uint32;
                        description
                            "An index that uniquely identifies an entry in the alarm
                             table.  Each such entry defines a diagnostic sample at a
                             particular interval for an object on the device.";
                    }

                    leaf alarm-value {
                        type int32;
                        description
                            "Specifies the value of the statistic during the last sampling
                             period.";
                    }

                    leaf variable-oid {
                        type string {
                            length "1..255";
                        }
                        description
                            "Specifies the object identifier of the particular variable
                             to be sampled.";
                    }

                    leaf rising-rmon-event-id {
                        type uint32;
                        description
                            "Specifies the index of the eventEntry that is used when a
                             rising threshold is crossed.";
                    }

                    leaf rising-event-last-time-sent {
                        type types-sros:time-interval;
                        description
                            "The value of sysUpTime at the time rising event
                             entry last generated an event.  If this entry has
                             not generated any events, this value will be
                             zero.";
                    }

                    leaf falling-rmon-event-id {
                        type uint32;
                        description
                            "Specifies the index of the eventEntry that is used when a
                             falling threshold is crossed.";
                    }

                    leaf falling-event-last-time-sent {
                        type types-sros:time-interval;
                        description
                            "The value of sysUpTime at the time falling event
                             entry last generated an event.  If this entry has
                             not generated any events, this value will be
                             zero.";
                    }

                } // container kb-memory-use-alarm

                container kb-memory-use-warn {
                    description "Enable the kb-memory-use-warn context";

                    leaf rmon-alarm-id {
                        type uint32;
                        description
                            "An index that uniquely identifies an entry in the alarm
                             table.  Each such entry defines a diagnostic sample at a
                             particular interval for an object on the device.";
                    }

                    leaf alarm-value {
                        type int32;
                        description
                            "Specifies the value of the statistic during the last sampling
                             period.";
                    }

                    leaf variable-oid {
                        type string {
                            length "1..255";
                        }
                        description
                            "Specifies the object identifier of the particular variable
                             to be sampled.";
                    }

                    leaf rising-rmon-event-id {
                        type uint32;
                        description
                            "Specifies the index of the eventEntry that is used when a
                             rising threshold is crossed.";
                    }

                    leaf rising-event-last-time-sent {
                        type types-sros:time-interval;
                        description
                            "The value of sysUpTime at the time rising event
                             entry last generated an event.  If this entry has
                             not generated any events, this value will be
                             zero.";
                    }

                    leaf falling-rmon-event-id {
                        type uint32;
                        description
                            "Specifies the index of the eventEntry that is used when a
                             falling threshold is crossed.";
                    }

                    leaf falling-event-last-time-sent {
                        type types-sros:time-interval;
                        description
                            "The value of sysUpTime at the time falling event
                             entry last generated an event.  If this entry has
                             not generated any events, this value will be
                             zero.";
                    }

                } // container kb-memory-use-warn

                container rmon {
                    description "Enter the rmon context";

                    list alarm {
                        key "rmon-alarm-id";
                        description "Enter the alarm list instance";

                        leaf rmon-alarm-id {
                            type uint32 {
                                range "0..65400";
                            }
                            description "Index ID for an entry in the alarm table";
                        }

                        leaf alarm-value {
                            type int32;
                            description
                                "Specifies the value of the statistic during the last sampling
                                 period.";
                        }

                    } // list alarm

                    list event {
                        key "rmon-event-id";
                        description "Enter the event list instance";

                        leaf rmon-event-id {
                            type uint32 {
                                range "1..65400";
                            }
                            description "Index ID for an entry in the event table";
                        }

                        leaf event-last-time-sent {
                            type types-sros:time-interval;
                            description
                                "The value of sysUpTime at the time this event
                                 entry last generated an event.  If this entry has
                                 not generated any events, this value will be
                                 zero.";
                        }

                    } // list event

                } // container rmon

            } // container thresholds

            container ip {
                description "Enter the ip context";

            } // container ip

            container lldp {
                description "Enter the lldp context";

                leaf chassis-id {
                    type types-lldp:chassis-id;
                    description "Indicates the chassis component provided by the local system.";
                }

                leaf chassis-id-subtype {
                    type types-lldp:chassis-id-subtype;
                    description "Indicates the chassis identifier subtype associated with the local system.";
                }

                leaf system-name {
                    type string;
                    description "Indicates the system name of the local system.";
                }

                leaf system-description {
                    type string;
                    description "Indicates the system description of the local system.";
                }

                leaf capabilities-supported {
                    type types-lldp:system-capabilities;
                    description "Indicates which system capabilities are supported on the local system.";
                }

                leaf capabilities-enabled {
                    type types-lldp:system-capabilities;
                    description "Indicates which system capabilities are enabled on the local system.";
                }

                list dest-mac {
                    key "mac-type";
                    description "Enter the dest-mac list instance";

                    leaf mac-type {
                        type types-lldp:mac-addr-type;
                        description "The identifier which uniquely identifies the MAC address type.";
                    }

                    leaf mac-address {
                        type yang:mac-address;
                        description
                            "Indicates the destination MAC address associated with
                             this entry.

                             The octet string identifies an individual or a group
                             MAC address that is in use by LLDP as a destination
                             MAC address.

                             The MAC address is encoded in the octet string in
                             canonical format (see IEEE Std 802).";
                    }

                } // list dest-mac

                list mgmt-address {
                    key "mgmt-address-subtype mgmt-address";
                    description "Enter the mgmt-address list instance";

                    leaf mgmt-address-subtype {
                        type types-lldp:address-family-numbers;
                        description
                            "Specifies the type of management address identifier encoding
                             used in mgmt-address.";
                    }

                    leaf mgmt-address {
                        type types-lldp:management-address;
                        description
                            "Specifies the string value used to identify the management address
                             component associated with the remote system. The purpose
                             of this address is to contact the management entity.";
                    }

                    leaf interface-subtype {
                        type enumeration {
                            enum unknown                        { value 1; }
                            enum if-index                       { value 2; }
                            enum system-port-number             { value 3; }
                        }
                        description
                            "Indicates the interface numbering type provided by the remote
                             system. The corresponding interface number is interface-id.";
                    }

                    leaf interface-id {
                        type int32;
                        description
                            "Indicates the integer value used to identify the interface number
                             regarding the management address component associated with
                             the remote system.";
                    }

                    leaf object-identifier {
                        type yang:object-identifier-128;
                        description
                            "Indicates the OID value used to identify the type of hardware
                             component or protocol entity associated with the management address
                             advertised by the remote system agent.";
                    }

                } // list mgmt-address

                container statistics {
                    description "Enter the statistics context";

                    container remote {
                        description "Enter the remote context";

                        leaf last-changed {
                            type yang:date-and-time;
                            description
                                "Indicates the system update time when the remote system information
                                 was last modified.";
                        }

                        leaf inserts {
                            type yang:zero-based-counter32;
                            description
                                "Indicates the number of times the complete set of information
                                 advertised by a particular MSAP has been inserted in the list
                                 /port/ethernet/lldp/dest-mac/remote-system.";
                        }

                        leaf deletes {
                            type yang:zero-based-counter32;
                            description
                                "Indicates the number of times the complete set of information
                                 advertised by a particular MSAP has been deleted from the list
                                 /port/ethernet/lldp/dest-mac/remote-system.";
                        }

                        leaf drops {
                            type yang:zero-based-counter32;
                            description
                                "Indicates the number of times the complete set of information
                                 advertised by a particular MSAP could not be entered into the list
                                 /port/ethernet/lldp/dest-mac/remote-system.";
                        }

                        leaf ageouts {
                            type yang:zero-based-counter32;
                            description
                                "Indicates the number of times the complete set of information
                                 advertised by a particular MSAP has been deleted from the list
                                 /port/ethernet/lldp/dest-mac/remote-system because the information
                                 timeliness interval has expired.";
                        }

                    } // container remote

                } // container statistics

            } // container lldp

            container l2tp {
                description "Enter the l2tp context";

                leaf max-tunnels {
                    type uint32;
                    description "The maximum number of supported tunnels in the system.";
                }

                leaf max-sessions {
                    type uint32;
                    description "The maximum number of supported sessions in the system.";
                }

                leaf max-sessions-per-tunnel {
                    type uint32;
                    description "The maximum number of supported sessions per tunnel.";
                }

            } // container l2tp

            list power-management {
                key "power-zone";
                description "Enter the power-management list instance";

                leaf power-zone {
                    type uint32 {
                        range "1..2";
                    }
                    description "Power zone";
                }

                leaf active-conditions {
                    type bits {
                        bit capacity-exceeded              { position 0; }
                        bit lost-capacity                  { position 1; }
                        bit insufficient-capacity          { position 2; }
                        bit overload                       { position 3; }
                        bit safety-alert                   { position 4; }
                        bit safety-level                   { position 5; }
                    }
                    description
                        "Indicates the active conditions present on a given power zone. When
                         the bit is set, the condition is active. 

                         Conditions include:
                            capacity-exceeded - a device in the power-zone requires power to
                                boot, but there is insufficient capcity to support it
                            lost-capacity - system power capacity is insufficient to
                                satisfy the safety level while maintaining any applicable
                                power reserve
                            insufficient-capacity - the provisioned capacity of the power-zone
                                can not support the requirements of the system and provisioned
                                equipment, while maintaining any applicable power reserve
                            overload - the system power capacity is insufficient to power
                                essential equipment while maintaining any applicable power reserve.
                            safety-alert - the system power capacity has dropped below the
                                safety alert threshold configured by tmnxChassisPwrMgmtSafetyAlert
                            safety-level - the peak power consumption has exceeded the safety
                                level threshold configured by tmnxChassisPwrMgmtSafetyLevel";
                }

                leaf peak-utilization {
                    type uint32;
                    units "watts";
                    description
                        "The maximum power consumed by the system within the current power zone,
                         measured in Watts (W).";
                }

                leaf reserve-power {
                    type uint32;
                    units "watts";
                    description "The greatest rated output among equipped power sources, measured in Watts (W)";
                }

                leaf requirement-remaining-power {
                    type int32;
                    units "watts";
                    description
                        "The remaining power available to the system beyond the required and
                         reserved power ratings, measured in Watts (W).";
                }

                leaf utilization-remaining-power {
                    type int32;
                    units "watts";
                    description
                        "The remaining power available to the system beyond the currently-utilized
                         and reserved power ratings, measured in Watts (W).";
                }

                leaf oper-safety-level {
                    type uint32;
                    units "watts";
                    description "Indicates the operational safety level.";
                }

                leaf oper-safety-alert {
                    type uint32;
                    units "watts";
                    description "Indicates the operational safety alert.";
                }

            } // list power-management

            container limits {
                description "Enter the limits context";

                leaf slots {
                    type uint32;
                    description
                        "The maximum number of slots that can be made
                         available for plug-in cards if the maximum number of physical
                         router chassis are populated. This includes both CPM and
                         IOM/IMM/XCM slots.";
                }

                leaf operational-slots {
                    type uint32;
                    description
                        "The number of slots that are available for plug-in
                         cards of all the physical router chassis configured in the
                         system. This includes both CPM and IOM/IMM/XCM slots.";
                }

                leaf ports {
                    type uint32;
                    description
                        "The total number of faceplate ports and connectors currently
                         installed for all of the physical router chassis in the
                         system. This does not include the Ethernet ports
                         on the CPM cards that are used for management access.";
                }

                leaf physical-ports {
                    type uint32;
                    description
                        "The total number of faceplate ports and connector-ports
                         currently installed for all the physical router chassis in
                         the system. This does not include the Ethernet ports on
                         the CPM cards that are used for management access.";
                }

                leaf power-supplies {
                    type uint32;
                    description
                        "The total number of power supplies installed for all
                         the physical router chassis in the system.";
                }

                leaf fan-trays {
                    type uint32;
                    description
                        "The total number of fan-trays installed for all the
                         physical router chassis in the system.";
                }

                leaf fans {
                    type uint32;
                    description
                        "The total number of fans installed for all the
                         physical router chassis in the system.";
                }

            } // container limits

            container led-states {
                description "Enter the led-states context";

                leaf critical {
                    type types-system:led-state;
                    description "The current state of the critical LED in the system.";
                }

                leaf major {
                    type types-system:led-state;
                    description "The current state of the major LED in the system.";
                }

                leaf minor {
                    type types-system:led-state;
                    description "The current state of the minor LED in the system.";
                }

                leaf alarm {
                    type types-system:led-state;
                    description "The current state of the alarm LED in the system.";
                }

            } // container led-states

            container connections {
                description "Enter the connections context";

                list tcp-connection {
                    key "local-ip-address local-port remote-ip-address remote-port router-instance";
                    description "Enter the tcp-connection list instance";

                    leaf local-ip-address {
                        type types-sros:ip-address;
                        description "IP address of local address.";
                    }

                    leaf local-port {
                        type inet:port-number;
                        description "Protocol port number of local port.";
                    }

                    leaf remote-ip-address {
                        type types-sros:ip-address;
                        description "IP address of remote address.";
                    }

                    leaf remote-port {
                        type inet:port-number;
                        description "Protocol port number of remote port.";
                    }

                    leaf router-instance {
                        type types-sros:router-instance;
                        description "Specifies the routing context.";
                    }

                    leaf rx-queue-depth {
                        type uint32;
                        description "Bytes in socket receive buffer.";
                    }

                    leaf tx-queue-depth {
                        type uint32;
                        description "Bytes in socket send buffer.";
                    }

                    leaf tcp-state {
                        type enumeration {
                            enum not-available                  { value 0; }
                            enum closed                         { value 1; }
                            enum listen                         { value 2; }
                            enum syn-sent                       { value 3; }
                            enum syn-rcvd                       { value 4; }
                            enum establish                      { value 5; }
                            enum fin-wait-1                     { value 6; }
                            enum fin-wait-2                     { value 7; }
                            enum close-wait                     { value 8; }
                            enum last-ack                       { value 9; }
                            enum closing                        { value 10; }
                            enum time-wait                      { value 11; }
                        }
                        description "TCP connections state.";
                    }

                    leaf oper-maximum-segment-size {
                        type uint32;
                        description "Maximum number of bytes in a single TCP segment.";
                    }

                    leaf received-maxseg-option {
                        type uint32;
                        description
                            "The value received from the peer in the MAXSEG TCP option
                             when the TCP session was started.";
                    }

                } // list tcp-connection

                container statistics {
                    description "Enter the statistics context";

                    container tcp {
                        description "Enter the tcp context";

                        leaf ack-for-unsent-data {
                            type uint32;
                            description "Received acks for unsent data.";
                        }

                        leaf ack-only-packets {
                            type uint32;
                            description "Ack-only packets sent.";
                        }

                        leaf ack-only-packets-delayed {
                            type uint32;
                            description "Delayed ack packets sent.";
                        }

                        leaf acks {
                            type uint32;
                            description "Received ack packets.";
                        }

                        leaf completely-duplicate-packet {
                            type uint32;
                            description "Duplicate-only packets received.";
                        }

                        leaf connections-accept {
                            type uint32;
                            description "Number of connections accepted.";
                        }

                        leaf connections-closed {
                            type uint32;
                            description "Number of connections closed including dropped connections.";
                        }

                        leaf connections-dropped {
                            type uint32;
                            description "Number of connections dropped.";
                        }

                        leaf packets-dropped-by-md5 {
                            type uint32;
                            description "Number of packets dropped because of MD5.";
                        }

                        leaf packets-dropped-by-enhanced-auth {
                            type uint32;
                            description "Enhanced authentication option packets dropped.";
                        }

                        leaf packets-dropped-by-tcp-ao {
                            type uint32;
                            description "Tcp-Ao packets dropped.";
                        }

                        leaf connections-dropped-by-full-queue {
                            type uint32;
                            description "Number of connections dropped because of full queue.";
                        }

                        leaf connections-dropped-by-keepalive {
                            type uint32;
                            description "Number of connections dropped by keepalive.";
                        }

                        leaf connections-dropped-by-rexmit-timeout {
                            type uint32;
                            description "Number of connections dropped in rxmt timeout.";
                        }

                        leaf connections-request {
                            type uint32;
                            description "Number of connections initiated.";
                        }

                        leaf connections-established {
                            type uint32;
                            description "Number of connection established including accepts.";
                        }

                        leaf control-packets {
                            type uint32;
                            description "Control (SYN|FIN|RST) packets sent.";
                        }

                        leaf data-packet {
                            type uint32;
                            description "Data packets sent.";
                        }

                        leaf data-packet-retransmitted {
                            type uint32;
                            description "Data packets retransmitted.";
                        }

                        leaf discarded-because-packet-too-short {
                            type uint32;
                            description "Packets received too short.";
                        }

                        leaf discarded-for-bad-checksum {
                            type uint32;
                            description "Packets received with checksum errors.";
                        }

                        leaf discarded-for-bad-header-offset-field {
                            type uint32;
                            description "Packets received with bad offset.";
                        }

                        leaf duplicate-acks {
                            type uint32;
                            description "Received duplicate acks.";
                        }

                        leaf embryonic-connections-dropped {
                            type uint32;
                            description "Embryonic connections dropped.";
                        }

                        leaf keepalive-probes-sent {
                            type uint32;
                            description "Keepalive probes sent.";
                        }

                        leaf keepalive-timeouts {
                            type uint32;
                            description "Keepalive timeouts.";
                        }

                        leaf out-of-order-packets {
                            type uint32;
                            description "Out of order packets received.";
                        }

                        leaf packet-of-data-after-window {
                            type uint32;
                            description "Packets with data after window.";
                        }

                        leaf packet-sent {
                            type uint32;
                            description "Total packets sent.";
                        }

                        leaf packet-with-some-dup-data {
                            type uint32;
                            description "Packets with some duplicate data.";
                        }

                        leaf packets-received {
                            type uint32;
                            description "Total packets received.";
                        }

                        leaf packets-received-in-sequence {
                            type uint32;
                            description "Packets received in sequence.";
                        }

                        leaf packets-recieved-after-close {
                            type uint32;
                            description "Packets received after 'close'.";
                        }

                        leaf path-mtu-discovery-backoff {
                            type uint32;
                            description "Number of times the path-mtu-discovery is switched off.";
                        }

                        leaf pcb-cache-lookups-failed {
                            type uint32;
                            description "Number of times pcb cache lookup failed.";
                        }

                        leaf persist-timeouts {
                            type uint32;
                            description "Persist timeouts.";
                        }

                        leaf retransmit-timeouts {
                            type uint32;
                            description "Retransmit timeouts.";
                        }

                        leaf segments-attempts {
                            type uint32;
                            description "Attempts to get rtt.";
                        }

                        leaf segments-updated-rtt {
                            type uint32;
                            description "Successful attempts of rtt update.";
                        }

                        leaf urg-only-packet {
                            type uint32;
                            description "Packets sent with URG only.";
                        }

                        leaf window-probe {
                            type uint32;
                            description "Received windows probe packets.";
                        }

                        leaf window-probe-packet {
                            type uint32;
                            description "Window probes sent.";
                        }

                        leaf window-update-packet {
                            type uint32;
                            description "Window update-only packets sent.";
                        }

                        leaf window-update-rcv-packet {
                            type uint32;
                            description "Received window update packets.";
                        }

                    } // container tcp

                } // container statistics

            } // container connections

            list cpu {
                key "sample-period";
                description "Enter the cpu list instance";

                leaf sample-period {
                    type types-sros:time-duration {
                        range "1|60|300";
                    }
                    units "seconds";
                    description "Number of seconds for how long to collect CPU information.";
                }

                container bfd {
                    description "Enter the bfd context";

                    leaf cpu-time {
                        status deprecated;
                        type types-sros:time-duration;
                        units "microseconds";
                        description
                            "Number of microseconds used by this group/core. (This leaf may experience
                             overflow because it is a 32-bit integer. Please use the neighboring leaf,
                             time-used, it is 64-bit.)";
                    }

                    leaf time-used {
                        type types-sros:time-duration-64;
                        units "microseconds";
                        description "Number of microseconds used by this group/core since start-up.";
                    }

                    leaf cpu-usage {
                        type decimal64 {
                            range "0..100";
                            fraction-digits 2;
                        }
                        units "percent";
                        description "Relative amount of time used by this group/core since start-up.";
                    }

                    leaf capacity-usage {
                        type decimal64 {
                            range "0..100";
                            fraction-digits 2;
                        }
                        units "percent";
                        description "Relative amount of time used by the busiest task/core.";
                    }

                } // container bfd

                container bgp {
                    description "Enter the bgp context";

                    leaf cpu-time {
                        status deprecated;
                        type types-sros:time-duration;
                        units "microseconds";
                        description
                            "Number of microseconds used by this group/core. (This leaf may experience
                             overflow because it is a 32-bit integer. Please use the neighboring leaf,
                             time-used, it is 64-bit.)";
                    }

                    leaf time-used {
                        type types-sros:time-duration-64;
                        units "microseconds";
                        description "Number of microseconds used by this group/core since start-up.";
                    }

                    leaf cpu-usage {
                        type decimal64 {
                            range "0..100";
                            fraction-digits 2;
                        }
                        units "percent";
                        description "Relative amount of time used by this group/core since start-up.";
                    }

                    leaf capacity-usage {
                        type decimal64 {
                            range "0..100";
                            fraction-digits 2;
                        }
                        units "percent";
                        description "Relative amount of time used by the busiest task/core.";
                    }

                } // container bgp

                container bgp-pe-ce {
                    description "Enter the bgp-pe-ce context";

                    leaf cpu-time {
                        status deprecated;
                        type types-sros:time-duration;
                        units "microseconds";
                        description
                            "Number of microseconds used by this group/core. (This leaf may experience
                             overflow because it is a 32-bit integer. Please use the neighboring leaf,
                             time-used, it is 64-bit.)";
                    }

                    leaf time-used {
                        type types-sros:time-duration-64;
                        units "microseconds";
                        description "Number of microseconds used by this group/core since start-up.";
                    }

                    leaf cpu-usage {
                        type decimal64 {
                            range "0..100";
                            fraction-digits 2;
                        }
                        units "percent";
                        description "Relative amount of time used by this group/core since start-up.";
                    }

                    leaf capacity-usage {
                        type decimal64 {
                            range "0..100";
                            fraction-digits 2;
                        }
                        units "percent";
                        description "Relative amount of time used by the busiest task/core.";
                    }

                } // container bgp-pe-ce

                container bier {
                    description "Enter the bier context";

                    leaf cpu-time {
                        status deprecated;
                        type types-sros:time-duration;
                        units "microseconds";
                        description
                            "Number of microseconds used by this group/core. (This leaf may experience
                             overflow because it is a 32-bit integer. Please use the neighboring leaf,
                             time-used, it is 64-bit.)";
                    }

                    leaf time-used {
                        type types-sros:time-duration-64;
                        units "microseconds";
                        description "Number of microseconds used by this group/core since start-up.";
                    }

                    leaf cpu-usage {
                        type decimal64 {
                            range "0..100";
                            fraction-digits 2;
                        }
                        units "percent";
                        description "Relative amount of time used by this group/core since start-up.";
                    }

                    leaf capacity-usage {
                        type decimal64 {
                            range "0..100";
                            fraction-digits 2;
                        }
                        units "percent";
                        description "Relative amount of time used by the busiest task/core.";
                    }

                } // container bier

                container calltrace {
                    description "Enter the calltrace context";

                    leaf cpu-time {
                        status deprecated;
                        type types-sros:time-duration;
                        units "microseconds";
                        description
                            "Number of microseconds used by this group/core. (This leaf may experience
                             overflow because it is a 32-bit integer. Please use the neighboring leaf,
                             time-used, it is 64-bit.)";
                    }

                    leaf time-used {
                        type types-sros:time-duration-64;
                        units "microseconds";
                        description "Number of microseconds used by this group/core since start-up.";
                    }

                    leaf cpu-usage {
                        type decimal64 {
                            range "0..100";
                            fraction-digits 2;
                        }
                        units "percent";
                        description "Relative amount of time used by this group/core since start-up.";
                    }

                    leaf capacity-usage {
                        type decimal64 {
                            range "0..100";
                            fraction-digits 2;
                        }
                        units "percent";
                        description "Relative amount of time used by the busiest task/core.";
                    }

                } // container calltrace

                container cflowd {
                    description "Enter the cflowd context";

                    leaf cpu-time {
                        status deprecated;
                        type types-sros:time-duration;
                        units "microseconds";
                        description
                            "Number of microseconds used by this group/core. (This leaf may experience
                             overflow because it is a 32-bit integer. Please use the neighboring leaf,
                             time-used, it is 64-bit.)";
                    }

                    leaf time-used {
                        type types-sros:time-duration-64;
                        units "microseconds";
                        description "Number of microseconds used by this group/core since start-up.";
                    }

                    leaf cpu-usage {
                        type decimal64 {
                            range "0..100";
                            fraction-digits 2;
                        }
                        units "percent";
                        description "Relative amount of time used by this group/core since start-up.";
                    }

                    leaf capacity-usage {
                        type decimal64 {
                            range "0..100";
                            fraction-digits 2;
                        }
                        units "percent";
                        description "Relative amount of time used by the busiest task/core.";
                    }

                } // container cflowd

                container cards-and-ports {
                    description "Enter the cards-and-ports context";

                    leaf cpu-time {
                        status deprecated;
                        type types-sros:time-duration;
                        units "microseconds";
                        description
                            "Number of microseconds used by this group/core. (This leaf may experience
                             overflow because it is a 32-bit integer. Please use the neighboring leaf,
                             time-used, it is 64-bit.)";
                    }

                    leaf time-used {
                        type types-sros:time-duration-64;
                        units "microseconds";
                        description "Number of microseconds used by this group/core since start-up.";
                    }

                    leaf cpu-usage {
                        type decimal64 {
                            range "0..100";
                            fraction-digits 2;
                        }
                        units "percent";
                        description "Relative amount of time used by this group/core since start-up.";
                    }

                    leaf capacity-usage {
                        type decimal64 {
                            range "0..100";
                            fraction-digits 2;
                        }
                        units "percent";
                        description "Relative amount of time used by the busiest task/core.";
                    }

                } // container cards-and-ports

                container dhcp-server {
                    description "Enter the dhcp-server context";

                    leaf cpu-time {
                        status deprecated;
                        type types-sros:time-duration;
                        units "microseconds";
                        description
                            "Number of microseconds used by this group/core. (This leaf may experience
                             overflow because it is a 32-bit integer. Please use the neighboring leaf,
                             time-used, it is 64-bit.)";
                    }

                    leaf time-used {
                        type types-sros:time-duration-64;
                        units "microseconds";
                        description "Number of microseconds used by this group/core since start-up.";
                    }

                    leaf cpu-usage {
                        type decimal64 {
                            range "0..100";
                            fraction-digits 2;
                        }
                        units "percent";
                        description "Relative amount of time used by this group/core since start-up.";
                    }

                    leaf capacity-usage {
                        type decimal64 {
                            range "0..100";
                            fraction-digits 2;
                        }
                        units "percent";
                        description "Relative amount of time used by the busiest task/core.";
                    }

                } // container dhcp-server

                container eth-cfm {
                    description "Enter the eth-cfm context";

                    leaf cpu-time {
                        status deprecated;
                        type types-sros:time-duration;
                        units "microseconds";
                        description
                            "Number of microseconds used by this group/core. (This leaf may experience
                             overflow because it is a 32-bit integer. Please use the neighboring leaf,
                             time-used, it is 64-bit.)";
                    }

                    leaf time-used {
                        type types-sros:time-duration-64;
                        units "microseconds";
                        description "Number of microseconds used by this group/core since start-up.";
                    }

                    leaf cpu-usage {
                        type decimal64 {
                            range "0..100";
                            fraction-digits 2;
                        }
                        units "percent";
                        description "Relative amount of time used by this group/core since start-up.";
                    }

                    leaf capacity-usage {
                        type decimal64 {
                            range "0..100";
                            fraction-digits 2;
                        }
                        units "percent";
                        description "Relative amount of time used by the busiest task/core.";
                    }

                } // container eth-cfm

                container fastpath {
                    description "Enter the fastpath context";

                    leaf cpu-time {
                        status deprecated;
                        type types-sros:time-duration;
                        units "microseconds";
                        description
                            "Number of microseconds used by this group/core. (This leaf may experience
                             overflow because it is a 32-bit integer. Please use the neighboring leaf,
                             time-used, it is 64-bit.)";
                    }

                    leaf time-used {
                        type types-sros:time-duration-64;
                        units "microseconds";
                        description "Number of microseconds used by this group/core since start-up.";
                    }

                    leaf cpu-usage {
                        type decimal64 {
                            range "0..100";
                            fraction-digits 2;
                        }
                        units "percent";
                        description "Relative amount of time used by this group/core since start-up.";
                    }

                    leaf capacity-usage {
                        type decimal64 {
                            range "0..100";
                            fraction-digits 2;
                        }
                        units "percent";
                        description "Relative amount of time used by the busiest task/core.";
                    }

                } // container fastpath

                container icc {
                    description "Enter the icc context";

                    leaf cpu-time {
                        status deprecated;
                        type types-sros:time-duration;
                        units "microseconds";
                        description
                            "Number of microseconds used by this group/core. (This leaf may experience
                             overflow because it is a 32-bit integer. Please use the neighboring leaf,
                             time-used, it is 64-bit.)";
                    }

                    leaf time-used {
                        type types-sros:time-duration-64;
                        units "microseconds";
                        description "Number of microseconds used by this group/core since start-up.";
                    }

                    leaf cpu-usage {
                        type decimal64 {
                            range "0..100";
                            fraction-digits 2;
                        }
                        units "percent";
                        description "Relative amount of time used by this group/core since start-up.";
                    }

                    leaf capacity-usage {
                        type decimal64 {
                            range "0..100";
                            fraction-digits 2;
                        }
                        units "percent";
                        description "Relative amount of time used by the busiest task/core.";
                    }

                } // container icc

                container igmp-mld {
                    description "Enter the igmp-mld context";

                    leaf cpu-time {
                        status deprecated;
                        type types-sros:time-duration;
                        units "microseconds";
                        description
                            "Number of microseconds used by this group/core. (This leaf may experience
                             overflow because it is a 32-bit integer. Please use the neighboring leaf,
                             time-used, it is 64-bit.)";
                    }

                    leaf time-used {
                        type types-sros:time-duration-64;
                        units "microseconds";
                        description "Number of microseconds used by this group/core since start-up.";
                    }

                    leaf cpu-usage {
                        type decimal64 {
                            range "0..100";
                            fraction-digits 2;
                        }
                        units "percent";
                        description "Relative amount of time used by this group/core since start-up.";
                    }

                    leaf capacity-usage {
                        type decimal64 {
                            range "0..100";
                            fraction-digits 2;
                        }
                        units "percent";
                        description "Relative amount of time used by the busiest task/core.";
                    }

                } // container igmp-mld

                container imsi-db-appl {
                    description "Enter the imsi-db-appl context";

                    leaf cpu-time {
                        status deprecated;
                        type types-sros:time-duration;
                        units "microseconds";
                        description
                            "Number of microseconds used by this group/core. (This leaf may experience
                             overflow because it is a 32-bit integer. Please use the neighboring leaf,
                             time-used, it is 64-bit.)";
                    }

                    leaf time-used {
                        type types-sros:time-duration-64;
                        units "microseconds";
                        description "Number of microseconds used by this group/core since start-up.";
                    }

                    leaf cpu-usage {
                        type decimal64 {
                            range "0..100";
                            fraction-digits 2;
                        }
                        units "percent";
                        description "Relative amount of time used by this group/core since start-up.";
                    }

                    leaf capacity-usage {
                        type decimal64 {
                            range "0..100";
                            fraction-digits 2;
                        }
                        units "percent";
                        description "Relative amount of time used by the busiest task/core.";
                    }

                } // container imsi-db-appl

                container ip-stack {
                    description "Enter the ip-stack context";

                    leaf cpu-time {
                        status deprecated;
                        type types-sros:time-duration;
                        units "microseconds";
                        description
                            "Number of microseconds used by this group/core. (This leaf may experience
                             overflow because it is a 32-bit integer. Please use the neighboring leaf,
                             time-used, it is 64-bit.)";
                    }

                    leaf time-used {
                        type types-sros:time-duration-64;
                        units "microseconds";
                        description "Number of microseconds used by this group/core since start-up.";
                    }

                    leaf cpu-usage {
                        type decimal64 {
                            range "0..100";
                            fraction-digits 2;
                        }
                        units "percent";
                        description "Relative amount of time used by this group/core since start-up.";
                    }

                    leaf capacity-usage {
                        type decimal64 {
                            range "0..100";
                            fraction-digits 2;
                        }
                        units "percent";
                        description "Relative amount of time used by the busiest task/core.";
                    }

                } // container ip-stack

                container is-is {
                    description "Enter the is-is context";

                    leaf cpu-time {
                        status deprecated;
                        type types-sros:time-duration;
                        units "microseconds";
                        description
                            "Number of microseconds used by this group/core. (This leaf may experience
                             overflow because it is a 32-bit integer. Please use the neighboring leaf,
                             time-used, it is 64-bit.)";
                    }

                    leaf time-used {
                        type types-sros:time-duration-64;
                        units "microseconds";
                        description "Number of microseconds used by this group/core since start-up.";
                    }

                    leaf cpu-usage {
                        type decimal64 {
                            range "0..100";
                            fraction-digits 2;
                        }
                        units "percent";
                        description "Relative amount of time used by this group/core since start-up.";
                    }

                    leaf capacity-usage {
                        type decimal64 {
                            range "0..100";
                            fraction-digits 2;
                        }
                        units "percent";
                        description "Relative amount of time used by the busiest task/core.";
                    }

                } // container is-is

                container isa {
                    description "Enter the isa context";

                    leaf cpu-time {
                        status deprecated;
                        type types-sros:time-duration;
                        units "microseconds";
                        description
                            "Number of microseconds used by this group/core. (This leaf may experience
                             overflow because it is a 32-bit integer. Please use the neighboring leaf,
                             time-used, it is 64-bit.)";
                    }

                    leaf time-used {
                        type types-sros:time-duration-64;
                        units "microseconds";
                        description "Number of microseconds used by this group/core since start-up.";
                    }

                    leaf cpu-usage {
                        type decimal64 {
                            range "0..100";
                            fraction-digits 2;
                        }
                        units "percent";
                        description "Relative amount of time used by this group/core since start-up.";
                    }

                    leaf capacity-usage {
                        type decimal64 {
                            range "0..100";
                            fraction-digits 2;
                        }
                        units "percent";
                        description "Relative amount of time used by the busiest task/core.";
                    }

                } // container isa

                container ldp {
                    description "Enter the ldp context";

                    leaf cpu-time {
                        status deprecated;
                        type types-sros:time-duration;
                        units "microseconds";
                        description
                            "Number of microseconds used by this group/core. (This leaf may experience
                             overflow because it is a 32-bit integer. Please use the neighboring leaf,
                             time-used, it is 64-bit.)";
                    }

                    leaf time-used {
                        type types-sros:time-duration-64;
                        units "microseconds";
                        description "Number of microseconds used by this group/core since start-up.";
                    }

                    leaf cpu-usage {
                        type decimal64 {
                            range "0..100";
                            fraction-digits 2;
                        }
                        units "percent";
                        description "Relative amount of time used by this group/core since start-up.";
                    }

                    leaf capacity-usage {
                        type decimal64 {
                            range "0..100";
                            fraction-digits 2;
                        }
                        units "percent";
                        description "Relative amount of time used by the busiest task/core.";
                    }

                } // container ldp

                container logging {
                    description "Enter the logging context";

                    leaf cpu-time {
                        status deprecated;
                        type types-sros:time-duration;
                        units "microseconds";
                        description
                            "Number of microseconds used by this group/core. (This leaf may experience
                             overflow because it is a 32-bit integer. Please use the neighboring leaf,
                             time-used, it is 64-bit.)";
                    }

                    leaf time-used {
                        type types-sros:time-duration-64;
                        units "microseconds";
                        description "Number of microseconds used by this group/core since start-up.";
                    }

                    leaf cpu-usage {
                        type decimal64 {
                            range "0..100";
                            fraction-digits 2;
                        }
                        units "percent";
                        description "Relative amount of time used by this group/core since start-up.";
                    }

                    leaf capacity-usage {
                        type decimal64 {
                            range "0..100";
                            fraction-digits 2;
                        }
                        units "percent";
                        description "Relative amount of time used by the busiest task/core.";
                    }

                } // container logging

                container mbuf {
                    description "Enter the mbuf context";

                    leaf cpu-time {
                        status deprecated;
                        type types-sros:time-duration;
                        units "microseconds";
                        description
                            "Number of microseconds used by this group/core. (This leaf may experience
                             overflow because it is a 32-bit integer. Please use the neighboring leaf,
                             time-used, it is 64-bit.)";
                    }

                    leaf time-used {
                        type types-sros:time-duration-64;
                        units "microseconds";
                        description "Number of microseconds used by this group/core since start-up.";
                    }

                    leaf cpu-usage {
                        type decimal64 {
                            range "0..100";
                            fraction-digits 2;
                        }
                        units "percent";
                        description "Relative amount of time used by this group/core since start-up.";
                    }

                    leaf capacity-usage {
                        type decimal64 {
                            range "0..100";
                            fraction-digits 2;
                        }
                        units "percent";
                        description "Relative amount of time used by the busiest task/core.";
                    }

                } // container mbuf

                container mcs {
                    description "Enter the mcs context";

                    leaf cpu-time {
                        status deprecated;
                        type types-sros:time-duration;
                        units "microseconds";
                        description
                            "Number of microseconds used by this group/core. (This leaf may experience
                             overflow because it is a 32-bit integer. Please use the neighboring leaf,
                             time-used, it is 64-bit.)";
                    }

                    leaf time-used {
                        type types-sros:time-duration-64;
                        units "microseconds";
                        description "Number of microseconds used by this group/core since start-up.";
                    }

                    leaf cpu-usage {
                        type decimal64 {
                            range "0..100";
                            fraction-digits 2;
                        }
                        units "percent";
                        description "Relative amount of time used by this group/core since start-up.";
                    }

                    leaf capacity-usage {
                        type decimal64 {
                            range "0..100";
                            fraction-digits 2;
                        }
                        units "percent";
                        description "Relative amount of time used by the busiest task/core.";
                    }

                } // container mcs

                container mpls-rsvp {
                    description "Enter the mpls-rsvp context";

                    leaf cpu-time {
                        status deprecated;
                        type types-sros:time-duration;
                        units "microseconds";
                        description
                            "Number of microseconds used by this group/core. (This leaf may experience
                             overflow because it is a 32-bit integer. Please use the neighboring leaf,
                             time-used, it is 64-bit.)";
                    }

                    leaf time-used {
                        type types-sros:time-duration-64;
                        units "microseconds";
                        description "Number of microseconds used by this group/core since start-up.";
                    }

                    leaf cpu-usage {
                        type decimal64 {
                            range "0..100";
                            fraction-digits 2;
                        }
                        units "percent";
                        description "Relative amount of time used by this group/core since start-up.";
                    }

                    leaf capacity-usage {
                        type decimal64 {
                            range "0..100";
                            fraction-digits 2;
                        }
                        units "percent";
                        description "Relative amount of time used by the busiest task/core.";
                    }

                } // container mpls-rsvp

                container mscp {
                    description "Enter the mscp context";

                    leaf cpu-time {
                        status deprecated;
                        type types-sros:time-duration;
                        units "microseconds";
                        description
                            "Number of microseconds used by this group/core. (This leaf may experience
                             overflow because it is a 32-bit integer. Please use the neighboring leaf,
                             time-used, it is 64-bit.)";
                    }

                    leaf time-used {
                        type types-sros:time-duration-64;
                        units "microseconds";
                        description "Number of microseconds used by this group/core since start-up.";
                    }

                    leaf cpu-usage {
                        type decimal64 {
                            range "0..100";
                            fraction-digits 2;
                        }
                        units "percent";
                        description "Relative amount of time used by this group/core since start-up.";
                    }

                    leaf capacity-usage {
                        type decimal64 {
                            range "0..100";
                            fraction-digits 2;
                        }
                        units "percent";
                        description "Relative amount of time used by the busiest task/core.";
                    }

                } // container mscp

                container msdp {
                    description "Enter the msdp context";

                    leaf cpu-time {
                        status deprecated;
                        type types-sros:time-duration;
                        units "microseconds";
                        description
                            "Number of microseconds used by this group/core. (This leaf may experience
                             overflow because it is a 32-bit integer. Please use the neighboring leaf,
                             time-used, it is 64-bit.)";
                    }

                    leaf time-used {
                        type types-sros:time-duration-64;
                        units "microseconds";
                        description "Number of microseconds used by this group/core since start-up.";
                    }

                    leaf cpu-usage {
                        type decimal64 {
                            range "0..100";
                            fraction-digits 2;
                        }
                        units "percent";
                        description "Relative amount of time used by this group/core since start-up.";
                    }

                    leaf capacity-usage {
                        type decimal64 {
                            range "0..100";
                            fraction-digits 2;
                        }
                        units "percent";
                        description "Relative amount of time used by the busiest task/core.";
                    }

                } // container msdp

                container management {
                    description "Enter the management context";

                    leaf cpu-time {
                        status deprecated;
                        type types-sros:time-duration;
                        units "microseconds";
                        description
                            "Number of microseconds used by this group/core. (This leaf may experience
                             overflow because it is a 32-bit integer. Please use the neighboring leaf,
                             time-used, it is 64-bit.)";
                    }

                    leaf time-used {
                        type types-sros:time-duration-64;
                        units "microseconds";
                        description "Number of microseconds used by this group/core since start-up.";
                    }

                    leaf cpu-usage {
                        type decimal64 {
                            range "0..100";
                            fraction-digits 2;
                        }
                        units "percent";
                        description "Relative amount of time used by this group/core since start-up.";
                    }

                    leaf capacity-usage {
                        type decimal64 {
                            range "0..100";
                            fraction-digits 2;
                        }
                        units "percent";
                        description "Relative amount of time used by the busiest task/core.";
                    }

                } // container management

                container oam {
                    description "Enter the oam context";

                    leaf cpu-time {
                        status deprecated;
                        type types-sros:time-duration;
                        units "microseconds";
                        description
                            "Number of microseconds used by this group/core. (This leaf may experience
                             overflow because it is a 32-bit integer. Please use the neighboring leaf,
                             time-used, it is 64-bit.)";
                    }

                    leaf time-used {
                        type types-sros:time-duration-64;
                        units "microseconds";
                        description "Number of microseconds used by this group/core since start-up.";
                    }

                    leaf cpu-usage {
                        type decimal64 {
                            range "0..100";
                            fraction-digits 2;
                        }
                        units "percent";
                        description "Relative amount of time used by this group/core since start-up.";
                    }

                    leaf capacity-usage {
                        type decimal64 {
                            range "0..100";
                            fraction-digits 2;
                        }
                        units "percent";
                        description "Relative amount of time used by the busiest task/core.";
                    }

                } // container oam

                container ospf {
                    description "Enter the ospf context";

                    leaf cpu-time {
                        status deprecated;
                        type types-sros:time-duration;
                        units "microseconds";
                        description
                            "Number of microseconds used by this group/core. (This leaf may experience
                             overflow because it is a 32-bit integer. Please use the neighboring leaf,
                             time-used, it is 64-bit.)";
                    }

                    leaf time-used {
                        type types-sros:time-duration-64;
                        units "microseconds";
                        description "Number of microseconds used by this group/core since start-up.";
                    }

                    leaf cpu-usage {
                        type decimal64 {
                            range "0..100";
                            fraction-digits 2;
                        }
                        units "percent";
                        description "Relative amount of time used by this group/core since start-up.";
                    }

                    leaf capacity-usage {
                        type decimal64 {
                            range "0..100";
                            fraction-digits 2;
                        }
                        units "percent";
                        description "Relative amount of time used by the busiest task/core.";
                    }

                } // container ospf

                container openflow {
                    status obsolete;
                    description "Enter the openflow context";

                    leaf cpu-time {
                        status obsolete;
                        type types-sros:time-duration;
                        units "microseconds";
                        description
                            "Number of microseconds used by this group/core. (This leaf may experience
                             overflow because it is a 32-bit integer. Please use the neighboring leaf,
                             time-used, it is 64-bit.)";
                    }

                    leaf time-used {
                        status obsolete;
                        type types-sros:time-duration-64;
                        units "microseconds";
                        description "Number of microseconds used by this group/core since start-up.";
                    }

                    leaf cpu-usage {
                        status obsolete;
                        type decimal64 {
                            range "0..100";
                            fraction-digits 2;
                        }
                        units "percent";
                        description "Relative amount of time used by this group/core since start-up.";
                    }

                    leaf capacity-usage {
                        status obsolete;
                        type decimal64 {
                            range "0..100";
                            fraction-digits 2;
                        }
                        units "percent";
                        description "Relative amount of time used by the busiest task/core.";
                    }

                } // container openflow

                container sdn-protocols {
                    description "Enter the sdn-protocols context";

                    leaf cpu-time {
                        status deprecated;
                        type types-sros:time-duration;
                        units "microseconds";
                        description
                            "Number of microseconds used by this group/core. (This leaf may experience
                             overflow because it is a 32-bit integer. Please use the neighboring leaf,
                             time-used, it is 64-bit.)";
                    }

                    leaf time-used {
                        type types-sros:time-duration-64;
                        units "microseconds";
                        description "Number of microseconds used by this group/core since start-up.";
                    }

                    leaf cpu-usage {
                        type decimal64 {
                            range "0..100";
                            fraction-digits 2;
                        }
                        units "percent";
                        description "Relative amount of time used by this group/core since start-up.";
                    }

                    leaf capacity-usage {
                        type decimal64 {
                            range "0..100";
                            fraction-digits 2;
                        }
                        units "percent";
                        description "Relative amount of time used by the busiest task/core.";
                    }

                } // container sdn-protocols

                container pim-l2mcast {
                    description "Enter the pim-l2mcast context";

                    leaf cpu-time {
                        status deprecated;
                        type types-sros:time-duration;
                        units "microseconds";
                        description
                            "Number of microseconds used by this group/core. (This leaf may experience
                             overflow because it is a 32-bit integer. Please use the neighboring leaf,
                             time-used, it is 64-bit.)";
                    }

                    leaf time-used {
                        type types-sros:time-duration-64;
                        units "microseconds";
                        description "Number of microseconds used by this group/core since start-up.";
                    }

                    leaf cpu-usage {
                        type decimal64 {
                            range "0..100";
                            fraction-digits 2;
                        }
                        units "percent";
                        description "Relative amount of time used by this group/core since start-up.";
                    }

                    leaf capacity-usage {
                        type decimal64 {
                            range "0..100";
                            fraction-digits 2;
                        }
                        units "percent";
                        description "Relative amount of time used by the busiest task/core.";
                    }

                } // container pim-l2mcast

                container pki {
                    description "Enter the pki context";

                    leaf cpu-time {
                        status deprecated;
                        type types-sros:time-duration;
                        units "microseconds";
                        description
                            "Number of microseconds used by this group/core. (This leaf may experience
                             overflow because it is a 32-bit integer. Please use the neighboring leaf,
                             time-used, it is 64-bit.)";
                    }

                    leaf time-used {
                        type types-sros:time-duration-64;
                        units "microseconds";
                        description "Number of microseconds used by this group/core since start-up.";
                    }

                    leaf cpu-usage {
                        type decimal64 {
                            range "0..100";
                            fraction-digits 2;
                        }
                        units "percent";
                        description "Relative amount of time used by this group/core since start-up.";
                    }

                    leaf capacity-usage {
                        type decimal64 {
                            range "0..100";
                            fraction-digits 2;
                        }
                        units "percent";
                        description "Relative amount of time used by the busiest task/core.";
                    }

                } // container pki

                container ptp {
                    description "Enter the ptp context";

                    leaf cpu-time {
                        status deprecated;
                        type types-sros:time-duration;
                        units "microseconds";
                        description
                            "Number of microseconds used by this group/core. (This leaf may experience
                             overflow because it is a 32-bit integer. Please use the neighboring leaf,
                             time-used, it is 64-bit.)";
                    }

                    leaf time-used {
                        type types-sros:time-duration-64;
                        units "microseconds";
                        description "Number of microseconds used by this group/core since start-up.";
                    }

                    leaf cpu-usage {
                        type decimal64 {
                            range "0..100";
                            fraction-digits 2;
                        }
                        units "percent";
                        description "Relative amount of time used by this group/core since start-up.";
                    }

                    leaf capacity-usage {
                        type decimal64 {
                            range "0..100";
                            fraction-digits 2;
                        }
                        units "percent";
                        description "Relative amount of time used by the busiest task/core.";
                    }

                } // container ptp

                container rip {
                    description "Enter the rip context";

                    leaf cpu-time {
                        status deprecated;
                        type types-sros:time-duration;
                        units "microseconds";
                        description
                            "Number of microseconds used by this group/core. (This leaf may experience
                             overflow because it is a 32-bit integer. Please use the neighboring leaf,
                             time-used, it is 64-bit.)";
                    }

                    leaf time-used {
                        type types-sros:time-duration-64;
                        units "microseconds";
                        description "Number of microseconds used by this group/core since start-up.";
                    }

                    leaf cpu-usage {
                        type decimal64 {
                            range "0..100";
                            fraction-digits 2;
                        }
                        units "percent";
                        description "Relative amount of time used by this group/core since start-up.";
                    }

                    leaf capacity-usage {
                        type decimal64 {
                            range "0..100";
                            fraction-digits 2;
                        }
                        units "percent";
                        description "Relative amount of time used by the busiest task/core.";
                    }

                } // container rip

                container rtm-policies {
                    description "Enter the rtm-policies context";

                    leaf cpu-time {
                        status deprecated;
                        type types-sros:time-duration;
                        units "microseconds";
                        description
                            "Number of microseconds used by this group/core. (This leaf may experience
                             overflow because it is a 32-bit integer. Please use the neighboring leaf,
                             time-used, it is 64-bit.)";
                    }

                    leaf time-used {
                        type types-sros:time-duration-64;
                        units "microseconds";
                        description "Number of microseconds used by this group/core since start-up.";
                    }

                    leaf cpu-usage {
                        type decimal64 {
                            range "0..100";
                            fraction-digits 2;
                        }
                        units "percent";
                        description "Relative amount of time used by this group/core since start-up.";
                    }

                    leaf capacity-usage {
                        type decimal64 {
                            range "0..100";
                            fraction-digits 2;
                        }
                        units "percent";
                        description "Relative amount of time used by the busiest task/core.";
                    }

                } // container rtm-policies

                container redundancy {
                    description "Enter the redundancy context";

                    leaf cpu-time {
                        status deprecated;
                        type types-sros:time-duration;
                        units "microseconds";
                        description
                            "Number of microseconds used by this group/core. (This leaf may experience
                             overflow because it is a 32-bit integer. Please use the neighboring leaf,
                             time-used, it is 64-bit.)";
                    }

                    leaf time-used {
                        type types-sros:time-duration-64;
                        units "microseconds";
                        description "Number of microseconds used by this group/core since start-up.";
                    }

                    leaf cpu-usage {
                        type decimal64 {
                            range "0..100";
                            fraction-digits 2;
                        }
                        units "percent";
                        description "Relative amount of time used by this group/core since start-up.";
                    }

                    leaf capacity-usage {
                        type decimal64 {
                            range "0..100";
                            fraction-digits 2;
                        }
                        units "percent";
                        description "Relative amount of time used by the busiest task/core.";
                    }

                } // container redundancy

                container sim {
                    description "Enter the sim context";

                    leaf cpu-time {
                        status deprecated;
                        type types-sros:time-duration;
                        units "microseconds";
                        description
                            "Number of microseconds used by this group/core. (This leaf may experience
                             overflow because it is a 32-bit integer. Please use the neighboring leaf,
                             time-used, it is 64-bit.)";
                    }

                    leaf time-used {
                        type types-sros:time-duration-64;
                        units "microseconds";
                        description "Number of microseconds used by this group/core since start-up.";
                    }

                    leaf cpu-usage {
                        type decimal64 {
                            range "0..100";
                            fraction-digits 2;
                        }
                        units "percent";
                        description "Relative amount of time used by this group/core since start-up.";
                    }

                    leaf capacity-usage {
                        type decimal64 {
                            range "0..100";
                            fraction-digits 2;
                        }
                        units "percent";
                        description "Relative amount of time used by the busiest task/core.";
                    }

                } // container sim

                container snmp-daemon {
                    description "Enter the snmp-daemon context";

                    leaf cpu-time {
                        status deprecated;
                        type types-sros:time-duration;
                        units "microseconds";
                        description
                            "Number of microseconds used by this group/core. (This leaf may experience
                             overflow because it is a 32-bit integer. Please use the neighboring leaf,
                             time-used, it is 64-bit.)";
                    }

                    leaf time-used {
                        type types-sros:time-duration-64;
                        units "microseconds";
                        description "Number of microseconds used by this group/core since start-up.";
                    }

                    leaf cpu-usage {
                        type decimal64 {
                            range "0..100";
                            fraction-digits 2;
                        }
                        units "percent";
                        description "Relative amount of time used by this group/core since start-up.";
                    }

                    leaf capacity-usage {
                        type decimal64 {
                            range "0..100";
                            fraction-digits 2;
                        }
                        units "percent";
                        description "Relative amount of time used by the busiest task/core.";
                    }

                } // container snmp-daemon

                container security {
                    description "Enter the security context";

                    leaf cpu-time {
                        status deprecated;
                        type types-sros:time-duration;
                        units "microseconds";
                        description
                            "Number of microseconds used by this group/core. (This leaf may experience
                             overflow because it is a 32-bit integer. Please use the neighboring leaf,
                             time-used, it is 64-bit.)";
                    }

                    leaf time-used {
                        type types-sros:time-duration-64;
                        units "microseconds";
                        description "Number of microseconds used by this group/core since start-up.";
                    }

                    leaf cpu-usage {
                        type decimal64 {
                            range "0..100";
                            fraction-digits 2;
                        }
                        units "percent";
                        description "Relative amount of time used by this group/core since start-up.";
                    }

                    leaf capacity-usage {
                        type decimal64 {
                            range "0..100";
                            fraction-digits 2;
                        }
                        units "percent";
                        description "Relative amount of time used by the busiest task/core.";
                    }

                } // container security

                container services {
                    description "Enter the services context";

                    leaf cpu-time {
                        status deprecated;
                        type types-sros:time-duration;
                        units "microseconds";
                        description
                            "Number of microseconds used by this group/core. (This leaf may experience
                             overflow because it is a 32-bit integer. Please use the neighboring leaf,
                             time-used, it is 64-bit.)";
                    }

                    leaf time-used {
                        type types-sros:time-duration-64;
                        units "microseconds";
                        description "Number of microseconds used by this group/core since start-up.";
                    }

                    leaf cpu-usage {
                        type decimal64 {
                            range "0..100";
                            fraction-digits 2;
                        }
                        units "percent";
                        description "Relative amount of time used by this group/core since start-up.";
                    }

                    leaf capacity-usage {
                        type decimal64 {
                            range "0..100";
                            fraction-digits 2;
                        }
                        units "percent";
                        description "Relative amount of time used by the busiest task/core.";
                    }

                } // container services

                container stats {
                    description "Enter the stats context";

                    leaf cpu-time {
                        status deprecated;
                        type types-sros:time-duration;
                        units "microseconds";
                        description
                            "Number of microseconds used by this group/core. (This leaf may experience
                             overflow because it is a 32-bit integer. Please use the neighboring leaf,
                             time-used, it is 64-bit.)";
                    }

                    leaf time-used {
                        type types-sros:time-duration-64;
                        units "microseconds";
                        description "Number of microseconds used by this group/core since start-up.";
                    }

                    leaf cpu-usage {
                        type decimal64 {
                            range "0..100";
                            fraction-digits 2;
                        }
                        units "percent";
                        description "Relative amount of time used by this group/core since start-up.";
                    }

                    leaf capacity-usage {
                        type decimal64 {
                            range "0..100";
                            fraction-digits 2;
                        }
                        units "percent";
                        description "Relative amount of time used by the busiest task/core.";
                    }

                } // container stats

                container stats-extended {
                    description "Enter the stats-extended context";

                    leaf cpu-time {
                        status deprecated;
                        type types-sros:time-duration;
                        units "microseconds";
                        description
                            "Number of microseconds used by this group/core. (This leaf may experience
                             overflow because it is a 32-bit integer. Please use the neighboring leaf,
                             time-used, it is 64-bit.)";
                    }

                    leaf time-used {
                        type types-sros:time-duration-64;
                        units "microseconds";
                        description "Number of microseconds used by this group/core since start-up.";
                    }

                    leaf cpu-usage {
                        type decimal64 {
                            range "0..100";
                            fraction-digits 2;
                        }
                        units "percent";
                        description "Relative amount of time used by this group/core since start-up.";
                    }

                    leaf capacity-usage {
                        type decimal64 {
                            range "0..100";
                            fraction-digits 2;
                        }
                        units "percent";
                        description "Relative amount of time used by the busiest task/core.";
                    }

                } // container stats-extended

                container subscriber-mgmt {
                    description "Enter the subscriber-mgmt context";

                    leaf cpu-time {
                        status deprecated;
                        type types-sros:time-duration;
                        units "microseconds";
                        description
                            "Number of microseconds used by this group/core. (This leaf may experience
                             overflow because it is a 32-bit integer. Please use the neighboring leaf,
                             time-used, it is 64-bit.)";
                    }

                    leaf time-used {
                        type types-sros:time-duration-64;
                        units "microseconds";
                        description "Number of microseconds used by this group/core since start-up.";
                    }

                    leaf cpu-usage {
                        type decimal64 {
                            range "0..100";
                            fraction-digits 2;
                        }
                        units "percent";
                        description "Relative amount of time used by this group/core since start-up.";
                    }

                    leaf capacity-usage {
                        type decimal64 {
                            range "0..100";
                            fraction-digits 2;
                        }
                        units "percent";
                        description "Relative amount of time used by the busiest task/core.";
                    }

                } // container subscriber-mgmt

                container system {
                    description "Enter the system context";

                    leaf cpu-time {
                        status deprecated;
                        type types-sros:time-duration;
                        units "microseconds";
                        description
                            "Number of microseconds used by this group/core. (This leaf may experience
                             overflow because it is a 32-bit integer. Please use the neighboring leaf,
                             time-used, it is 64-bit.)";
                    }

                    leaf time-used {
                        type types-sros:time-duration-64;
                        units "microseconds";
                        description "Number of microseconds used by this group/core since start-up.";
                    }

                    leaf cpu-usage {
                        type decimal64 {
                            range "0..100";
                            fraction-digits 2;
                        }
                        units "percent";
                        description "Relative amount of time used by this group/core since start-up.";
                    }

                    leaf capacity-usage {
                        type decimal64 {
                            range "0..100";
                            fraction-digits 2;
                        }
                        units "percent";
                        description "Relative amount of time used by the busiest task/core.";
                    }

                } // container system

                container traffic-eng {
                    description "Enter the traffic-eng context";

                    leaf cpu-time {
                        status deprecated;
                        type types-sros:time-duration;
                        units "microseconds";
                        description
                            "Number of microseconds used by this group/core. (This leaf may experience
                             overflow because it is a 32-bit integer. Please use the neighboring leaf,
                             time-used, it is 64-bit.)";
                    }

                    leaf time-used {
                        type types-sros:time-duration-64;
                        units "microseconds";
                        description "Number of microseconds used by this group/core since start-up.";
                    }

                    leaf cpu-usage {
                        type decimal64 {
                            range "0..100";
                            fraction-digits 2;
                        }
                        units "percent";
                        description "Relative amount of time used by this group/core since start-up.";
                    }

                    leaf capacity-usage {
                        type decimal64 {
                            range "0..100";
                            fraction-digits 2;
                        }
                        units "percent";
                        description "Relative amount of time used by the busiest task/core.";
                    }

                } // container traffic-eng

                container tree-sid {
                    description "Enter the tree-sid context";

                    leaf cpu-time {
                        status deprecated;
                        type types-sros:time-duration;
                        units "microseconds";
                        description
                            "Number of microseconds used by this group/core. (This leaf may experience
                             overflow because it is a 32-bit integer. Please use the neighboring leaf,
                             time-used, it is 64-bit.)";
                    }

                    leaf time-used {
                        type types-sros:time-duration-64;
                        units "microseconds";
                        description "Number of microseconds used by this group/core since start-up.";
                    }

                    leaf cpu-usage {
                        type decimal64 {
                            range "0..100";
                            fraction-digits 2;
                        }
                        units "percent";
                        description "Relative amount of time used by this group/core since start-up.";
                    }

                    leaf capacity-usage {
                        type decimal64 {
                            range "0..100";
                            fraction-digits 2;
                        }
                        units "percent";
                        description "Relative amount of time used by the busiest task/core.";
                    }

                } // container tree-sid

                container vrrp {
                    description "Enter the vrrp context";

                    leaf cpu-time {
                        status deprecated;
                        type types-sros:time-duration;
                        units "microseconds";
                        description
                            "Number of microseconds used by this group/core. (This leaf may experience
                             overflow because it is a 32-bit integer. Please use the neighboring leaf,
                             time-used, it is 64-bit.)";
                    }

                    leaf time-used {
                        type types-sros:time-duration-64;
                        units "microseconds";
                        description "Number of microseconds used by this group/core since start-up.";
                    }

                    leaf cpu-usage {
                        type decimal64 {
                            range "0..100";
                            fraction-digits 2;
                        }
                        units "percent";
                        description "Relative amount of time used by this group/core since start-up.";
                    }

                    leaf capacity-usage {
                        type decimal64 {
                            range "0..100";
                            fraction-digits 2;
                        }
                        units "percent";
                        description "Relative amount of time used by the busiest task/core.";
                    }

                } // container vrrp

                container web-redirect {
                    description "Enter the web-redirect context";

                    leaf cpu-time {
                        status deprecated;
                        type types-sros:time-duration;
                        units "microseconds";
                        description
                            "Number of microseconds used by this group/core. (This leaf may experience
                             overflow because it is a 32-bit integer. Please use the neighboring leaf,
                             time-used, it is 64-bit.)";
                    }

                    leaf time-used {
                        type types-sros:time-duration-64;
                        units "microseconds";
                        description "Number of microseconds used by this group/core since start-up.";
                    }

                    leaf cpu-usage {
                        type decimal64 {
                            range "0..100";
                            fraction-digits 2;
                        }
                        units "percent";
                        description "Relative amount of time used by this group/core since start-up.";
                    }

                    leaf capacity-usage {
                        type decimal64 {
                            range "0..100";
                            fraction-digits 2;
                        }
                        units "percent";
                        description "Relative amount of time used by the busiest task/core.";
                    }

                } // container web-redirect






                container hqos-algorithm {
                    description "Enter the hqos-algorithm context";

                    leaf cpu-time {
                        status deprecated;
                        type types-sros:time-duration;
                        units "microseconds";
                        description
                            "Number of microseconds used by this group/core. (This leaf may experience
                             overflow because it is a 32-bit integer. Please use the neighboring leaf,
                             time-used, it is 64-bit.)";
                    }

                    leaf time-used {
                        type types-sros:time-duration-64;
                        units "microseconds";
                        description "Number of microseconds used by this group/core since start-up.";
                    }

                    leaf cpu-usage {
                        type decimal64 {
                            range "0..100";
                            fraction-digits 2;
                        }
                        units "percent";
                        description "Relative amount of time used by this group/core since start-up.";
                    }

                    leaf capacity-usage {
                        type decimal64 {
                            range "0..100";
                            fraction-digits 2;
                        }
                        units "percent";
                        description "Relative amount of time used by the busiest task/core.";
                    }

                } // container hqos-algorithm

                container hqos-statistics {
                    description "Enter the hqos-statistics context";

                    leaf cpu-time {
                        status deprecated;
                        type types-sros:time-duration;
                        units "microseconds";
                        description
                            "Number of microseconds used by this group/core. (This leaf may experience
                             overflow because it is a 32-bit integer. Please use the neighboring leaf,
                             time-used, it is 64-bit.)";
                    }

                    leaf time-used {
                        type types-sros:time-duration-64;
                        units "microseconds";
                        description "Number of microseconds used by this group/core since start-up.";
                    }

                    leaf cpu-usage {
                        type decimal64 {
                            range "0..100";
                            fraction-digits 2;
                        }
                        units "percent";
                        description "Relative amount of time used by this group/core since start-up.";
                    }

                    leaf capacity-usage {
                        type decimal64 {
                            range "0..100";
                            fraction-digits 2;
                        }
                        units "percent";
                        description "Relative amount of time used by the busiest task/core.";
                    }

                } // container hqos-statistics

                container iom {
                    description "Enter the iom context";

                    leaf cpu-time {
                        status deprecated;
                        type types-sros:time-duration;
                        units "microseconds";
                        description
                            "Number of microseconds used by this group/core. (This leaf may experience
                             overflow because it is a 32-bit integer. Please use the neighboring leaf,
                             time-used, it is 64-bit.)";
                    }

                    leaf time-used {
                        type types-sros:time-duration-64;
                        units "microseconds";
                        description "Number of microseconds used by this group/core since start-up.";
                    }

                    leaf cpu-usage {
                        type decimal64 {
                            range "0..100";
                            fraction-digits 2;
                        }
                        units "percent";
                        description "Relative amount of time used by this group/core since start-up.";
                    }

                    leaf capacity-usage {
                        type decimal64 {
                            range "0..100";
                            fraction-digits 2;
                        }
                        units "percent";
                        description "Relative amount of time used by the busiest task/core.";
                    }

                } // container iom

                container summary {
                    description "Enter the summary context";

                    container total {
                        description "Enter the total context";

                        leaf cpu-time {
                            status deprecated;
                            type types-sros:time-duration;
                            units "microseconds";
                            description
                                "Number of microseconds used by this group/core. (This leaf may experience
                                 overflow because it is a 32-bit integer. Please use the neighboring leaf,
                                 time-used, it is 64-bit.)";
                        }

                        leaf time-used {
                            type types-sros:time-duration-64;
                            units "microseconds";
                            description "Number of microseconds used by this group/core since start-up.";
                        }

                        leaf cpu-usage {
                            type decimal64 {
                                range "0..100";
                                fraction-digits 2;
                            }
                            units "percent";
                            description "Relative amount of time used by this group/core since start-up.";
                        }

                    } // container total

                    container idle {
                        description "Enter the idle context";

                        leaf cpu-time {
                            status deprecated;
                            type types-sros:time-duration;
                            units "microseconds";
                            description
                                "Number of microseconds used by this group/core. (This leaf may experience
                                 overflow because it is a 32-bit integer. Please use the neighboring leaf,
                                 time-used, it is 64-bit.)";
                        }

                        leaf time-used {
                            type types-sros:time-duration-64;
                            units "microseconds";
                            description "Number of microseconds used by this group/core since start-up.";
                        }

                        leaf cpu-usage {
                            type decimal64 {
                                range "0..100";
                                fraction-digits 2;
                            }
                            units "percent";
                            description "Relative amount of time used by this group/core since start-up.";
                        }

                    } // container idle

                    container usage {
                        description "Enter the usage context";

                        leaf cpu-time {
                            status deprecated;
                            type types-sros:time-duration;
                            units "microseconds";
                            description
                                "Number of microseconds used by this group/core. (This leaf may experience
                                 overflow because it is a 32-bit integer. Please use the neighboring leaf,
                                 time-used, it is 64-bit.)";
                        }

                        leaf time-used {
                            type types-sros:time-duration-64;
                            units "microseconds";
                            description "Number of microseconds used by this group/core since start-up.";
                        }

                        leaf cpu-usage {
                            type decimal64 {
                                range "0..100";
                                fraction-digits 2;
                            }
                            units "percent";
                            description "Relative amount of time used by this group/core since start-up.";
                        }

                    } // container usage

                    container busiest-core-utilization {
                        description "Enter the busiest-core-utilization context";

                        leaf cpu-time {
                            status deprecated;
                            type types-sros:time-duration;
                            units "microseconds";
                            description
                                "Number of microseconds used by this group/core. (This leaf may experience
                                 overflow because it is a 32-bit integer. Please use the neighboring leaf,
                                 time-used, it is 64-bit.)";
                        }

                        leaf time-used {
                            type types-sros:time-duration-64;
                            units "microseconds";
                            description "Number of microseconds used by this group/core since start-up.";
                        }

                        leaf cpu-usage {
                            type decimal64 {
                                range "0..100";
                                fraction-digits 2;
                            }
                            units "percent";
                            description "Relative amount of time used by this group/core since start-up.";
                        }

                    } // container busiest-core-utilization

                } // container summary

            } // list cpu

            container memory-pools {
                description "Enter the memory-pools context";

                container bfd {
                    description "Enter the bfd context";

                    leaf max-allowed {
                        type uint64 {
                            range "1..max";
                        }
                        units "bytes";
                        description "Maximum allowed amount of memory that can be allocated for a group.";
                    }

                    leaf current-size {
                        type uint64 {
                            range "0..max";
                        }
                        units "bytes";
                        description "Current amount of allocated memory for a group.";
                    }

                    leaf max-so-far {
                        type uint64 {
                            range "0..max";
                        }
                        units "bytes";
                        description "The highest amount of allocated memory for a group.";
                    }

                    leaf in-use {
                        type uint64 {
                            range "0..max";
                        }
                        units "bytes";
                        description "Amount of memory used by group.";
                    }

                } // container bfd

                container bgp {
                    description "Enter the bgp context";

                    leaf max-allowed {
                        type uint64 {
                            range "1..max";
                        }
                        units "bytes";
                        description "Maximum allowed amount of memory that can be allocated for a group.";
                    }

                    leaf current-size {
                        type uint64 {
                            range "0..max";
                        }
                        units "bytes";
                        description "Current amount of allocated memory for a group.";
                    }

                    leaf max-so-far {
                        type uint64 {
                            range "0..max";
                        }
                        units "bytes";
                        description "The highest amount of allocated memory for a group.";
                    }

                    leaf in-use {
                        type uint64 {
                            range "0..max";
                        }
                        units "bytes";
                        description "Amount of memory used by group.";
                    }

                } // container bgp

                container bgp-pe-ce {
                    description "Enter the bgp-pe-ce context";

                    leaf max-allowed {
                        type uint64 {
                            range "1..max";
                        }
                        units "bytes";
                        description "Maximum allowed amount of memory that can be allocated for a group.";
                    }

                    leaf current-size {
                        type uint64 {
                            range "0..max";
                        }
                        units "bytes";
                        description "Current amount of allocated memory for a group.";
                    }

                    leaf max-so-far {
                        type uint64 {
                            range "0..max";
                        }
                        units "bytes";
                        description "The highest amount of allocated memory for a group.";
                    }

                    leaf in-use {
                        type uint64 {
                            range "0..max";
                        }
                        units "bytes";
                        description "Amount of memory used by group.";
                    }

                } // container bgp-pe-ce

                container bier {
                    description "Enter the bier context";

                    leaf max-allowed {
                        type uint64 {
                            range "1..max";
                        }
                        units "bytes";
                        description "Maximum allowed amount of memory that can be allocated for a group.";
                    }

                    leaf current-size {
                        type uint64 {
                            range "0..max";
                        }
                        units "bytes";
                        description "Current amount of allocated memory for a group.";
                    }

                    leaf max-so-far {
                        type uint64 {
                            range "0..max";
                        }
                        units "bytes";
                        description "The highest amount of allocated memory for a group.";
                    }

                    leaf in-use {
                        type uint64 {
                            range "0..max";
                        }
                        units "bytes";
                        description "Amount of memory used by group.";
                    }

                } // container bier

                container calltrace {
                    description "Enter the calltrace context";

                    leaf max-allowed {
                        type uint64 {
                            range "1..max";
                        }
                        units "bytes";
                        description "Maximum allowed amount of memory that can be allocated for a group.";
                    }

                    leaf current-size {
                        type uint64 {
                            range "0..max";
                        }
                        units "bytes";
                        description "Current amount of allocated memory for a group.";
                    }

                    leaf max-so-far {
                        type uint64 {
                            range "0..max";
                        }
                        units "bytes";
                        description "The highest amount of allocated memory for a group.";
                    }

                    leaf in-use {
                        type uint64 {
                            range "0..max";
                        }
                        units "bytes";
                        description "Amount of memory used by group.";
                    }

                } // container calltrace

                container cflowd {
                    description "Enter the cflowd context";

                    leaf max-allowed {
                        type uint64 {
                            range "1..max";
                        }
                        units "bytes";
                        description "Maximum allowed amount of memory that can be allocated for a group.";
                    }

                    leaf current-size {
                        type uint64 {
                            range "0..max";
                        }
                        units "bytes";
                        description "Current amount of allocated memory for a group.";
                    }

                    leaf max-so-far {
                        type uint64 {
                            range "0..max";
                        }
                        units "bytes";
                        description "The highest amount of allocated memory for a group.";
                    }

                    leaf in-use {
                        type uint64 {
                            range "0..max";
                        }
                        units "bytes";
                        description "Amount of memory used by group.";
                    }

                } // container cflowd

                container cards-and-ports {
                    description "Enter the cards-and-ports context";

                    leaf max-allowed {
                        type uint64 {
                            range "1..max";
                        }
                        units "bytes";
                        description "Maximum allowed amount of memory that can be allocated for a group.";
                    }

                    leaf current-size {
                        type uint64 {
                            range "0..max";
                        }
                        units "bytes";
                        description "Current amount of allocated memory for a group.";
                    }

                    leaf max-so-far {
                        type uint64 {
                            range "0..max";
                        }
                        units "bytes";
                        description "The highest amount of allocated memory for a group.";
                    }

                    leaf in-use {
                        type uint64 {
                            range "0..max";
                        }
                        units "bytes";
                        description "Amount of memory used by group.";
                    }

                } // container cards-and-ports

                container dhcp-server {
                    description "Enter the dhcp-server context";

                    leaf max-allowed {
                        type uint64 {
                            range "1..max";
                        }
                        units "bytes";
                        description "Maximum allowed amount of memory that can be allocated for a group.";
                    }

                    leaf current-size {
                        type uint64 {
                            range "0..max";
                        }
                        units "bytes";
                        description "Current amount of allocated memory for a group.";
                    }

                    leaf max-so-far {
                        type uint64 {
                            range "0..max";
                        }
                        units "bytes";
                        description "The highest amount of allocated memory for a group.";
                    }

                    leaf in-use {
                        type uint64 {
                            range "0..max";
                        }
                        units "bytes";
                        description "Amount of memory used by group.";
                    }

                } // container dhcp-server

                container eth-cfm {
                    description "Enter the eth-cfm context";

                    leaf max-allowed {
                        type uint64 {
                            range "1..max";
                        }
                        units "bytes";
                        description "Maximum allowed amount of memory that can be allocated for a group.";
                    }

                    leaf current-size {
                        type uint64 {
                            range "0..max";
                        }
                        units "bytes";
                        description "Current amount of allocated memory for a group.";
                    }

                    leaf max-so-far {
                        type uint64 {
                            range "0..max";
                        }
                        units "bytes";
                        description "The highest amount of allocated memory for a group.";
                    }

                    leaf in-use {
                        type uint64 {
                            range "0..max";
                        }
                        units "bytes";
                        description "Amount of memory used by group.";
                    }

                } // container eth-cfm

                container fastpath {
                    description "Enter the fastpath context";

                    leaf max-allowed {
                        type uint64 {
                            range "1..max";
                        }
                        units "bytes";
                        description "Maximum allowed amount of memory that can be allocated for a group.";
                    }

                    leaf current-size {
                        type uint64 {
                            range "0..max";
                        }
                        units "bytes";
                        description "Current amount of allocated memory for a group.";
                    }

                    leaf max-so-far {
                        type uint64 {
                            range "0..max";
                        }
                        units "bytes";
                        description "The highest amount of allocated memory for a group.";
                    }

                    leaf in-use {
                        type uint64 {
                            range "0..max";
                        }
                        units "bytes";
                        description "Amount of memory used by group.";
                    }

                } // container fastpath

                container hqos-algorithm {
                    description "Enter the hqos-algorithm context";

                    leaf max-allowed {
                        type uint64 {
                            range "1..max";
                        }
                        units "bytes";
                        description "Maximum allowed amount of memory that can be allocated for a group.";
                    }

                    leaf current-size {
                        type uint64 {
                            range "0..max";
                        }
                        units "bytes";
                        description "Current amount of allocated memory for a group.";
                    }

                    leaf max-so-far {
                        type uint64 {
                            range "0..max";
                        }
                        units "bytes";
                        description "The highest amount of allocated memory for a group.";
                    }

                    leaf in-use {
                        type uint64 {
                            range "0..max";
                        }
                        units "bytes";
                        description "Amount of memory used by group.";
                    }

                } // container hqos-algorithm

                container hqos-statistics {
                    description "Enter the hqos-statistics context";

                    leaf max-allowed {
                        type uint64 {
                            range "1..max";
                        }
                        units "bytes";
                        description "Maximum allowed amount of memory that can be allocated for a group.";
                    }

                    leaf current-size {
                        type uint64 {
                            range "0..max";
                        }
                        units "bytes";
                        description "Current amount of allocated memory for a group.";
                    }

                    leaf max-so-far {
                        type uint64 {
                            range "0..max";
                        }
                        units "bytes";
                        description "The highest amount of allocated memory for a group.";
                    }

                    leaf in-use {
                        type uint64 {
                            range "0..max";
                        }
                        units "bytes";
                        description "Amount of memory used by group.";
                    }

                } // container hqos-statistics

                container icc {
                    description "Enter the icc context";

                    leaf max-allowed {
                        type uint64 {
                            range "1..max";
                        }
                        units "bytes";
                        description "Maximum allowed amount of memory that can be allocated for a group.";
                    }

                    leaf current-size {
                        type uint64 {
                            range "0..max";
                        }
                        units "bytes";
                        description "Current amount of allocated memory for a group.";
                    }

                    leaf max-so-far {
                        type uint64 {
                            range "0..max";
                        }
                        units "bytes";
                        description "The highest amount of allocated memory for a group.";
                    }

                    leaf in-use {
                        type uint64 {
                            range "0..max";
                        }
                        units "bytes";
                        description "Amount of memory used by group.";
                    }

                } // container icc

                container igmp-mld {
                    description "Enter the igmp-mld context";

                    leaf max-allowed {
                        type uint64 {
                            range "1..max";
                        }
                        units "bytes";
                        description "Maximum allowed amount of memory that can be allocated for a group.";
                    }

                    leaf current-size {
                        type uint64 {
                            range "0..max";
                        }
                        units "bytes";
                        description "Current amount of allocated memory for a group.";
                    }

                    leaf max-so-far {
                        type uint64 {
                            range "0..max";
                        }
                        units "bytes";
                        description "The highest amount of allocated memory for a group.";
                    }

                    leaf in-use {
                        type uint64 {
                            range "0..max";
                        }
                        units "bytes";
                        description "Amount of memory used by group.";
                    }

                } // container igmp-mld

                container imsi-db-appl {
                    description "Enter the imsi-db-appl context";

                    leaf max-allowed {
                        type uint64 {
                            range "1..max";
                        }
                        units "bytes";
                        description "Maximum allowed amount of memory that can be allocated for a group.";
                    }

                    leaf current-size {
                        type uint64 {
                            range "0..max";
                        }
                        units "bytes";
                        description "Current amount of allocated memory for a group.";
                    }

                    leaf max-so-far {
                        type uint64 {
                            range "0..max";
                        }
                        units "bytes";
                        description "The highest amount of allocated memory for a group.";
                    }

                    leaf in-use {
                        type uint64 {
                            range "0..max";
                        }
                        units "bytes";
                        description "Amount of memory used by group.";
                    }

                } // container imsi-db-appl

                container ip-stack {
                    description "Enter the ip-stack context";

                    leaf max-allowed {
                        type uint64 {
                            range "1..max";
                        }
                        units "bytes";
                        description "Maximum allowed amount of memory that can be allocated for a group.";
                    }

                    leaf current-size {
                        type uint64 {
                            range "0..max";
                        }
                        units "bytes";
                        description "Current amount of allocated memory for a group.";
                    }

                    leaf max-so-far {
                        type uint64 {
                            range "0..max";
                        }
                        units "bytes";
                        description "The highest amount of allocated memory for a group.";
                    }

                    leaf in-use {
                        type uint64 {
                            range "0..max";
                        }
                        units "bytes";
                        description "Amount of memory used by group.";
                    }

                } // container ip-stack

                container is-is {
                    description "Enter the is-is context";

                    leaf max-allowed {
                        type uint64 {
                            range "1..max";
                        }
                        units "bytes";
                        description "Maximum allowed amount of memory that can be allocated for a group.";
                    }

                    leaf current-size {
                        type uint64 {
                            range "0..max";
                        }
                        units "bytes";
                        description "Current amount of allocated memory for a group.";
                    }

                    leaf max-so-far {
                        type uint64 {
                            range "0..max";
                        }
                        units "bytes";
                        description "The highest amount of allocated memory for a group.";
                    }

                    leaf in-use {
                        type uint64 {
                            range "0..max";
                        }
                        units "bytes";
                        description "Amount of memory used by group.";
                    }

                } // container is-is

                container isa {
                    description "Enter the isa context";

                    leaf max-allowed {
                        type uint64 {
                            range "1..max";
                        }
                        units "bytes";
                        description "Maximum allowed amount of memory that can be allocated for a group.";
                    }

                    leaf current-size {
                        type uint64 {
                            range "0..max";
                        }
                        units "bytes";
                        description "Current amount of allocated memory for a group.";
                    }

                    leaf max-so-far {
                        type uint64 {
                            range "0..max";
                        }
                        units "bytes";
                        description "The highest amount of allocated memory for a group.";
                    }

                    leaf in-use {
                        type uint64 {
                            range "0..max";
                        }
                        units "bytes";
                        description "Amount of memory used by group.";
                    }

                } // container isa

                container ldp {
                    description "Enter the ldp context";

                    leaf max-allowed {
                        type uint64 {
                            range "1..max";
                        }
                        units "bytes";
                        description "Maximum allowed amount of memory that can be allocated for a group.";
                    }

                    leaf current-size {
                        type uint64 {
                            range "0..max";
                        }
                        units "bytes";
                        description "Current amount of allocated memory for a group.";
                    }

                    leaf max-so-far {
                        type uint64 {
                            range "0..max";
                        }
                        units "bytes";
                        description "The highest amount of allocated memory for a group.";
                    }

                    leaf in-use {
                        type uint64 {
                            range "0..max";
                        }
                        units "bytes";
                        description "Amount of memory used by group.";
                    }

                } // container ldp

                container logging {
                    description "Enter the logging context";

                    leaf max-allowed {
                        type uint64 {
                            range "1..max";
                        }
                        units "bytes";
                        description "Maximum allowed amount of memory that can be allocated for a group.";
                    }

                    leaf current-size {
                        type uint64 {
                            range "0..max";
                        }
                        units "bytes";
                        description "Current amount of allocated memory for a group.";
                    }

                    leaf max-so-far {
                        type uint64 {
                            range "0..max";
                        }
                        units "bytes";
                        description "The highest amount of allocated memory for a group.";
                    }

                    leaf in-use {
                        type uint64 {
                            range "0..max";
                        }
                        units "bytes";
                        description "Amount of memory used by group.";
                    }

                } // container logging

                container mbuf {
                    description "Enter the mbuf context";

                    leaf max-allowed {
                        type uint64 {
                            range "1..max";
                        }
                        units "bytes";
                        description "Maximum allowed amount of memory that can be allocated for a group.";
                    }

                    leaf current-size {
                        type uint64 {
                            range "0..max";
                        }
                        units "bytes";
                        description "Current amount of allocated memory for a group.";
                    }

                    leaf max-so-far {
                        type uint64 {
                            range "0..max";
                        }
                        units "bytes";
                        description "The highest amount of allocated memory for a group.";
                    }

                    leaf in-use {
                        type uint64 {
                            range "0..max";
                        }
                        units "bytes";
                        description "Amount of memory used by group.";
                    }

                } // container mbuf

                container mcs {
                    description "Enter the mcs context";

                    leaf max-allowed {
                        type uint64 {
                            range "1..max";
                        }
                        units "bytes";
                        description "Maximum allowed amount of memory that can be allocated for a group.";
                    }

                    leaf current-size {
                        type uint64 {
                            range "0..max";
                        }
                        units "bytes";
                        description "Current amount of allocated memory for a group.";
                    }

                    leaf max-so-far {
                        type uint64 {
                            range "0..max";
                        }
                        units "bytes";
                        description "The highest amount of allocated memory for a group.";
                    }

                    leaf in-use {
                        type uint64 {
                            range "0..max";
                        }
                        units "bytes";
                        description "Amount of memory used by group.";
                    }

                } // container mcs

                container mpls-rsvp {
                    description "Enter the mpls-rsvp context";

                    leaf max-allowed {
                        type uint64 {
                            range "1..max";
                        }
                        units "bytes";
                        description "Maximum allowed amount of memory that can be allocated for a group.";
                    }

                    leaf current-size {
                        type uint64 {
                            range "0..max";
                        }
                        units "bytes";
                        description "Current amount of allocated memory for a group.";
                    }

                    leaf max-so-far {
                        type uint64 {
                            range "0..max";
                        }
                        units "bytes";
                        description "The highest amount of allocated memory for a group.";
                    }

                    leaf in-use {
                        type uint64 {
                            range "0..max";
                        }
                        units "bytes";
                        description "Amount of memory used by group.";
                    }

                } // container mpls-rsvp

                container mscp {
                    description "Enter the mscp context";

                    leaf max-allowed {
                        type uint64 {
                            range "1..max";
                        }
                        units "bytes";
                        description "Maximum allowed amount of memory that can be allocated for a group.";
                    }

                    leaf current-size {
                        type uint64 {
                            range "0..max";
                        }
                        units "bytes";
                        description "Current amount of allocated memory for a group.";
                    }

                    leaf max-so-far {
                        type uint64 {
                            range "0..max";
                        }
                        units "bytes";
                        description "The highest amount of allocated memory for a group.";
                    }

                    leaf in-use {
                        type uint64 {
                            range "0..max";
                        }
                        units "bytes";
                        description "Amount of memory used by group.";
                    }

                } // container mscp

                container msdp {
                    description "Enter the msdp context";

                    leaf max-allowed {
                        type uint64 {
                            range "1..max";
                        }
                        units "bytes";
                        description "Maximum allowed amount of memory that can be allocated for a group.";
                    }

                    leaf current-size {
                        type uint64 {
                            range "0..max";
                        }
                        units "bytes";
                        description "Current amount of allocated memory for a group.";
                    }

                    leaf max-so-far {
                        type uint64 {
                            range "0..max";
                        }
                        units "bytes";
                        description "The highest amount of allocated memory for a group.";
                    }

                    leaf in-use {
                        type uint64 {
                            range "0..max";
                        }
                        units "bytes";
                        description "Amount of memory used by group.";
                    }

                } // container msdp

                container management {
                    description "Enter the management context";

                    leaf max-allowed {
                        type uint64 {
                            range "1..max";
                        }
                        units "bytes";
                        description "Maximum allowed amount of memory that can be allocated for a group.";
                    }

                    leaf current-size {
                        type uint64 {
                            range "0..max";
                        }
                        units "bytes";
                        description "Current amount of allocated memory for a group.";
                    }

                    leaf max-so-far {
                        type uint64 {
                            range "0..max";
                        }
                        units "bytes";
                        description "The highest amount of allocated memory for a group.";
                    }

                    leaf in-use {
                        type uint64 {
                            range "0..max";
                        }
                        units "bytes";
                        description "Amount of memory used by group.";
                    }

                } // container management

                container oam {
                    description "Enter the oam context";

                    leaf max-allowed {
                        type uint64 {
                            range "1..max";
                        }
                        units "bytes";
                        description "Maximum allowed amount of memory that can be allocated for a group.";
                    }

                    leaf current-size {
                        type uint64 {
                            range "0..max";
                        }
                        units "bytes";
                        description "Current amount of allocated memory for a group.";
                    }

                    leaf max-so-far {
                        type uint64 {
                            range "0..max";
                        }
                        units "bytes";
                        description "The highest amount of allocated memory for a group.";
                    }

                    leaf in-use {
                        type uint64 {
                            range "0..max";
                        }
                        units "bytes";
                        description "Amount of memory used by group.";
                    }

                } // container oam

                container ospf {
                    description "Enter the ospf context";

                    leaf max-allowed {
                        type uint64 {
                            range "1..max";
                        }
                        units "bytes";
                        description "Maximum allowed amount of memory that can be allocated for a group.";
                    }

                    leaf current-size {
                        type uint64 {
                            range "0..max";
                        }
                        units "bytes";
                        description "Current amount of allocated memory for a group.";
                    }

                    leaf max-so-far {
                        type uint64 {
                            range "0..max";
                        }
                        units "bytes";
                        description "The highest amount of allocated memory for a group.";
                    }

                    leaf in-use {
                        type uint64 {
                            range "0..max";
                        }
                        units "bytes";
                        description "Amount of memory used by group.";
                    }

                } // container ospf

                container openflow {
                    status obsolete;
                    description "Enter the openflow context";

                    leaf max-allowed {
                        status obsolete;
                        type uint64 {
                            range "1..max";
                        }
                        units "bytes";
                        description "Maximum allowed amount of memory that can be allocated for a group.";
                    }

                    leaf current-size {
                        status obsolete;
                        type uint64 {
                            range "0..max";
                        }
                        units "bytes";
                        description "Current amount of allocated memory for a group.";
                    }

                    leaf max-so-far {
                        status obsolete;
                        type uint64 {
                            range "0..max";
                        }
                        units "bytes";
                        description "The highest amount of allocated memory for a group.";
                    }

                    leaf in-use {
                        status obsolete;
                        type uint64 {
                            range "0..max";
                        }
                        units "bytes";
                        description "Amount of memory used by group.";
                    }

                } // container openflow

                container sdn-protocols {
                    description "Enter the sdn-protocols context";

                    leaf max-allowed {
                        type uint64 {
                            range "1..max";
                        }
                        units "bytes";
                        description "Maximum allowed amount of memory that can be allocated for a group.";
                    }

                    leaf current-size {
                        type uint64 {
                            range "0..max";
                        }
                        units "bytes";
                        description "Current amount of allocated memory for a group.";
                    }

                    leaf max-so-far {
                        type uint64 {
                            range "0..max";
                        }
                        units "bytes";
                        description "The highest amount of allocated memory for a group.";
                    }

                    leaf in-use {
                        type uint64 {
                            range "0..max";
                        }
                        units "bytes";
                        description "Amount of memory used by group.";
                    }

                } // container sdn-protocols

                container pim-l2mcast {
                    description "Enter the pim-l2mcast context";

                    leaf max-allowed {
                        type uint64 {
                            range "1..max";
                        }
                        units "bytes";
                        description "Maximum allowed amount of memory that can be allocated for a group.";
                    }

                    leaf current-size {
                        type uint64 {
                            range "0..max";
                        }
                        units "bytes";
                        description "Current amount of allocated memory for a group.";
                    }

                    leaf max-so-far {
                        type uint64 {
                            range "0..max";
                        }
                        units "bytes";
                        description "The highest amount of allocated memory for a group.";
                    }

                    leaf in-use {
                        type uint64 {
                            range "0..max";
                        }
                        units "bytes";
                        description "Amount of memory used by group.";
                    }

                } // container pim-l2mcast

                container pki {
                    description "Enter the pki context";

                    leaf max-allowed {
                        type uint64 {
                            range "1..max";
                        }
                        units "bytes";
                        description "Maximum allowed amount of memory that can be allocated for a group.";
                    }

                    leaf current-size {
                        type uint64 {
                            range "0..max";
                        }
                        units "bytes";
                        description "Current amount of allocated memory for a group.";
                    }

                    leaf max-so-far {
                        type uint64 {
                            range "0..max";
                        }
                        units "bytes";
                        description "The highest amount of allocated memory for a group.";
                    }

                    leaf in-use {
                        type uint64 {
                            range "0..max";
                        }
                        units "bytes";
                        description "Amount of memory used by group.";
                    }

                } // container pki

                container ptp {
                    description "Enter the ptp context";

                    leaf max-allowed {
                        type uint64 {
                            range "1..max";
                        }
                        units "bytes";
                        description "Maximum allowed amount of memory that can be allocated for a group.";
                    }

                    leaf current-size {
                        type uint64 {
                            range "0..max";
                        }
                        units "bytes";
                        description "Current amount of allocated memory for a group.";
                    }

                    leaf max-so-far {
                        type uint64 {
                            range "0..max";
                        }
                        units "bytes";
                        description "The highest amount of allocated memory for a group.";
                    }

                    leaf in-use {
                        type uint64 {
                            range "0..max";
                        }
                        units "bytes";
                        description "Amount of memory used by group.";
                    }

                } // container ptp

                container rip {
                    description "Enter the rip context";

                    leaf max-allowed {
                        type uint64 {
                            range "1..max";
                        }
                        units "bytes";
                        description "Maximum allowed amount of memory that can be allocated for a group.";
                    }

                    leaf current-size {
                        type uint64 {
                            range "0..max";
                        }
                        units "bytes";
                        description "Current amount of allocated memory for a group.";
                    }

                    leaf max-so-far {
                        type uint64 {
                            range "0..max";
                        }
                        units "bytes";
                        description "The highest amount of allocated memory for a group.";
                    }

                    leaf in-use {
                        type uint64 {
                            range "0..max";
                        }
                        units "bytes";
                        description "Amount of memory used by group.";
                    }

                } // container rip

                container rtm-policies {
                    description "Enter the rtm-policies context";

                    leaf max-allowed {
                        type uint64 {
                            range "1..max";
                        }
                        units "bytes";
                        description "Maximum allowed amount of memory that can be allocated for a group.";
                    }

                    leaf current-size {
                        type uint64 {
                            range "0..max";
                        }
                        units "bytes";
                        description "Current amount of allocated memory for a group.";
                    }

                    leaf max-so-far {
                        type uint64 {
                            range "0..max";
                        }
                        units "bytes";
                        description "The highest amount of allocated memory for a group.";
                    }

                    leaf in-use {
                        type uint64 {
                            range "0..max";
                        }
                        units "bytes";
                        description "Amount of memory used by group.";
                    }

                } // container rtm-policies

                container redundancy {
                    description "Enter the redundancy context";

                    leaf max-allowed {
                        type uint64 {
                            range "1..max";
                        }
                        units "bytes";
                        description "Maximum allowed amount of memory that can be allocated for a group.";
                    }

                    leaf current-size {
                        type uint64 {
                            range "0..max";
                        }
                        units "bytes";
                        description "Current amount of allocated memory for a group.";
                    }

                    leaf max-so-far {
                        type uint64 {
                            range "0..max";
                        }
                        units "bytes";
                        description "The highest amount of allocated memory for a group.";
                    }

                    leaf in-use {
                        type uint64 {
                            range "0..max";
                        }
                        units "bytes";
                        description "Amount of memory used by group.";
                    }

                } // container redundancy

                container sim {
                    description "Enter the sim context";

                    leaf max-allowed {
                        type uint64 {
                            range "1..max";
                        }
                        units "bytes";
                        description "Maximum allowed amount of memory that can be allocated for a group.";
                    }

                    leaf current-size {
                        type uint64 {
                            range "0..max";
                        }
                        units "bytes";
                        description "Current amount of allocated memory for a group.";
                    }

                    leaf max-so-far {
                        type uint64 {
                            range "0..max";
                        }
                        units "bytes";
                        description "The highest amount of allocated memory for a group.";
                    }

                    leaf in-use {
                        type uint64 {
                            range "0..max";
                        }
                        units "bytes";
                        description "Amount of memory used by group.";
                    }

                } // container sim

                container snmp-daemon {
                    description "Enter the snmp-daemon context";

                    leaf max-allowed {
                        type uint64 {
                            range "1..max";
                        }
                        units "bytes";
                        description "Maximum allowed amount of memory that can be allocated for a group.";
                    }

                    leaf current-size {
                        type uint64 {
                            range "0..max";
                        }
                        units "bytes";
                        description "Current amount of allocated memory for a group.";
                    }

                    leaf max-so-far {
                        type uint64 {
                            range "0..max";
                        }
                        units "bytes";
                        description "The highest amount of allocated memory for a group.";
                    }

                    leaf in-use {
                        type uint64 {
                            range "0..max";
                        }
                        units "bytes";
                        description "Amount of memory used by group.";
                    }

                } // container snmp-daemon

                container security {
                    description "Enter the security context";

                    leaf max-allowed {
                        type uint64 {
                            range "1..max";
                        }
                        units "bytes";
                        description "Maximum allowed amount of memory that can be allocated for a group.";
                    }

                    leaf current-size {
                        type uint64 {
                            range "0..max";
                        }
                        units "bytes";
                        description "Current amount of allocated memory for a group.";
                    }

                    leaf max-so-far {
                        type uint64 {
                            range "0..max";
                        }
                        units "bytes";
                        description "The highest amount of allocated memory for a group.";
                    }

                    leaf in-use {
                        type uint64 {
                            range "0..max";
                        }
                        units "bytes";
                        description "Amount of memory used by group.";
                    }

                } // container security

                container services {
                    description "Enter the services context";

                    leaf max-allowed {
                        type uint64 {
                            range "1..max";
                        }
                        units "bytes";
                        description "Maximum allowed amount of memory that can be allocated for a group.";
                    }

                    leaf current-size {
                        type uint64 {
                            range "0..max";
                        }
                        units "bytes";
                        description "Current amount of allocated memory for a group.";
                    }

                    leaf max-so-far {
                        type uint64 {
                            range "0..max";
                        }
                        units "bytes";
                        description "The highest amount of allocated memory for a group.";
                    }

                    leaf in-use {
                        type uint64 {
                            range "0..max";
                        }
                        units "bytes";
                        description "Amount of memory used by group.";
                    }

                } // container services

                container stats {
                    description "Enter the stats context";

                    leaf max-allowed {
                        type uint64 {
                            range "1..max";
                        }
                        units "bytes";
                        description "Maximum allowed amount of memory that can be allocated for a group.";
                    }

                    leaf current-size {
                        type uint64 {
                            range "0..max";
                        }
                        units "bytes";
                        description "Current amount of allocated memory for a group.";
                    }

                    leaf max-so-far {
                        type uint64 {
                            range "0..max";
                        }
                        units "bytes";
                        description "The highest amount of allocated memory for a group.";
                    }

                    leaf in-use {
                        type uint64 {
                            range "0..max";
                        }
                        units "bytes";
                        description "Amount of memory used by group.";
                    }

                } // container stats

                container subscriber-mgmt {
                    description "Enter the subscriber-mgmt context";

                    leaf max-allowed {
                        type uint64 {
                            range "1..max";
                        }
                        units "bytes";
                        description "Maximum allowed amount of memory that can be allocated for a group.";
                    }

                    leaf current-size {
                        type uint64 {
                            range "0..max";
                        }
                        units "bytes";
                        description "Current amount of allocated memory for a group.";
                    }

                    leaf max-so-far {
                        type uint64 {
                            range "0..max";
                        }
                        units "bytes";
                        description "The highest amount of allocated memory for a group.";
                    }

                    leaf in-use {
                        type uint64 {
                            range "0..max";
                        }
                        units "bytes";
                        description "Amount of memory used by group.";
                    }

                } // container subscriber-mgmt

                container system {
                    description "Enter the system context";

                    leaf max-allowed {
                        type uint64 {
                            range "1..max";
                        }
                        units "bytes";
                        description "Maximum allowed amount of memory that can be allocated for a group.";
                    }

                    leaf current-size {
                        type uint64 {
                            range "0..max";
                        }
                        units "bytes";
                        description "Current amount of allocated memory for a group.";
                    }

                    leaf max-so-far {
                        type uint64 {
                            range "0..max";
                        }
                        units "bytes";
                        description "The highest amount of allocated memory for a group.";
                    }

                    leaf in-use {
                        type uint64 {
                            range "0..max";
                        }
                        units "bytes";
                        description "Amount of memory used by group.";
                    }

                } // container system

                container traffic-eng {
                    description "Enter the traffic-eng context";

                    leaf max-allowed {
                        type uint64 {
                            range "1..max";
                        }
                        units "bytes";
                        description "Maximum allowed amount of memory that can be allocated for a group.";
                    }

                    leaf current-size {
                        type uint64 {
                            range "0..max";
                        }
                        units "bytes";
                        description "Current amount of allocated memory for a group.";
                    }

                    leaf max-so-far {
                        type uint64 {
                            range "0..max";
                        }
                        units "bytes";
                        description "The highest amount of allocated memory for a group.";
                    }

                    leaf in-use {
                        type uint64 {
                            range "0..max";
                        }
                        units "bytes";
                        description "Amount of memory used by group.";
                    }

                } // container traffic-eng

                container tree-sid {
                    description "Enter the tree-sid context";

                    leaf max-allowed {
                        type uint64 {
                            range "1..max";
                        }
                        units "bytes";
                        description "Maximum allowed amount of memory that can be allocated for a group.";
                    }

                    leaf current-size {
                        type uint64 {
                            range "0..max";
                        }
                        units "bytes";
                        description "Current amount of allocated memory for a group.";
                    }

                    leaf max-so-far {
                        type uint64 {
                            range "0..max";
                        }
                        units "bytes";
                        description "The highest amount of allocated memory for a group.";
                    }

                    leaf in-use {
                        type uint64 {
                            range "0..max";
                        }
                        units "bytes";
                        description "Amount of memory used by group.";
                    }

                } // container tree-sid

                container vrrp {
                    description "Enter the vrrp context";

                    leaf max-allowed {
                        type uint64 {
                            range "1..max";
                        }
                        units "bytes";
                        description "Maximum allowed amount of memory that can be allocated for a group.";
                    }

                    leaf current-size {
                        type uint64 {
                            range "0..max";
                        }
                        units "bytes";
                        description "Current amount of allocated memory for a group.";
                    }

                    leaf max-so-far {
                        type uint64 {
                            range "0..max";
                        }
                        units "bytes";
                        description "The highest amount of allocated memory for a group.";
                    }

                    leaf in-use {
                        type uint64 {
                            range "0..max";
                        }
                        units "bytes";
                        description "Amount of memory used by group.";
                    }

                } // container vrrp

                container web-redirect {
                    description "Enter the web-redirect context";

                    leaf max-allowed {
                        type uint64 {
                            range "1..max";
                        }
                        units "bytes";
                        description "Maximum allowed amount of memory that can be allocated for a group.";
                    }

                    leaf current-size {
                        type uint64 {
                            range "0..max";
                        }
                        units "bytes";
                        description "Current amount of allocated memory for a group.";
                    }

                    leaf max-so-far {
                        type uint64 {
                            range "0..max";
                        }
                        units "bytes";
                        description "The highest amount of allocated memory for a group.";
                    }

                    leaf in-use {
                        type uint64 {
                            range "0..max";
                        }
                        units "bytes";
                        description "Amount of memory used by group.";
                    }

                } // container web-redirect

                container iom {
                    description "Enter the iom context";

                    leaf max-allowed {
                        type uint64 {
                            range "1..max";
                        }
                        units "bytes";
                        description "Maximum allowed amount of memory that can be allocated for a group.";
                    }

                    leaf current-size {
                        type uint64 {
                            range "0..max";
                        }
                        units "bytes";
                        description "Current amount of allocated memory for a group.";
                    }

                    leaf max-so-far {
                        type uint64 {
                            range "0..max";
                        }
                        units "bytes";
                        description "The highest amount of allocated memory for a group.";
                    }

                    leaf in-use {
                        type uint64 {
                            range "0..max";
                        }
                        units "bytes";
                        description "Amount of memory used by group.";
                    }

                } // container iom

                container summary {
                    description "Enter the summary context";

                    leaf current-total-size {
                        type uint64 {
                            range "0..max";
                        }
                        units "bytes";
                        description "Amount of memory allocated for all groups.";
                    }

                    leaf total-in-use {
                        type uint64 {
                            range "0..max";
                        }
                        units "bytes";
                        description "Amount of memory used by all groups.";
                    }

                    leaf available-memory {
                        type uint64 {
                            range "0..max";
                        }
                        units "bytes";
                        description "Amount of unused memory.";
                    }

                } // container summary

            } // container memory-pools

            container version {
                description "Enter the version context";

                leaf version-number {
                    type string;
                    description "Version number.";
                }

                leaf version-string {
                    type string {
                        length "0..256";
                    }
                    description "Version string.";
                }

            } // container version

            container statistics {
                description "Enter the statistics context";

                container ip-tunnel {
                    description "Enter the ip-tunnel context";

                    container number-of-tunnels {
                        description "Enter the number-of-tunnels context";

                        container current {
                            description "Enter the current context";

                            leaf gre {
                                type yang:counter64;
                                description "Number of GRE tunnels.";
                            }

                            leaf ip {
                                type yang:counter64;
                                description "Number of IP tunnels.";
                            }

                            leaf l2tpv3 {
                                type yang:counter64;
                                description "Number of L2TPv3 tunnels.";
                            }

                            leaf start-time {
                                type yang:date-and-time;
                                description "The time when the sampling interval started.";
                            }

                        } // container current

                    } // container number-of-tunnels

                    container throughput {
                        description "Enter the throughput context";

                        container gre {
                            description "Enter the gre context";

                            container current {
                                description "Enter the current context";

                                leaf start-time {
                                    type yang:date-and-time;
                                    description "The time when the sampling interval started.";
                                }

                                leaf sampling-duration {
                                    type types-sros:time-duration;
                                    description "The duration of the corresponding sampling interval.";
                                }

                                container packets {
                                    description "Enter the packets context";

                                    leaf encapsulated {
                                        type yang:counter64;
                                        units "packets per second";
                                        description "Encapsulated GRE tunnel throughput.";
                                    }

                                    leaf decapsulated {
                                        type yang:counter64;
                                        units "packets per second";
                                        description "Decapsulated GRE tunnel throughput.";
                                    }

                                    leaf total {
                                        type yang:counter64;
                                        units "packets per second";
                                        description "Encapsulated and decapsulated GRE tunnel throughput.";
                                    }

                                } // container packets

                                container bytes {
                                    description "Enter the bytes context";

                                    leaf encapsulated {
                                        type yang:counter64;
                                        units "megabps";
                                        description "Encapsulated GRE tunnel throughput.";
                                    }

                                    leaf decapsulated {
                                        type yang:counter64;
                                        units "megabps";
                                        description "Decapsulated GRE tunnel throughput.";
                                    }

                                    leaf total {
                                        type yang:counter64;
                                        units "megabps";
                                        description "Encapsulated and decapsulated GRE tunnel throughput.";
                                    }

                                } // container bytes

                            } // container current

                            list historical {
                                key "index";
                                description "Enter the historical list instance";

                                leaf index {
                                    type uint32 {
                                        range "2..max";
                                    }
                                    description
                                        "The index of the finished sampling interval period for this statistic.
                                         It starts with '2' and is ordered by start time of intervals so that
                                         smaller index indicate more recent intervals.";
                                }

                                leaf start-time {
                                    type yang:date-and-time;
                                    description "The time when the sampling interval started.";
                                }

                                leaf sampling-duration {
                                    type types-sros:time-duration;
                                    description "The duration of the corresponding sampling interval.";
                                }

                                container packets {
                                    description "Enter the packets context";

                                    leaf encapsulated {
                                        type yang:counter64;
                                        units "packets per second";
                                        description "Encapsulated GRE tunnel throughput.";
                                    }

                                    leaf decapsulated {
                                        type yang:counter64;
                                        units "packets per second";
                                        description "Decapsulated GRE tunnel throughput.";
                                    }

                                    leaf total {
                                        type yang:counter64;
                                        units "packets per second";
                                        description "Encapsulated and decapsulated GRE tunnel throughput.";
                                    }

                                } // container packets

                                container bytes {
                                    description "Enter the bytes context";

                                    leaf encapsulated {
                                        type yang:counter64;
                                        units "megabps";
                                        description "Encapsulated GRE tunnel throughput.";
                                    }

                                    leaf decapsulated {
                                        type yang:counter64;
                                        units "megabps";
                                        description "Decapsulated GRE tunnel throughput.";
                                    }

                                    leaf total {
                                        type yang:counter64;
                                        units "megabps";
                                        description "Encapsulated and decapsulated GRE tunnel throughput.";
                                    }

                                } // container bytes

                            } // list historical

                        } // container gre

                        container ip {
                            description "Enter the ip context";

                            container current {
                                description "Enter the current context";

                                leaf start-time {
                                    type yang:date-and-time;
                                    description "The time when the sampling interval started.";
                                }

                                leaf sampling-duration {
                                    type types-sros:time-duration;
                                    description "The duration of the corresponding sampling interval.";
                                }

                                container packets {
                                    description "Enter the packets context";

                                    leaf encapsulated {
                                        type yang:counter64;
                                        units "packets per second";
                                        description "Encapsulated IP tunnel throughput.";
                                    }

                                    leaf decapsulated {
                                        type yang:counter64;
                                        units "packets per second";
                                        description "Decapsulated IP tunnel throughput.";
                                    }

                                    leaf total {
                                        type yang:counter64;
                                        units "packets per second";
                                        description "Encapsulated and decapsulated IP tunnel throughput.";
                                    }

                                } // container packets

                                container bytes {
                                    description "Enter the bytes context";

                                    leaf encapsulated {
                                        type yang:counter64;
                                        units "megabps";
                                        description "Encapsulated IP tunnel throughput.";
                                    }

                                    leaf decapsulated {
                                        type yang:counter64;
                                        units "megabps";
                                        description "Decapsulated IP tunnel throughput.";
                                    }

                                    leaf total {
                                        type yang:counter64;
                                        units "megabps";
                                        description "Encapsulated and decapsulated IP tunnel throughput.";
                                    }

                                } // container bytes

                            } // container current

                            list historical {
                                key "index";
                                description "Enter the historical list instance";

                                leaf index {
                                    type uint32 {
                                        range "2..max";
                                    }
                                    description
                                        "The index of the finished sampling interval period for this statistic.
                                         It starts with '2' and is ordered by start time of intervals so that
                                         smaller index indicate more recent intervals.";
                                }

                                leaf start-time {
                                    type yang:date-and-time;
                                    description "The time when the sampling interval started.";
                                }

                                leaf sampling-duration {
                                    type types-sros:time-duration;
                                    description "The duration of the corresponding sampling interval.";
                                }

                                container packets {
                                    description "Enter the packets context";

                                    leaf encapsulated {
                                        type yang:counter64;
                                        units "packets per second";
                                        description "Encapsulated IP tunnel throughput.";
                                    }

                                    leaf decapsulated {
                                        type yang:counter64;
                                        units "packets per second";
                                        description "Decapsulated IP tunnel throughput.";
                                    }

                                    leaf total {
                                        type yang:counter64;
                                        units "packets per second";
                                        description "Encapsulated and decapsulated IP tunnel throughput.";
                                    }

                                } // container packets

                                container bytes {
                                    description "Enter the bytes context";

                                    leaf encapsulated {
                                        type yang:counter64;
                                        units "megabps";
                                        description "Encapsulated IP tunnel throughput.";
                                    }

                                    leaf decapsulated {
                                        type yang:counter64;
                                        units "megabps";
                                        description "Decapsulated IP tunnel throughput.";
                                    }

                                    leaf total {
                                        type yang:counter64;
                                        units "megabps";
                                        description "Encapsulated and decapsulated IP tunnel throughput.";
                                    }

                                } // container bytes

                            } // list historical

                        } // container ip

                        container l2tpv3 {
                            description "Enter the l2tpv3 context";

                            container current {
                                description "Enter the current context";

                                leaf start-time {
                                    type yang:date-and-time;
                                    description "The time when the sampling interval started.";
                                }

                                leaf sampling-duration {
                                    type types-sros:time-duration;
                                    description "The duration of the corresponding sampling interval.";
                                }

                                container packets {
                                    description "Enter the packets context";

                                    leaf encapsulated {
                                        type yang:counter64;
                                        units "packets per second";
                                        description "Encapsulated L2TPv3 tunnel throughput.";
                                    }

                                    leaf decapsulated {
                                        type yang:counter64;
                                        units "packets per second";
                                        description "Decapsulated L2TPv3 tunnel throughput.";
                                    }

                                    leaf total {
                                        type yang:counter64;
                                        units "packets per second";
                                        description "Encapsulated and decapsulated L2TPv3 tunnel throughput.";
                                    }

                                } // container packets

                                container bytes {
                                    description "Enter the bytes context";

                                    leaf encapsulated {
                                        type yang:counter64;
                                        units "megabps";
                                        description "Encapsulated L2TPv3 tunnel throughput.";
                                    }

                                    leaf decapsulated {
                                        type yang:counter64;
                                        units "megabps";
                                        description "Decapsulated L2TPv3 tunnel throughput.";
                                    }

                                    leaf total {
                                        type yang:counter64;
                                        units "megabps";
                                        description "Encapsulated and decapsulated L2TPv3 tunnel throughput.";
                                    }

                                } // container bytes

                            } // container current

                            list historical {
                                key "index";
                                description "Enter the historical list instance";

                                leaf index {
                                    type uint32 {
                                        range "2..max";
                                    }
                                    description
                                        "The index of the finished sampling interval period for this statistic.
                                         It starts with '2' and is ordered by start time of intervals so that
                                         smaller index indicate more recent intervals.";
                                }

                                leaf start-time {
                                    type yang:date-and-time;
                                    description "The time when the sampling interval started.";
                                }

                                leaf sampling-duration {
                                    type types-sros:time-duration;
                                    description "The duration of the corresponding sampling interval.";
                                }

                                container packets {
                                    description "Enter the packets context";

                                    leaf encapsulated {
                                        type yang:counter64;
                                        units "packets per second";
                                        description "Encapsulated L2TPv3 tunnel throughput.";
                                    }

                                    leaf decapsulated {
                                        type yang:counter64;
                                        units "packets per second";
                                        description "Decapsulated L2TPv3 tunnel throughput.";
                                    }

                                    leaf total {
                                        type yang:counter64;
                                        units "packets per second";
                                        description "Encapsulated and decapsulated L2TPv3 tunnel throughput.";
                                    }

                                } // container packets

                                container bytes {
                                    description "Enter the bytes context";

                                    leaf encapsulated {
                                        type yang:counter64;
                                        units "megabps";
                                        description "Encapsulated L2TPv3 tunnel throughput.";
                                    }

                                    leaf decapsulated {
                                        type yang:counter64;
                                        units "megabps";
                                        description "Decapsulated L2TPv3 tunnel throughput.";
                                    }

                                    leaf total {
                                        type yang:counter64;
                                        units "megabps";
                                        description "Encapsulated and decapsulated L2TPv3 tunnel throughput.";
                                    }

                                } // container bytes

                            } // list historical

                        } // container l2tpv3

                    } // container throughput

                } // container ip-tunnel

                container ipsec {
                    description "Enter the ipsec context";

                    container number-of-tunnels {
                        description "Enter the number-of-tunnels context";

                        container current {
                            description "Enter the current context";

                            leaf static-lan-to-lan {
                                type yang:counter64;
                                description "Number of IPsec static LAN-to-LAN (SL2L) tunnels.";
                            }

                            leaf dynamic-lan-to-lan {
                                type yang:counter64;
                                description "Number of IPsec dynamic LAN-to-LAN (DL2L) tunnels.";
                            }

                            leaf remote-access {
                                type yang:counter64;
                                description "Number of IPsec remote access (RA) tunnels.";
                            }

                            leaf total {
                                type yang:counter64;
                                description "Total number of IPsec tunnels.";
                            }

                            leaf start-time {
                                type yang:date-and-time;
                                description "The time when the sampling interval started.";
                            }

                        } // container current

                        list historical {
                            key "index";
                            description "Enter the historical list instance";

                            leaf index {
                                type uint32 {
                                    range "2..max";
                                }
                                description
                                    "The index of the finished sampling interval period for this statistic.
                                     It starts with '2' and is ordered by start time of intervals so that
                                     smaller index indicate more recent intervals.";
                            }

                            leaf static-lan-to-lan {
                                type yang:counter64;
                                description "Number of IPsec static LAN-to-LAN (SL2L) tunnels.";
                            }

                            leaf dynamic-lan-to-lan {
                                type yang:counter64;
                                description "Number of IPsec dynamic LAN-to-LAN (DL2L) tunnels.";
                            }

                            leaf remote-access {
                                type yang:counter64;
                                description "Number of IPsec remote access (RA) tunnels.";
                            }

                            leaf total {
                                type yang:counter64;
                                description "Total number of IPsec tunnels.";
                            }

                            leaf start-time {
                                type yang:date-and-time;
                                description "The time when the sampling interval started.";
                            }

                        } // list historical

                    } // container number-of-tunnels

                    container throughput {
                        description "Enter the throughput context";

                        container current {
                            description "Enter the current context";

                            leaf start-time {
                                type yang:date-and-time;
                                description "The time when the sampling interval started.";
                            }

                            leaf sampling-duration {
                                type types-sros:time-duration;
                                description "The duration of the corresponding sampling interval.";
                            }

                            container packets {
                                description "Enter the packets context";

                                leaf encrypted {
                                    type yang:counter64;
                                    units "packets per second";
                                    description "Encrypted IPsec traffic throughput.";
                                }

                                leaf decrypted {
                                    type yang:counter64;
                                    units "packets per second";
                                    description "Decrypted IPsec traffic throughput.";
                                }

                                leaf total {
                                    type yang:counter64;
                                    units "packets per second";
                                    description "Encrypted and decrypted IPsec traffic throughput.";
                                }

                            } // container packets

                            container bytes {
                                description "Enter the bytes context";

                                leaf encrypted {
                                    type yang:counter64;
                                    units "megabps";
                                    description "Encrypted IPsec traffic throughput.";
                                }

                                leaf decrypted {
                                    type yang:counter64;
                                    units "megabps";
                                    description "Decrypted IPsec traffic throughput.";
                                }

                                leaf total {
                                    type yang:counter64;
                                    units "megabps";
                                    description "Encrypted and decrypted IPsec traffic throughput.";
                                }

                            } // container bytes

                        } // container current

                        list historical {
                            key "index";
                            description "Enter the historical list instance";

                            leaf index {
                                type uint32 {
                                    range "2..max";
                                }
                                description
                                    "The index of the finished sampling interval period for this statistic.
                                     It starts with '2' and is ordered by start time of intervals so that
                                     smaller index indicate more recent intervals.";
                            }

                            leaf start-time {
                                type yang:date-and-time;
                                description "The time when the sampling interval started.";
                            }

                            leaf sampling-duration {
                                type types-sros:time-duration;
                                description "The duration of the corresponding sampling interval.";
                            }

                            container packets {
                                description "Enter the packets context";

                                leaf encrypted {
                                    type yang:counter64;
                                    units "packets per second";
                                    description "Encrypted IPsec traffic throughput.";
                                }

                                leaf decrypted {
                                    type yang:counter64;
                                    units "packets per second";
                                    description "Decrypted IPsec traffic throughput.";
                                }

                                leaf total {
                                    type yang:counter64;
                                    units "packets per second";
                                    description "Encrypted and decrypted IPsec traffic throughput.";
                                }

                            } // container packets

                            container bytes {
                                description "Enter the bytes context";

                                leaf encrypted {
                                    type yang:counter64;
                                    units "megabps";
                                    description "Encrypted IPsec traffic throughput.";
                                }

                                leaf decrypted {
                                    type yang:counter64;
                                    units "megabps";
                                    description "Decrypted IPsec traffic throughput.";
                                }

                                leaf total {
                                    type yang:counter64;
                                    units "megabps";
                                    description "Encrypted and decrypted IPsec traffic throughput.";
                                }

                            } // container bytes

                        } // list historical

                    } // container throughput

                    container tunnel-setup-rate {
                        description "Enter the tunnel-setup-rate context";

                        container current {
                            description "Enter the current context";

                            leaf static-lan-to-lan {
                                type decimal64 {
                                    fraction-digits 2;
                                }
                                units "tunnels per second";
                                description "Static LAN-to-LAN (SL2L) tunnel setup rate.";
                            }

                            leaf total {
                                type decimal64 {
                                    fraction-digits 2;
                                }
                                units "tunnels per second";
                                description "Total IPsec tunnel setup rate.";
                            }

                            leaf dynamic-lan-to-lan {
                                type decimal64 {
                                    fraction-digits 2;
                                }
                                units "tunnels per second";
                                description "Dynamic LAN-to-LAN (DL2L) tunnel setup rate.";
                            }

                            leaf remote-access {
                                type decimal64 {
                                    fraction-digits 2;
                                }
                                units "tunnels per second";
                                description "Remote access (RA) tunnel setup rate.";
                            }

                            leaf start-time {
                                type yang:date-and-time;
                                description "The time when the sampling interval started.";
                            }

                            leaf sampling-duration {
                                type types-sros:time-duration;
                                description "The duration of the corresponding sampling interval.";
                            }

                        } // container current

                        list historical {
                            key "index";
                            description "Enter the historical list instance";

                            leaf index {
                                type uint32 {
                                    range "2..max";
                                }
                                description
                                    "The index of the finished sampling interval period for this statistic.
                                     It starts with '2' and is ordered by start time of intervals so that
                                     smaller index indicate more recent intervals.";
                            }

                            leaf static-lan-to-lan {
                                type decimal64 {
                                    fraction-digits 2;
                                }
                                units "tunnels per second";
                                description "Static LAN-to-LAN (SL2L) tunnel setup rate.";
                            }

                            leaf total {
                                type decimal64 {
                                    fraction-digits 2;
                                }
                                units "tunnels per second";
                                description "Total IPsec tunnel setup rate.";
                            }

                            leaf dynamic-lan-to-lan {
                                type decimal64 {
                                    fraction-digits 2;
                                }
                                units "tunnels per second";
                                description "Dynamic LAN-to-LAN (DL2L) tunnel setup rate.";
                            }

                            leaf remote-access {
                                type decimal64 {
                                    fraction-digits 2;
                                }
                                units "tunnels per second";
                                description "Remote access (RA) tunnel setup rate.";
                            }

                            leaf start-time {
                                type yang:date-and-time;
                                description "The time when the sampling interval started.";
                            }

                            leaf sampling-duration {
                                type types-sros:time-duration;
                                description "The duration of the corresponding sampling interval.";
                            }

                        } // list historical

                    } // container tunnel-setup-rate

                    container ike-exchange-failure-rate {
                        description "Enter the ike-exchange-failure-rate context";

                        container current {
                            description "Enter the current context";

                            leaf start-time {
                                type yang:date-and-time;
                                description "The time when the sampling interval started.";
                            }

                            leaf sampling-duration {
                                type types-sros:time-duration;
                                description "The duration of the corresponding sampling interval.";
                            }

                            container auth-failure {
                                description "Enter the auth-failure context";

                                leaf count {
                                    type decimal64 {
                                        fraction-digits 2;
                                    }
                                    units "failures per second";
                                    description "IKE exchange failure rate - authentication.";
                                }

                                leaf first-failure {
                                    type yang:date-and-time;
                                    description
                                        "The time when the first IKE exchange failure happened
                                         in the corresponding sampling interval.";
                                }

                                leaf first-failure-description {
                                    type types-sros:long-description;
                                    description "The description of the place where the first IKE exchange failure happened.";
                                }

                                leaf last-failure {
                                    type yang:date-and-time;
                                    description
                                        "The time when the last IKE exchange failure happened
                                         in the corresponding sampling interval.";
                                }

                                leaf last-failure-description {
                                    type types-sros:long-description;
                                    description "The description of the place where the last IKE exchange failure happened.";
                                }

                            } // container auth-failure

                            container non-proposal-chosen {
                                description "Enter the non-proposal-chosen context";

                                leaf count {
                                    type decimal64 {
                                        fraction-digits 2;
                                    }
                                    units "failures per second";
                                    description "IKE exchange failure rate - non-proposal chosen.";
                                }

                                leaf first-failure {
                                    type yang:date-and-time;
                                    description
                                        "The time when the first IKE exchange failure happened
                                         in the corresponding sampling interval.";
                                }

                                leaf first-failure-description {
                                    type types-sros:long-description;
                                    description "The description of the place where the first IKE exchange failure happened.";
                                }

                                leaf last-failure {
                                    type yang:date-and-time;
                                    description
                                        "The time when the last IKE exchange failure happened
                                         in the corresponding sampling interval.";
                                }

                                leaf last-failure-description {
                                    type types-sros:long-description;
                                    description "The description of the place where the last IKE exchange failure happened.";
                                }

                            } // container non-proposal-chosen

                            container internal-address-assignment {
                                description "Enter the internal-address-assignment context";

                                leaf count {
                                    type decimal64 {
                                        fraction-digits 2;
                                    }
                                    units "failures per second";
                                    description "IKE exchange failure rate - address assignment.";
                                }

                                leaf first-failure {
                                    type yang:date-and-time;
                                    description
                                        "The time when the first IKE exchange failure happened
                                         in the corresponding sampling interval.";
                                }

                                leaf first-failure-description {
                                    type types-sros:long-description;
                                    description "The description of the place where the first IKE exchange failure happened.";
                                }

                                leaf last-failure {
                                    type yang:date-and-time;
                                    description
                                        "The time when the last IKE exchange failure happened
                                         in the corresponding sampling interval.";
                                }

                                leaf last-failure-description {
                                    type types-sros:long-description;
                                    description "The description of the place where the last IKE exchange failure happened.";
                                }

                            } // container internal-address-assignment

                            container invalid-ts {
                                description "Enter the invalid-ts context";

                                leaf count {
                                    type decimal64 {
                                        fraction-digits 2;
                                    }
                                    units "failures per second";
                                    description "IKE exchange failure rate - invalid traffic selector.";
                                }

                                leaf first-failure {
                                    type yang:date-and-time;
                                    description
                                        "The time when the first IKE exchange failure happened
                                         in the corresponding sampling interval.";
                                }

                                leaf first-failure-description {
                                    type types-sros:long-description;
                                    description "The description of the place where the first IKE exchange failure happened.";
                                }

                                leaf last-failure {
                                    type yang:date-and-time;
                                    description
                                        "The time when the last IKE exchange failure happened
                                         in the corresponding sampling interval.";
                                }

                                leaf last-failure-description {
                                    type types-sros:long-description;
                                    description "The description of the place where the last IKE exchange failure happened.";
                                }

                            } // container invalid-ts

                            container invalid-ke {
                                description "Enter the invalid-ke context";

                                leaf count {
                                    type decimal64 {
                                        fraction-digits 2;
                                    }
                                    units "failures per second";
                                    description "IKE exchange failure rate - invalid key exchange.";
                                }

                                leaf first-failure {
                                    type yang:date-and-time;
                                    description
                                        "The time when the first IKE exchange failure happened
                                         in the corresponding sampling interval.";
                                }

                                leaf first-failure-description {
                                    type types-sros:long-description;
                                    description "The description of the place where the first IKE exchange failure happened.";
                                }

                                leaf last-failure {
                                    type yang:date-and-time;
                                    description
                                        "The time when the last IKE exchange failure happened
                                         in the corresponding sampling interval.";
                                }

                                leaf last-failure-description {
                                    type types-sros:long-description;
                                    description "The description of the place where the last IKE exchange failure happened.";
                                }

                            } // container invalid-ke

                            container dpd-timeout {
                                description "Enter the dpd-timeout context";

                                leaf count {
                                    type decimal64 {
                                        fraction-digits 2;
                                    }
                                    units "failures per second";
                                    description "IKE exchange failure rate - DPD timeout.";
                                }

                                leaf first-failure {
                                    type yang:date-and-time;
                                    description
                                        "The time when the first IKE exchange failure happened
                                         in the corresponding sampling interval.";
                                }

                                leaf first-failure-description {
                                    type types-sros:long-description;
                                    description "The description of the place where the first IKE exchange failure happened.";
                                }

                                leaf last-failure {
                                    type yang:date-and-time;
                                    description
                                        "The time when the last IKE exchange failure happened
                                         in the corresponding sampling interval.";
                                }

                                leaf last-failure-description {
                                    type types-sros:long-description;
                                    description "The description of the place where the last IKE exchange failure happened.";
                                }

                            } // container dpd-timeout

                            container other {
                                description "Enter the other context";

                                leaf count {
                                    type decimal64 {
                                        fraction-digits 2;
                                    }
                                    units "failures per second";
                                    description "IKE exchange failure rate - other failure reasons.";
                                }

                                leaf first-failure {
                                    type yang:date-and-time;
                                    description
                                        "The time when the first IKE exchange failure happened
                                         in the corresponding sampling interval.";
                                }

                                leaf first-failure-description {
                                    type types-sros:long-description;
                                    description "The description of the place where the first IKE exchange failure happened.";
                                }

                                leaf last-failure {
                                    type yang:date-and-time;
                                    description
                                        "The time when the last IKE exchange failure happened
                                         in the corresponding sampling interval.";
                                }

                                leaf last-failure-description {
                                    type types-sros:long-description;
                                    description "The description of the place where the last IKE exchange failure happened.";
                                }

                            } // container other

                        } // container current

                        list historical {
                            key "index";
                            description "Enter the historical list instance";

                            leaf index {
                                type uint32 {
                                    range "2..max";
                                }
                                description
                                    "The index of the finished sampling interval period for this statistic.
                                     It starts with '2' and is ordered by start time of intervals so that
                                     smaller index indicate more recent intervals.";
                            }

                            leaf start-time {
                                type yang:date-and-time;
                                description "The time when the sampling interval started.";
                            }

                            leaf sampling-duration {
                                type types-sros:time-duration;
                                description "The duration of the corresponding sampling interval.";
                            }

                            container auth-failure {
                                description "Enter the auth-failure context";

                                leaf count {
                                    type decimal64 {
                                        fraction-digits 2;
                                    }
                                    units "failures per second";
                                    description "IKE exchange failure rate - authentication.";
                                }

                                leaf first-failure {
                                    type yang:date-and-time;
                                    description
                                        "The time when the first IKE exchange failure happened
                                         in the corresponding sampling interval.";
                                }

                                leaf first-failure-description {
                                    type types-sros:long-description;
                                    description "The description of the place where the first IKE exchange failure happened.";
                                }

                                leaf last-failure {
                                    type yang:date-and-time;
                                    description
                                        "The time when the last IKE exchange failure happened
                                         in the corresponding sampling interval.";
                                }

                                leaf last-failure-description {
                                    type types-sros:long-description;
                                    description "The description of the place where the last IKE exchange failure happened.";
                                }

                            } // container auth-failure

                            container non-proposal-chosen {
                                description "Enter the non-proposal-chosen context";

                                leaf count {
                                    type decimal64 {
                                        fraction-digits 2;
                                    }
                                    units "failures per second";
                                    description "IKE exchange failure rate - non-proposal chosen.";
                                }

                                leaf first-failure {
                                    type yang:date-and-time;
                                    description
                                        "The time when the first IKE exchange failure happened
                                         in the corresponding sampling interval.";
                                }

                                leaf first-failure-description {
                                    type types-sros:long-description;
                                    description "The description of the place where the first IKE exchange failure happened.";
                                }

                                leaf last-failure {
                                    type yang:date-and-time;
                                    description
                                        "The time when the last IKE exchange failure happened
                                         in the corresponding sampling interval.";
                                }

                                leaf last-failure-description {
                                    type types-sros:long-description;
                                    description "The description of the place where the last IKE exchange failure happened.";
                                }

                            } // container non-proposal-chosen

                            container internal-address-assignment {
                                description "Enter the internal-address-assignment context";

                                leaf count {
                                    type decimal64 {
                                        fraction-digits 2;
                                    }
                                    units "failures per second";
                                    description "IKE exchange failure rate - address assignment.";
                                }

                                leaf first-failure {
                                    type yang:date-and-time;
                                    description
                                        "The time when the first IKE exchange failure happened
                                         in the corresponding sampling interval.";
                                }

                                leaf first-failure-description {
                                    type types-sros:long-description;
                                    description "The description of the place where the first IKE exchange failure happened.";
                                }

                                leaf last-failure {
                                    type yang:date-and-time;
                                    description
                                        "The time when the last IKE exchange failure happened
                                         in the corresponding sampling interval.";
                                }

                                leaf last-failure-description {
                                    type types-sros:long-description;
                                    description "The description of the place where the last IKE exchange failure happened.";
                                }

                            } // container internal-address-assignment

                            container invalid-ts {
                                description "Enter the invalid-ts context";

                                leaf count {
                                    type decimal64 {
                                        fraction-digits 2;
                                    }
                                    units "failures per second";
                                    description "IKE exchange failure rate - invalid traffic selector.";
                                }

                                leaf first-failure {
                                    type yang:date-and-time;
                                    description
                                        "The time when the first IKE exchange failure happened
                                         in the corresponding sampling interval.";
                                }

                                leaf first-failure-description {
                                    type types-sros:long-description;
                                    description "The description of the place where the first IKE exchange failure happened.";
                                }

                                leaf last-failure {
                                    type yang:date-and-time;
                                    description
                                        "The time when the last IKE exchange failure happened
                                         in the corresponding sampling interval.";
                                }

                                leaf last-failure-description {
                                    type types-sros:long-description;
                                    description "The description of the place where the last IKE exchange failure happened.";
                                }

                            } // container invalid-ts

                            container invalid-ke {
                                description "Enter the invalid-ke context";

                                leaf count {
                                    type decimal64 {
                                        fraction-digits 2;
                                    }
                                    units "failures per second";
                                    description "IKE exchange failure rate - invalid key exchange.";
                                }

                                leaf first-failure {
                                    type yang:date-and-time;
                                    description
                                        "The time when the first IKE exchange failure happened
                                         in the corresponding sampling interval.";
                                }

                                leaf first-failure-description {
                                    type types-sros:long-description;
                                    description "The description of the place where the first IKE exchange failure happened.";
                                }

                                leaf last-failure {
                                    type yang:date-and-time;
                                    description
                                        "The time when the last IKE exchange failure happened
                                         in the corresponding sampling interval.";
                                }

                                leaf last-failure-description {
                                    type types-sros:long-description;
                                    description "The description of the place where the last IKE exchange failure happened.";
                                }

                            } // container invalid-ke

                            container dpd-timeout {
                                description "Enter the dpd-timeout context";

                                leaf count {
                                    type decimal64 {
                                        fraction-digits 2;
                                    }
                                    units "failures per second";
                                    description "IKE exchange failure rate - DPD timeout.";
                                }

                                leaf first-failure {
                                    type yang:date-and-time;
                                    description
                                        "The time when the first IKE exchange failure happened
                                         in the corresponding sampling interval.";
                                }

                                leaf first-failure-description {
                                    type types-sros:long-description;
                                    description "The description of the place where the first IKE exchange failure happened.";
                                }

                                leaf last-failure {
                                    type yang:date-and-time;
                                    description
                                        "The time when the last IKE exchange failure happened
                                         in the corresponding sampling interval.";
                                }

                                leaf last-failure-description {
                                    type types-sros:long-description;
                                    description "The description of the place where the last IKE exchange failure happened.";
                                }

                            } // container dpd-timeout

                            container other {
                                description "Enter the other context";

                                leaf count {
                                    type decimal64 {
                                        fraction-digits 2;
                                    }
                                    units "failures per second";
                                    description "IKE exchange failure rate - other failure reasons.";
                                }

                                leaf first-failure {
                                    type yang:date-and-time;
                                    description
                                        "The time when the first IKE exchange failure happened
                                         in the corresponding sampling interval.";
                                }

                                leaf first-failure-description {
                                    type types-sros:long-description;
                                    description "The description of the place where the first IKE exchange failure happened.";
                                }

                                leaf last-failure {
                                    type yang:date-and-time;
                                    description
                                        "The time when the last IKE exchange failure happened
                                         in the corresponding sampling interval.";
                                }

                                leaf last-failure-description {
                                    type types-sros:long-description;
                                    description "The description of the place where the last IKE exchange failure happened.";
                                }

                            } // container other

                        } // list historical

                    } // container ike-exchange-failure-rate

                } // container ipsec

            } // container statistics

            container mpls-resource-usage {
                description "Enter the mpls-resource-usage context";

                container nhlfe {
                    description "Enter the nhlfe context";

                    leaf total {
                        type uint32;
                        description "Total number of mpls resources in the system.";
                    }

                    leaf allocated {
                        type uint32;
                        description "Total number of mpls resources allocated in the system.";
                    }

                    leaf free {
                        type uint32;
                        description "Total number of free mpls resources in the system.";
                    }

                    list by-owner {
                        key "owner";
                        description "Enter the by-owner list instance";

                        leaf owner {
                            type types-system:mpls-resource-owner;
                            description "Application that uses the mpls resources.";
                        }

                        leaf allocated {
                            type uint32;
                            description "Total number of mpls resources allocated in the system by the owner.";
                        }

                    } // list by-owner

                } // container nhlfe

                container ltn {
                    description "Enter the ltn context";

                    leaf total {
                        type uint32;
                        description "Total number of mpls resources in the system.";
                    }

                    leaf allocated {
                        type uint32;
                        description "Total number of mpls resources allocated in the system.";
                    }

                    leaf free {
                        type uint32;
                        description "Total number of free mpls resources in the system.";
                    }

                    list by-owner {
                        key "owner";
                        description "Enter the by-owner list instance";

                        leaf owner {
                            type types-system:mpls-resource-owner;
                            description "Application that uses the mpls resources.";
                        }

                        leaf allocated {
                            type uint32;
                            description "Total number of mpls resources allocated in the system by the owner.";
                        }

                    } // list by-owner

                } // container ltn

                container label {
                    description "Enter the label context";

                    leaf total {
                        type uint32;
                        description "Total number of mpls resources in the system.";
                    }

                    leaf allocated {
                        type uint32;
                        description "Total number of mpls resources allocated in the system.";
                    }

                    leaf free {
                        type uint32;
                        description "Total number of free mpls resources in the system.";
                    }

                    list by-owner {
                        key "owner";
                        description "Enter the by-owner list instance";

                        leaf owner {
                            type types-system:mpls-resource-owner;
                            description "Application that uses the mpls resources.";
                        }

                        leaf allocated {
                            type uint32;
                            description "Total number of mpls resources allocated in the system by the owner.";
                        }

                    } // list by-owner

                } // container label

            } // container mpls-resource-usage

            container resource-usage {
                description "Enter the resource-usage context";

                container sap-ingress-qos-policies {
                    description "Enter the sap-ingress-qos-policies context";

                    leaf total {
                        type yang:counter32;
                        description "The total number of resources supported on this system.";
                    }

                    leaf allocated {
                        type yang:counter32;
                        description "The total number of resources that are currently allocated on this system.";
                    }

                    leaf free {
                        type yang:counter32;
                        description "The total number of resources that are remaining free on this system.";
                    }

                } // container sap-ingress-qos-policies

                container sap-egress-qos-policies {
                    description "Enter the sap-egress-qos-policies context";

                    leaf total {
                        type yang:counter32;
                        description "The total number of resources supported on this system.";
                    }

                    leaf allocated {
                        type yang:counter32;
                        description "The total number of resources that are currently allocated on this system.";
                    }

                    leaf free {
                        type yang:counter32;
                        description "The total number of resources that are remaining free on this system.";
                    }

                } // container sap-egress-qos-policies

                container ingress-queue-group-templates {
                    description "Enter the ingress-queue-group-templates context";

                    leaf total {
                        type yang:counter32;
                        description "The total number of resources supported on this system.";
                    }

                    leaf allocated {
                        type yang:counter32;
                        description "The total number of resources that are currently allocated on this system.";
                    }

                    leaf free {
                        type yang:counter32;
                        description "The total number of resources that are remaining free on this system.";
                    }

                } // container ingress-queue-group-templates

                container egress-queue-group-templates {
                    description "Enter the egress-queue-group-templates context";

                    leaf total {
                        type yang:counter32;
                        description "The total number of resources supported on this system.";
                    }

                    leaf allocated {
                        type yang:counter32;
                        description "The total number of resources that are currently allocated on this system.";
                    }

                    leaf free {
                        type yang:counter32;
                        description "The total number of resources that are remaining free on this system.";
                    }

                } // container egress-queue-group-templates

                container egress-port-queue-group-instances {
                    description "Enter the egress-port-queue-group-instances context";

                    leaf total {
                        type yang:counter32;
                        description "The total number of resources supported on this system.";
                    }

                    leaf allocated {
                        type yang:counter32;
                        description "The total number of resources that are currently allocated on this system.";
                    }

                    leaf free {
                        type yang:counter32;
                        description "The total number of resources that are remaining free on this system.";
                    }

                } // container egress-port-queue-group-instances

                container ingress-fp-queue-group-instances {
                    description "Enter the ingress-fp-queue-group-instances context";

                    leaf total {
                        type yang:counter32;
                        description "The total number of resources supported on this system.";
                    }

                    leaf allocated {
                        type yang:counter32;
                        description "The total number of resources that are currently allocated on this system.";
                    }

                    leaf free {
                        type yang:counter32;
                        description "The total number of resources that are remaining free on this system.";
                    }

                } // container ingress-fp-queue-group-instances

                container egress-port-vport {
                    description "Enter the egress-port-vport context";

                    leaf total {
                        type yang:counter32;
                        description "The total number of resources supported on this system.";
                    }

                    leaf allocated {
                        type yang:counter32;
                        description "The total number of resources that are currently allocated on this system.";
                    }

                    leaf free {
                        type yang:counter32;
                        description "The total number of resources that are remaining free on this system.";
                    }

                } // container egress-port-vport

                container fast-depth-monitored-queues {
                    description "Enter the fast-depth-monitored-queues context";

                    leaf total {
                        type yang:counter32;
                        description "The total number of resources supported on this system.";
                    }

                    leaf allocated {
                        type yang:counter32;
                        description "The total number of resources that are currently allocated on this system.";
                    }

                    leaf free {
                        type yang:counter32;
                        description "The total number of resources that are remaining free on this system.";
                    }

                } // container fast-depth-monitored-queues

                container input-output-capacity {
                    description "Enter the input-output-capacity context";

                    leaf total {
                        type yang:counter32;
                        description "The total number of resources supported on this system.";
                    }

                    leaf allocated {
                        type yang:counter32;
                        description "The total number of resources that are currently allocated on this system.";
                    }

                    leaf free {
                        type yang:counter32;
                        description "The total number of resources that are remaining free on this system.";
                    }

                } // container input-output-capacity

                container mtu-profile {
                    description "Enter the mtu-profile context";

                    leaf total {
                        type yang:counter32;
                        description "The total number of resources supported on this system.";
                    }

                    leaf allocated {
                        type yang:counter32;
                        description "The total number of resources that are currently allocated on this system.";
                    }

                    leaf free {
                        type yang:counter32;
                        description "The total number of resources that are remaining free on this system.";
                    }

                } // container mtu-profile

                container dynamic-services-next-hop-entries {
                    description "Enter the dynamic-services-next-hop-entries context";

                    leaf total {
                        type yang:counter32;
                        description "The total number of resources supported on this system.";
                    }

                    leaf allocated {
                        type yang:counter32;
                        description "The total number of resources that are currently allocated on this system.";
                    }

                    leaf free {
                        type yang:counter32;
                        description "The total number of resources that are remaining free on this system.";
                    }

                } // container dynamic-services-next-hop-entries

                container ipsec-next-hop-entries {
                    description "Enter the ipsec-next-hop-entries context";

                    leaf total {
                        type yang:counter32;
                        description "The total number of resources supported on this system.";
                    }

                    leaf allocated {
                        type yang:counter32;
                        description "The total number of resources that are currently allocated on this system.";
                    }

                    leaf free {
                        type yang:counter32;
                        description "The total number of resources that are remaining free on this system.";
                    }

                } // container ipsec-next-hop-entries

                container subscriber-next-hop-entries {
                    description "Enter the subscriber-next-hop-entries context";

                    leaf total {
                        type yang:counter32;
                        description "The total number of resources supported on this system.";
                    }

                    leaf allocated {
                        type yang:counter32;
                        description "The total number of resources that are currently allocated on this system.";
                    }

                    leaf free {
                        type yang:counter32;
                        description "The total number of resources that are remaining free on this system.";
                    }

                } // container subscriber-next-hop-entries


                container sap {
                    description "Enter the sap context";

                    leaf total {
                        type uint32;
                        description "Total number of SAPs available in the system.";
                    }

                    leaf allocated {
                        type uint32;
                        description "Total number of SAPs allocated in the system.";
                    }

                    leaf free {
                        type uint32;
                        description "total number of SAPs free in the system.";
                    }

                    container cpipe {
                        description "Enter the cpipe context";

                        leaf allocated {
                            type uint32;
                            description "Total number of SAPs per service allocated in the system.";
                        }

                    } // container cpipe

                    container epipe {
                        description "Enter the epipe context";

                        leaf allocated {
                            type uint32;
                            description "Total number of SAPs per service allocated in the system.";
                        }

                    } // container epipe

                    container ipipe {
                        description "Enter the ipipe context";

                        leaf allocated {
                            type uint32;
                            description "Total number of SAPs per service allocated in the system.";
                        }

                    } // container ipipe

                    container ies {
                        description "Enter the ies context";

                        leaf allocated {
                            type uint32;
                            description "Total number of SAPs per service allocated in the system.";
                        }

                    } // container ies

                    container mirror {
                        description "Enter the mirror context";

                        leaf allocated {
                            type uint32;
                            description "Total number of SAPs per service allocated in the system.";
                        }

                    } // container mirror

                    container vpls {
                        description "Enter the vpls context";

                        leaf allocated {
                            type uint32;
                            description "Total number of SAPs per service allocated in the system.";
                        }

                    } // container vpls

                    container vprn {
                        description "Enter the vprn context";

                        leaf allocated {
                            type uint32;
                            description "Total number of SAPs per service allocated in the system.";
                        }

                    } // container vprn

                } // container sap

                container service {
                    description "Enter the service context";

                    container cpipe {
                        description "Enter the cpipe context";

                        leaf allocated {
                            type uint32;
                            description "Total number of services allocated in the system.";
                        }

                    } // container cpipe

                    container epipe {
                        description "Enter the epipe context";

                        leaf allocated {
                            type uint32;
                            description "Total number of services allocated in the system.";
                        }

                    } // container epipe

                    container ipipe {
                        description "Enter the ipipe context";

                        leaf allocated {
                            type uint32;
                            description "Total number of services allocated in the system.";
                        }

                    } // container ipipe

                    container ies {
                        description "Enter the ies context";

                        leaf allocated {
                            type uint32;
                            description "Total number of services allocated in the system.";
                        }

                    } // container ies

                    container mirror {
                        description "Enter the mirror context";

                        leaf allocated {
                            type uint32;
                            description "Total number of services allocated in the system.";
                        }

                    } // container mirror

                    container vpls {
                        description "Enter the vpls context";

                        leaf allocated {
                            type uint32;
                            description "Total number of services allocated in the system.";
                        }

                    } // container vpls

                    container vprn {
                        description "Enter the vprn context";

                        leaf allocated {
                            type uint32;
                            description "Total number of services allocated in the system.";
                        }

                    } // container vprn

                } // container service

                container egress-packet-re-injection-resources {
                    description "Enter the egress-packet-re-injection-resources context";

                    leaf total {
                        type uint32;
                        description "The total number of egress packet re-injection resources supported on this system.";
                    }

                    leaf allocated {
                        type uint32;
                        description "The total number of egress packet re-injection resources that are currently allocated on this system.";
                    }

                    leaf free {
                        type uint32;
                        description "The total number of egress packet re-injection resources that are remaining free on this system.";
                    }

                    container mirror {
                        description "Enter the mirror context";

                        leaf allocated {
                            type uint32;
                            description "Egress packet re-injection resources allocated to mirror.";
                        }

                    } // container mirror

                    container radius {
                        description "Enter the radius context";

                        leaf allocated {
                            type uint32;
                            description "Egress packet re-injection resources allocated to radius.";
                        }

                    } // container radius

                    container sat-traffic-generator {
                        description "Enter the sat-traffic-generator context";

                        leaf total {
                            type uint32;
                            description "Egress packet re-injection resources available to SAT traffic generator.";
                        }

                        leaf free {
                            type uint32;
                            description "SAT traffic generator resources unused by SAT traffic generator.";
                        }

                        leaf allocated {
                            type uint32;
                            description "SAT traffic generator resources allocated to SAT traffic generator.";
                        }

                    } // container sat-traffic-generator

                    container reserved {
                        description "Enter the reserved context";

                        leaf allocated {
                            type uint32;
                            description "Egress packet re-injection resources reserved.";
                        }

                    } // container reserved

                    container filter {
                        description "Enter the filter context";

                        leaf allocated {
                            type uint32;
                            description "Egress packet re-injection resources allocated to filter.";
                        }

                    } // container filter

                } // container egress-packet-re-injection-resources

                container ixr {
                    description "Enter the ixr context";

                    container common-lif {
                        description "Enter the common-lif context";

                        leaf total {
                            type yang:counter32;
                            description "The total number of resources.";
                        }

                        leaf allocated {
                            type yang:counter32;
                            description "The number of resources that are currently allocated.";
                        }

                        leaf free {
                            type yang:counter32;
                            description "The number of free resources that are currently available.";
                        }

                        list by-owner {
                            key "owner";
                            description "Enter the by-owner list instance";

                            leaf owner {
                                type types-system:ixr-resource-index-owner;
                                description "Application that uses the pool resources.";
                            }

                            leaf total {
                                type yang:counter32;
                                description "The total number of resources.";
                            }

                            leaf allocated {
                                type yang:counter32;
                                description "The number of resources that are currently allocated.";
                            }

                            leaf free {
                                type yang:counter32;
                                description "The number of free resources that are currently available.";
                            }

                        } // list by-owner

                    } // container common-lif

                    container arp-lif {
                        description "Enter the arp-lif context";

                        leaf total {
                            type yang:counter32;
                            description "The total number of resources.";
                        }

                        leaf allocated {
                            type yang:counter32;
                            description "The number of resources that are currently allocated.";
                        }

                        leaf free {
                            type yang:counter32;
                            description "The number of free resources that are currently available.";
                        }

                        list by-owner {
                            key "owner";
                            description "Enter the by-owner list instance";

                            leaf owner {
                                type types-system:ixr-resource-index-owner;
                                description "Application that uses the pool resources.";
                            }

                            leaf allocated {
                                type yang:counter32;
                                description "The number of resources that are currently allocated.";
                            }

                        } // list by-owner

                    } // container arp-lif

                    container mpls-lif {
                        description "Enter the mpls-lif context";

                        leaf total {
                            type yang:counter32;
                            description "The total number of resources.";
                        }

                        leaf allocated {
                            type yang:counter32;
                            description "The number of resources that are currently allocated.";
                        }

                        leaf free {
                            type yang:counter32;
                            description "The number of free resources that are currently available.";
                        }

                        list by-owner {
                            key "owner";
                            description "Enter the by-owner list instance";

                            leaf owner {
                                type types-system:ixr-resource-index-owner;
                                description "Application that uses the pool resources.";
                            }

                            leaf allocated {
                                type yang:counter32;
                                description "The number of resources that are currently allocated.";
                            }

                        } // list by-owner

                    } // container mpls-lif

                    container l3-vsi-rif {
                        description "Enter the l3-vsi-rif context";

                        leaf total {
                            type yang:counter32;
                            description "The total number of resources.";
                        }

                        leaf allocated {
                            type yang:counter32;
                            description "The number of resources that are currently allocated.";
                        }

                        leaf free {
                            type yang:counter32;
                            description "The number of free resources that are currently available.";
                        }

                        list by-owner {
                            key "owner";
                            description "Enter the by-owner list instance";

                            leaf owner {
                                type types-system:ixr-resource-index-owner;
                                description "Application that uses the pool resources.";
                            }

                            leaf allocated {
                                type yang:counter32;
                                description "The number of resources that are currently allocated.";
                            }

                        } // list by-owner

                    } // container l3-vsi-rif

                    container fec-system-wide {
                        description "Enter the fec-system-wide context";

                        container unpaired {
                            description "Enter the unpaired context";

                            leaf total {
                                type yang:counter32;
                                description "The total number of resources.";
                            }

                            leaf allocated {
                                type yang:counter32;
                                description "The number of resources that are currently allocated.";
                            }

                            leaf free {
                                type yang:counter32;
                                description "The number of free resources that are currently available.";
                            }

                            list by-owner {
                                key "owner";
                                description "Enter the by-owner list instance";

                                leaf owner {
                                    type types-system:ixr-resource-index-owner;
                                    description "Application that uses the pool resources.";
                                }

                                leaf allocated {
                                    type yang:counter32;
                                    description "The number of resources that are currently allocated.";
                                }

                            } // list by-owner

                        } // container unpaired

                        container paired {
                            description "Enter the paired context";

                            leaf total {
                                type yang:counter32;
                                description "The total number of resources.";
                            }

                            leaf allocated {
                                type yang:counter32;
                                description "The number of resources that are currently allocated.";
                            }

                            leaf free {
                                type yang:counter32;
                                description "The number of free resources that are currently available.";
                            }

                            list by-owner {
                                key "owner";
                                description "Enter the by-owner list instance";

                                leaf owner {
                                    type types-system:ixr-resource-index-owner;
                                    description "Application that uses the pool resources.";
                                }

                                leaf allocated {
                                    type yang:counter32;
                                    description "The number of resources that are currently allocated.";
                                }

                            } // list by-owner

                        } // container paired

                    } // container fec-system-wide

                    container oam-lm-ctr-id {
                        description "Enter the oam-lm-ctr-id context";

                        leaf total {
                            type yang:counter32;
                            description "The total number of resources.";
                        }

                        leaf allocated {
                            type yang:counter32;
                            description "The number of resources that are currently allocated.";
                        }

                        leaf free {
                            type yang:counter32;
                            description "The number of free resources that are currently available.";
                        }

                        list by-owner {
                            key "owner";
                            description "Enter the by-owner list instance";

                            leaf owner {
                                type types-system:ixr-resource-index-owner;
                                description "Application that uses the pool resources.";
                            }

                            leaf allocated {
                                type yang:counter32;
                                description "The number of resources that are currently allocated.";
                            }

                        } // list by-owner

                    } // container oam-lm-ctr-id

                    container mpls-nhlfe-lif {
                        description "Enter the mpls-nhlfe-lif context";

                        leaf total {
                            type yang:counter32;
                            description "The total number of resources.";
                        }

                        leaf allocated {
                            type yang:counter32;
                            description "The number of resources that are currently allocated.";
                        }

                        leaf free {
                            type yang:counter32;
                            description "The number of free resources that are currently available.";
                        }

                        list by-owner {
                            key "owner";
                            description "Enter the by-owner list instance";

                            leaf owner {
                                type types-system:ixr-resource-index-owner;
                                description "Application that uses the pool resources.";
                            }

                            leaf allocated {
                                type yang:counter32;
                                description "The number of resources that are currently allocated.";
                            }

                        } // list by-owner

                    } // container mpls-nhlfe-lif

                    container ac-lif {
                        description "Enter the ac-lif context";

                        leaf total {
                            type yang:counter32;
                            description "The total number of resources.";
                        }

                        leaf allocated {
                            type yang:counter32;
                            description "The number of resources that are currently allocated.";
                        }

                        leaf free {
                            type yang:counter32;
                            description "The number of free resources that are currently available.";
                        }

                        list by-owner {
                            key "owner";
                            description "Enter the by-owner list instance";

                            leaf owner {
                                type types-system:ixr-resource-index-owner;
                                description "Application that uses the pool resources.";
                            }

                            leaf allocated {
                                type yang:counter32;
                                description "The number of resources that are currently allocated.";
                            }

                        } // list by-owner

                    } // container ac-lif

                    container bgp-label-route-lif {
                        description "Enter the bgp-label-route-lif context";

                        leaf total {
                            type yang:counter32;
                            description "The total number of resources.";
                        }

                        leaf allocated {
                            type yang:counter32;
                            description "The number of resources that are currently allocated.";
                        }

                        leaf free {
                            type yang:counter32;
                            description "The number of free resources that are currently available.";
                        }

                        list by-owner {
                            key "owner";
                            description "Enter the by-owner list instance";

                            leaf owner {
                                type types-system:ixr-resource-index-owner;
                                description "Application that uses the pool resources.";
                            }

                            leaf total {
                                type yang:counter32;
                                description "The total number of resources.";
                            }

                            leaf allocated {
                                type yang:counter32;
                                description "The number of resources that are currently allocated.";
                            }

                            leaf free {
                                type yang:counter32;
                                description "The number of free resources that are currently available.";
                            }

                        } // list by-owner

                    } // container bgp-label-route-lif

                    container sdp-bind-mpls-lif {
                        description "Enter the sdp-bind-mpls-lif context";

                        leaf total {
                            type yang:counter32;
                            description "The total number of resources.";
                        }

                        leaf allocated {
                            type yang:counter32;
                            description "The number of resources that are currently allocated.";
                        }

                        leaf free {
                            type yang:counter32;
                            description "The number of free resources that are currently available.";
                        }

                        list by-owner {
                            key "owner";
                            description "Enter the by-owner list instance";

                            leaf owner {
                                type types-system:ixr-resource-index-owner;
                                description "Application that uses the pool resources.";
                            }

                            leaf allocated {
                                type yang:counter32;
                                description "The number of resources that are currently allocated.";
                            }

                        } // list by-owner

                    } // container sdp-bind-mpls-lif

                    container sdp-bind-gre-lif {
                        description "Enter the sdp-bind-gre-lif context";

                        leaf total {
                            type yang:counter32;
                            description "The total number of resources.";
                        }

                        leaf allocated {
                            type yang:counter32;
                            description "The number of resources that are currently allocated.";
                        }

                        leaf free {
                            type yang:counter32;
                            description "The number of free resources that are currently available.";
                        }

                        list by-owner {
                            key "owner";
                            description "Enter the by-owner list instance";

                            leaf owner {
                                type types-system:ixr-resource-index-owner;
                                description "Application that uses the pool resources.";
                            }

                            leaf allocated {
                                type yang:counter32;
                                description "The number of resources that are currently allocated.";
                            }

                        } // list by-owner

                    } // container sdp-bind-gre-lif

                    container ssid-lif {
                        description "Enter the ssid-lif context";

                        leaf total {
                            type yang:counter32;
                            description "The total number of resources.";
                        }

                        leaf allocated {
                            type yang:counter32;
                            description "The number of resources that are currently allocated.";
                        }

                        leaf free {
                            type yang:counter32;
                            description "The number of free resources that are currently available.";
                        }

                        list by-owner {
                            key "owner";
                            description "Enter the by-owner list instance";

                            leaf owner {
                                type types-system:ixr-resource-index-owner;
                                description "Application that uses the pool resources.";
                            }

                            leaf allocated {
                                type yang:counter32;
                                description "The number of resources that are currently allocated.";
                            }

                        } // list by-owner

                    } // container ssid-lif

                    container srv6-tunnel-lif {
                        description "Enter the srv6-tunnel-lif context";

                        leaf total {
                            type yang:counter32;
                            description "The total number of resources.";
                        }

                        leaf allocated {
                            type yang:counter32;
                            description "The number of resources that are currently allocated.";
                        }

                        leaf free {
                            type yang:counter32;
                            description "The number of free resources that are currently available.";
                        }

                        list by-owner {
                            key "owner";
                            description "Enter the by-owner list instance";

                            leaf owner {
                                type types-system:ixr-resource-index-owner;
                                description "Application that uses the pool resources.";
                            }

                            leaf allocated {
                                type yang:counter32;
                                description "The number of resources that are currently allocated.";
                            }

                        } // list by-owner

                    } // container srv6-tunnel-lif

                    container vxlan-lif {
                        description "Enter the vxlan-lif context";

                        leaf total {
                            type yang:counter32;
                            description "The total number of resources.";
                        }

                        leaf allocated {
                            type yang:counter32;
                            description "The number of resources that are currently allocated.";
                        }

                        leaf free {
                            type yang:counter32;
                            description "The number of free resources that are currently available.";
                        }

                        list by-owner {
                            key "owner";
                            description "Enter the by-owner list instance";

                            leaf owner {
                                type types-system:ixr-resource-index-owner;
                                description "Application that uses the pool resources.";
                            }

                            leaf allocated {
                                type yang:counter32;
                                description "The number of resources that are currently allocated.";
                            }

                        } // list by-owner

                    } // container vxlan-lif

                    container l2-service {
                        description "Enter the l2-service context";

                        leaf total {
                            type yang:counter32;
                            description "The total number of resources.";
                        }

                        leaf allocated {
                            type yang:counter32;
                            description "The number of resources that are currently allocated.";
                        }

                        leaf free {
                            type yang:counter32;
                            description "The number of free resources that are currently available.";
                        }

                        list by-owner {
                            key "owner";
                            description "Enter the by-owner list instance";

                            leaf owner {
                                type types-system:ixr-resource-index-owner;
                                description "Application that uses the pool resources.";
                            }

                            leaf allocated {
                                type yang:counter32;
                                description "The number of resources that are currently allocated.";
                            }

                        } // list by-owner

                    } // container l2-service

                    container station-id {
                        description "Enter the station-id context";

                        leaf total {
                            type yang:counter32;
                            description "The total number of resources.";
                        }

                        leaf allocated {
                            type yang:counter32;
                            description "The number of resources that are currently allocated.";
                        }

                        leaf free {
                            type yang:counter32;
                            description "The number of free resources that are currently available.";
                        }

                        list by-owner {
                            key "owner";
                            description "Enter the by-owner list instance";

                            leaf owner {
                                type types-system:ixr-resource-index-owner;
                                description "Application that uses the pool resources.";
                            }

                            leaf allocated {
                                type yang:counter32;
                                description "The number of resources that are currently allocated.";
                            }

                        } // list by-owner

                    } // container station-id

                    container ingress-classification-policies {
                        description "Enter the ingress-classification-policies context";

                        leaf total {
                            type yang:counter32;
                            description "The total number of resources supported on this system.";
                        }

                        leaf allocated {
                            type yang:counter32;
                            description "The total number of resources that are currently allocated on this system.";
                        }

                        leaf free {
                            type yang:counter32;
                            description "The total number of resources that are remaining free on this system.";
                        }

                    } // container ingress-classification-policies

                    container dot1p-fc-maps {
                        description "Enter the dot1p-fc-maps context";

                        leaf total {
                            type yang:counter32;
                            description "The total number of resources supported on this system.";
                        }

                        leaf allocated {
                            type yang:counter32;
                            description "The total number of resources that are currently allocated on this system.";
                        }

                        leaf free {
                            type yang:counter32;
                            description "The total number of resources that are remaining free on this system.";
                        }

                    } // container dot1p-fc-maps

                    container dscp-fc-maps {
                        description "Enter the dscp-fc-maps context";

                        leaf total {
                            type yang:counter32;
                            description "The total number of resources supported on this system.";
                        }

                        leaf allocated {
                            type yang:counter32;
                            description "The total number of resources that are currently allocated on this system.";
                        }

                        leaf free {
                            type yang:counter32;
                            description "The total number of resources that are remaining free on this system.";
                        }

                    } // container dscp-fc-maps

                    container lsp-exp-fc-maps {
                        description "Enter the lsp-exp-fc-maps context";

                        leaf total {
                            type yang:counter32;
                            description "The total number of resources supported on this system.";
                        }

                        leaf allocated {
                            type yang:counter32;
                            description "The total number of resources that are currently allocated on this system.";
                        }

                        leaf free {
                            type yang:counter32;
                            description "The total number of resources that are remaining free on this system.";
                        }

                    } // container lsp-exp-fc-maps

                    container egress-remark-policies {
                        description "Enter the egress-remark-policies context";

                        leaf total {
                            type yang:counter32;
                            description "The total number of resources supported on this system.";
                        }

                        leaf allocated {
                            type yang:counter32;
                            description "The total number of resources that are currently allocated on this system.";
                        }

                        leaf free {
                            type yang:counter32;
                            description "The total number of resources that are remaining free on this system.";
                        }

                    } // container egress-remark-policies

                    container fc-dot1p-maps {
                        description "Enter the fc-dot1p-maps context";

                        leaf total {
                            type yang:counter32;
                            description "The total number of resources supported on this system.";
                        }

                        leaf allocated {
                            type yang:counter32;
                            description "The total number of resources that are currently allocated on this system.";
                        }

                        leaf free {
                            type yang:counter32;
                            description "The total number of resources that are remaining free on this system.";
                        }

                    } // container fc-dot1p-maps

                    container fc-dscp-maps {
                        description "Enter the fc-dscp-maps context";

                        leaf total {
                            type yang:counter32;
                            description "The total number of resources supported on this system.";
                        }

                        leaf allocated {
                            type yang:counter32;
                            description "The total number of resources that are currently allocated on this system.";
                        }

                        leaf free {
                            type yang:counter32;
                            description "The total number of resources that are remaining free on this system.";
                        }

                    } // container fc-dscp-maps

                    container fc-lsp-exp-maps {
                        description "Enter the fc-lsp-exp-maps context";

                        leaf total {
                            type yang:counter32;
                            description "The total number of resources supported on this system.";
                        }

                        leaf allocated {
                            type yang:counter32;
                            description "The total number of resources that are currently allocated on this system.";
                        }

                        leaf free {
                            type yang:counter32;
                            description "The total number of resources that are remaining free on this system.";
                        }

                    } // container fc-lsp-exp-maps

                    container queue-mgmt-policies {
                        description "Enter the queue-mgmt-policies context";

                        leaf total {
                            type yang:counter32;
                            description "The total number of resources supported on this system.";
                        }

                        leaf allocated {
                            type yang:counter32;
                            description "The total number of resources that are currently allocated on this system.";
                        }

                        leaf free {
                            type yang:counter32;
                            description "The total number of resources that are remaining free on this system.";
                        }

                    } // container queue-mgmt-policies

                    container vlan-qos-voq-with-statistics {
                        description "Enter the vlan-qos-voq-with-statistics context";

                        leaf total {
                            type yang:counter32;
                            description "The total number of resources supported on this system.";
                        }

                        leaf allocated {
                            type yang:counter32;
                            description "The total number of resources that are currently allocated on this system.";
                        }

                        leaf free {
                            type yang:counter32;
                            description "The total number of resources that are remaining free on this system.";
                        }

                    } // container vlan-qos-voq-with-statistics

                    container vlan-qos-voq-without-statistics {
                        description "Enter the vlan-qos-voq-without-statistics context";

                        leaf total {
                            type yang:counter32;
                            description "The total number of resources supported on this system.";
                        }

                        leaf allocated {
                            type yang:counter32;
                            description "The total number of resources that are currently allocated on this system.";
                        }

                        leaf free {
                            type yang:counter32;
                            description "The total number of resources that are remaining free on this system.";
                        }

                    } // container vlan-qos-voq-without-statistics

                } // container ixr

            } // container resource-usage

            container switch-fabric {
                description "Enter the switch-fabric context";

                container failure-recovery {
                    description "Enter the failure-recovery context";

                    leaf oper-state {
                        type enumeration {
                            enum disabled                       { value 0; }
                            enum hold-down                      { value 1; }
                            enum ready                          { value 2; }
                            enum recovery-in-progress           { value 3; }
                            enum detected-disabled              { value 4; }
                            enum detected-hold-down             { value 5; }
                            enum detected-xrs40-migration       { value 6; }
                            enum detected-sfm-upgrade-pending   { value 7; }
                        }
                        description
                            "Indicates the operational state of the automatic switch fabric
                             failure recovery process.";
                    }

                    list sfm {
                        key "sfm-slot";
                        description "Enter the sfm list instance";

                        leaf sfm-slot {
                            type leafref {
                                path "../../../../../sfm/sfm-slot";
                            }
                            description
                                "The unique value which identifies this SFM slot within a
                                 chassis in the system.";
                        }

                        leaf state {
                            type enumeration {
                                enum complete                       { value 0; }
                                enum in-progress                    { value 1; }
                                enum pending                        { value 2; }
                                enum aborted                        { value 3; }
                                enum failed                         { value 4; }
                            }
                            description
                                "Indicates the current state of the SFM in the automatic
                                 switch fabric recovery process.

                                 Values:
                                     complete    - this SFM has already been reset as part of
                                                   the recovery process
                                     in-progress - this SFM is currently being reset
                                     pending     - this SFM has not yet been reset
                                     aborted     - the recovery was aborted before this SFM
                                                   was processed
                                     failed      - the SFM has not successfully completed";
                        }

                        leaf state-time {
                            type yang:date-and-time;
                            description "Indicates the date and time the state changed.";
                        }

                    } // list sfm

                } // container failure-recovery

            } // container switch-fabric

            container last-reboot {
                description "Enter the last-reboot context";

                leaf reason {
                    type enumeration {
                        enum admin                          { value 1; }
                        enum other                          { value 2; }
                    }
                    description "Indicates whether the last reboot was due to admin action.";
                }

                leaf user {
                    type types-sros:named-item-or-empty;
                    description "The unique identifier of the user who initiated the last reboot.";
                }

                leaf router {
                    type types-sros:router-instance-base-management-vprn-loose;
                    description
                        "Router-instance of the management session which initiated the last
                         reboot command.";
                }

                leaf ip-address {
                    type types-sros:ip-address;
                    description
                        "Ip-address sourcing the management session which initiated the last
                         reboot command.";
                }

                leaf time {
                    type yang:date-and-time;
                    description "The date and time the last reboot was initiated.";
                }

            } // container last-reboot

            uses state-system-bluetooth;
            uses state-system-bootup;
            uses state-system-cron;
            uses state-system-licensing;
            uses state-system-ptp;
            uses state-system-script-control;
            uses state-system-security;
            uses state-system-telemetry;
            uses state-system-time;
        } // container system

    } // grouping state-system

}
