submodule nokia-conf-svc-ipfix {

    yang-version "1.1";

    belongs-to nokia-conf { prefix "conf"; }

    import nokia-sros-yang-extensions     { prefix "sros-ext"; }
    import nokia-types-l2tp               { prefix "types-l2tp"; }
    import nokia-types-sros               { prefix "types-sros"; }

    include nokia-conf-groups;

    sros-ext:sros-major-release "rel25";
    organization "Nokia";
    contact
        "Nokia SR OS Support
         Web: <http://www.nokia.com>";
    description
        "Nokia YANG Data model to configure ipfix service on SR OS based routers.

         Copyright 2016 Nokia. All rights reserved. Reproduction of this document
         is authorized on the condition that the foregoing copyright notice is included.

         This nokia-conf-svc-ipfix YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";
    revision "2025-03-12";

    grouping conf-svc-ipfix {
        container ipfix {
            description "Enter the ipfix context";

            leaf-list apply-groups {
                type leafref {
                    path "../../../groups/group/name";
                }
                max-elements 8;
                ordered-by user;
                description "Apply a configuration group at this level";
            }

            leaf-list apply-groups-exclude {
                type leafref {
                    path "../../../groups/group/name";
                }
                max-elements 8;
                ordered-by user;
                description "Exclude a configuration group at this level";
            }

            list export-policy {
                key "name";
                description "Enter the export-policy list instance";

                leaf name {
                    type types-sros:named-item;
                    description "IPFIX policy name";
                }

                leaf description {
                    type types-sros:description;
                    description "Text description";
                }

                leaf template-format {
                    type enumeration {
                        enum format1                        { value 1; }
                        enum format2                        { value 2; }
                    }
                    default "format1";
                    description "Template format used by this IPFIX export policy";
                }

                leaf-list apply-groups {
                    type leafref {
                        path "../../../../groups/group/name";
                    }
                    max-elements 8;
                    ordered-by user;
                    description "Apply a configuration group at this level";
                }

                leaf-list apply-groups-exclude {
                    type leafref {
                        path "../../../../groups/group/name";
                    }
                    max-elements 8;
                    ordered-by user;
                    description "Exclude a configuration group at this level";
                }

                list collector {
                    key "router-instance ip-address";
                    description "Enter the collector list instance";

                    leaf router-instance {
                        type string;
                        description "Router where the collector is reached";
                    }

                    leaf ip-address {
                        type types-sros:ipv4-unicast-address;
                        description "IPv4 address of the external collector node";
                    }

                    leaf admin-state {
                        type types-sros:admin-state;
                        default "disable";
                        description "Administrative state of the collector";
                    }

                    leaf mtu {
                        type types-l2tp:base-ppp-mtu;
                        sros-ext:auto-restart-to-modify;
                        default "1500";
                        description "Maximum Transmission Unit";
                    }

                    leaf source-ip-address {
                        type types-sros:ipv4-unicast-address;
                        sros-ext:auto-restart-to-modify;
                        description "Source IP address from which UDP streams are sent";
                    }

                    leaf refresh-timeout {
                        type types-sros:time-duration {
                            range "240..86400";
                        }
                        units "seconds";
                        sros-ext:auto-restart-to-modify;
                        default "600";
                        description "IPFIX template refresh time";
                    }

                    leaf-list apply-groups {
                        type leafref {
                            path "../../../../../groups/group/name";
                        }
                        max-elements 8;
                        ordered-by user;
                        sros-ext:auto-restart-to-modify;
                        description "Apply a configuration group at this level";
                    }

                    leaf-list apply-groups-exclude {
                        type leafref {
                            path "../../../../../groups/group/name";
                        }
                        max-elements 8;
                        ordered-by user;
                        sros-ext:auto-restart-to-modify;
                        description "Exclude a configuration group at this level";
                    }

                } // list collector

            } // list export-policy

        } // container ipfix

    } // grouping conf-svc-ipfix

}
