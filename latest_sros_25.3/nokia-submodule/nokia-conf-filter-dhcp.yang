submodule nokia-conf-filter-dhcp {

    yang-version "1.1";

    belongs-to nokia-conf { prefix "conf"; }

    import nokia-sros-yang-extensions     { prefix "sros-ext"; }
    import nokia-types-sros               { prefix "types-sros"; }

    include nokia-conf-groups;

    sros-ext:sros-major-release "rel25";
    organization "Nokia";
    contact
        "Nokia SR OS Support
         Web: <http://www.nokia.com>";
    description
        "Nokia YANG Data model to configure CPM software based DHCP filters on SR OS based routers.

         Copyright 2016 Nokia. All rights reserved. Reproduction of this document
         is authorized on the condition that the foregoing copyright notice is included.

         This nokia-conf-filter-dhcp YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";
    revision "2025-03-12";

    grouping conf-filter-dhcp-dhcp-filter {
        list dhcp-filter {
            key "filter-id";
            description "Enter the dhcp-filter list instance";

            leaf filter-id {
                type uint32 {
                    range "1..65535";
                }
                description "Unique DHCP filter policy ID";
            }

            leaf description {
                type types-sros:description;
                description "Text description";
            }

            leaf-list apply-groups {
                type leafref {
                    path "../../../groups/group/name";
                }
                max-elements 8;
                ordered-by user;
                description "Apply a configuration group at this level";
            }

            leaf-list apply-groups-exclude {
                type leafref {
                    path "../../../groups/group/name";
                }
                max-elements 8;
                ordered-by user;
                description "Exclude a configuration group at this level";
            }

            container default-action {
                presence "Enable the default-action context";
                description "Enable the default-action context";

                choice action {
                    mandatory true;
                    description
                        "The action to take for DHCP host creation requests that match this
                         filter entry. If not set host creation proceeds as usual";
                    case bypass-host-creation {

                        leaf bypass-host-creation {
                            type empty;
                            description "Host creation options to bypass";
                        }

                    }
                    case drop {

                        leaf drop {
                            type empty;
                            description "DHCP host creation when the filter entry is matched";
                        }

                    }
                }
            } // container default-action

            list entry {
                key "entry-id";
                max-elements 10;
                description "Enter the entry list instance";

                leaf entry-id {
                    type uint32 {
                        range "1..65535";
                    }
                    description "DHCP filter entry ID";
                }

                leaf-list apply-groups {
                    type leafref {
                        path "../../../../groups/group/name";
                    }
                    max-elements 8;
                    ordered-by user;
                    description "Apply a configuration group at this level";
                }

                leaf-list apply-groups-exclude {
                    type leafref {
                        path "../../../../groups/group/name";
                    }
                    max-elements 8;
                    ordered-by user;
                    description "Exclude a configuration group at this level";
                }

                container action {
                    presence "Enable the action context";
                    description "Enable the action context";

                    choice action {
                        mandatory true;
                        description
                            "The action to take for DHCP host creation requests that match this
                             filter entry. If not set host creation proceeds as usual";
                        case bypass-host-creation {

                            leaf bypass-host-creation {
                                type empty;
                                description "Host creation options to bypass";
                            }

                        }
                        case drop {

                            leaf drop {
                                type empty;
                                description "DHCP host creation when the filter entry is matched";
                            }

                        }
                    }
                } // container action

                container option {
                    presence "Enable the option context";
                    description "Enable the option context";

                    leaf number {
                        type int32 {
                            range "0..255";
                        }
                        mandatory true;
                        description "Number for DHCP or DHCPv6 option to filter on";
                    }

                    choice option-match {
                        mandatory true;
                        case present {

                            leaf present {
                                type empty;
                                description "Require the presence of related option";
                            }

                        }
                        case absent {

                            leaf absent {
                                type empty;
                                description "Require the absence of related option";
                            }

                        }
                        case match {

                            container match {
                                presence "Enable the match context";
                                description "Enable the match context";

                                leaf exact {
                                    type boolean;
                                    default "false";
                                    description "Use an exact match pattern (not partial)";
                                }

                                leaf invert {
                                    type boolean;
                                    default "false";
                                    description "Invert (partial) matching criteria";
                                }

                                choice option-value {
                                    mandatory true;
                                    case string {

                                        leaf string {
                                            type string {
                                                length "1..127";
                                            }
                                            description "Matching pattern for the filtered option";
                                        }

                                    }
                                    case hex {

                                        leaf hex {
                                            type string {
                                                length "1..256";
                                                pattern "0x[0-9a-fA-F]+";
                                            }
                                            description "Matching pattern for the filtered option";
                                        }

                                    }
                                }
                            } // container match

                        }
                    }
                } // container option

            } // list entry

        } // list dhcp-filter

    } // grouping conf-filter-dhcp-dhcp-filter

    grouping conf-filter-dhcp-dhcp6-filter {
        list dhcp6-filter {
            key "filter-id";
            description "Enter the dhcp6-filter list instance";

            leaf filter-id {
                type uint32 {
                    range "1..65535";
                }
                description "Unique DHCP filter policy ID";
            }

            leaf description {
                type types-sros:description;
                description "Text description";
            }

            leaf-list apply-groups {
                type leafref {
                    path "../../../groups/group/name";
                }
                max-elements 8;
                ordered-by user;
                description "Apply a configuration group at this level";
            }

            leaf-list apply-groups-exclude {
                type leafref {
                    path "../../../groups/group/name";
                }
                max-elements 8;
                ordered-by user;
                description "Exclude a configuration group at this level";
            }

            container default-action {
                presence "Enable the default-action context";
                description "Enable the default-action context";

                choice action {
                    mandatory true;
                    description
                        "The action to take for DHCP6 host creation requests that match this
                         filter entry. If not set host creation proceeds as usual";
                    case bypass-host-creation {

                        container bypass-host-creation {
                            presence "Enable the bypass-host-creation context";
                            description "Enable the bypass-host-creation context";

                            leaf na {
                                type boolean;
                                default "true";
                                description "Bypass the DHCPv6 NA host creation";
                            }

                            leaf pd {
                                type boolean;
                                default "true";
                                description "Bypass the DHCPv6 PD host creation";
                            }

                        } // container bypass-host-creation

                    }
                    case drop {

                        leaf drop {
                            type empty;
                            description "Drop DHCPv6 message (do not process)";
                        }

                    }
                }
            } // container default-action

            list entry {
                key "entry-id";
                max-elements 10;
                description "Enter the entry list instance";

                leaf entry-id {
                    type uint32 {
                        range "1..65535";
                    }
                    description "DHCP filter entry ID";
                }

                leaf-list apply-groups {
                    type leafref {
                        path "../../../../groups/group/name";
                    }
                    max-elements 8;
                    ordered-by user;
                    description "Apply a configuration group at this level";
                }

                leaf-list apply-groups-exclude {
                    type leafref {
                        path "../../../../groups/group/name";
                    }
                    max-elements 8;
                    ordered-by user;
                    description "Exclude a configuration group at this level";
                }

                container action {
                    presence "Enable the action context";
                    description "Enable the action context";

                    choice action {
                        mandatory true;
                        description
                            "The action to take for DHCP6 host creation requests that match this
                             filter entry. If not set host creation proceeds as usual";
                        case bypass-host-creation {

                            container bypass-host-creation {
                                presence "Enable the bypass-host-creation context";
                                description "Enable the bypass-host-creation context";

                                leaf na {
                                    type boolean;
                                    default "true";
                                    description "Bypass the DHCPv6 NA host creation";
                                }

                                leaf pd {
                                    type boolean;
                                    default "true";
                                    description "Bypass the DHCPv6 PD host creation";
                                }

                            } // container bypass-host-creation

                        }
                        case drop {

                            leaf drop {
                                type empty;
                                description "Drop DHCPv6 message (do not process)";
                            }

                        }
                    }
                } // container action

                container option {
                    presence "Enable the option context";
                    description "Enable the option context";

                    leaf number {
                        type int32 {
                            range "0..255";
                        }
                        mandatory true;
                        description "Number for DHCP or DHCPv6 option to filter on";
                    }

                    choice option-match {
                        mandatory true;
                        case present {

                            leaf present {
                                type empty;
                                description "Require the presence of related option";
                            }

                        }
                        case absent {

                            leaf absent {
                                type empty;
                                description "Require the absence of related option";
                            }

                        }
                        case match {

                            container match {
                                presence "Enable the match context";
                                description "Enable the match context";

                                leaf exact {
                                    type boolean;
                                    default "false";
                                    description "Use an exact match pattern (not partial)";
                                }

                                leaf invert {
                                    type boolean;
                                    default "false";
                                    description "Invert (partial) matching criteria";
                                }

                                choice option-value {
                                    mandatory true;
                                    case string {

                                        leaf string {
                                            type string {
                                                length "1..127";
                                            }
                                            description "Matching pattern for the filtered option";
                                        }

                                    }
                                    case hex {

                                        leaf hex {
                                            type string {
                                                length "1..256";
                                                pattern "0x[0-9a-fA-F]+";
                                            }
                                            description "Matching pattern for the filtered option";
                                        }

                                    }
                                }
                            } // container match

                        }
                    }
                } // container option

            } // list entry

        } // list dhcp6-filter

    } // grouping conf-filter-dhcp-dhcp6-filter

}
