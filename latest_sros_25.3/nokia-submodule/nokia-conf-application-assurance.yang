submodule nokia-conf-application-assurance {

    yang-version "1.1";

    belongs-to nokia-conf { prefix "conf"; }

    import nokia-sros-yang-extensions     { prefix "sros-ext"; }
    import nokia-types-port               { prefix "types-port"; }
    import nokia-types-services           { prefix "types-services"; }
    import nokia-types-sros               { prefix "types-sros"; }

    include nokia-conf-aa-group;
    include nokia-conf-groups;

    sros-ext:sros-major-release "rel25";
    organization "Nokia";
    contact
        "Nokia SR OS Support
         Web: <http://www.nokia.com>";
    description
        "Nokia YANG Data model to configure application assurance components on SR OS based routers.

         Copyright 2016 Nokia. All rights reserved. Reproduction of this document
         is authorized on the condition that the foregoing copyright notice is included.

         This nokia-conf-application-assurance YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";
    revision "2025-03-12";

    grouping conf-application-assurance {
        container application-assurance {
            description "Enter the application-assurance context";

            leaf-list apply-groups {
                type leafref {
                    path "../../groups/group/name";
                }
                max-elements 8;
                ordered-by user;
                description "Apply a configuration group at this level";
            }

            leaf-list apply-groups-exclude {
                type leafref {
                    path "../../groups/group/name";
                }
                max-elements 8;
                ordered-by user;
                description "Exclude a configuration group at this level";
            }

            container usage-alert-thresholds {
                description "Enter the usage-alert-thresholds context";

                leaf bit-rate-high-wmark {
                    type union {
                        type int32 {
                            range "1..100000";
                        }
                        type enumeration {
                            enum max                            { value 1; }
                        }
                    }
                    units "megabps";
                    default "max";
                    description "High watermark for bit rate alarms";
                }

                leaf bit-rate-low-wmark {
                    type uint32 {
                        range "0..99999";
                    }
                    default "0";
                    description "Low watermark for bit rate alarms";
                }

                leaf datapath-cpu-high-wmark {
                    type union {
                        type int32 {
                            range "0..100";
                        }
                        type enumeration {
                            enum max                            { value 1; }
                        }
                    }
                    units "percent";
                    default "95";
                    description "High watermark for datapath CPU alarms";
                }

                leaf datapath-cpu-low-wmark {
                    type int32 {
                        range "0..100";
                    }
                    units "percent";
                    default "90";
                    description "Low watermark for datapath CPU alarms";
                }

                leaf flow-table-high-wmark {
                    type int32 {
                        range "0..100";
                    }
                    units "percent";
                    default "95";
                    description "Flow table high watermark";
                }

                leaf flow-table-low-wmark {
                    type int32 {
                        range "0..100";
                    }
                    units "percent";
                    default "90";
                    description "Flow table low watermark";
                }

                leaf flow-setup-rate-high-wmark {
                    type union {
                        type int32 {
                            range "1..2000000";
                        }
                        type enumeration {
                            enum max                            { value 1; }
                        }
                    }
                    default "max";
                    description "High watermark for flow setup rate";
                }

                leaf flow-setup-rate-low-wmark {
                    type uint32 {
                        range "0..1999999";
                    }
                    default "0";
                    description "Low watermark for flow setup rate";
                }

                leaf packet-rate-high-wmark {
                    type union {
                        type int32 {
                            range "1..148809524";
                        }
                        type enumeration {
                            enum max                            { value 1; }
                        }
                    }
                    default "max";
                    description "Packet rate high watermark";
                }

                leaf packet-rate-low-wmark {
                    type uint32 {
                        range "0..148809523";
                    }
                    default "0";
                    description "Packet rate low watermark";
                }

            } // container usage-alert-thresholds

            list aarp {
                key "aarp-id";
                max-elements 100;
                description "Enter the aarp list instance";

                leaf aarp-id {
                    type types-services:bsx-aarp-id;
                    description "AARP ID";
                }

                leaf admin-state {
                    type types-sros:admin-state;
                    default "disable";
                    description "Administrative state of the AARP instance";
                }

                leaf description {
                    type types-sros:description;
                    description "Text description";
                }

                leaf master-selection-mode {
                    type enumeration {
                        enum minimize-switchovers           { value 1; }
                        enum inter-chassis-efficiency       { value 2; }
                        enum priority-based-balance         { value 3; }
                    }
                    sros-ext:auto-restart-to-modify;
                    default "minimize-switchovers";
                    description "AARP master selection mode";
                }

                leaf peer {
                    type types-sros:ip-unicast-address;
                    sros-ext:auto-restart-to-modify;
                    description "AARP peer IP address";
                }

                leaf priority {
                    type uint32 {
                        range "0..255";
                    }
                    sros-ext:auto-restart-to-modify;
                    default "100";
                    description "AARP priority";
                }

                leaf-list apply-groups {
                    type leafref {
                        path "../../../groups/group/name";
                    }
                    max-elements 8;
                    ordered-by user;
                    description "Apply a configuration group at this level";
                }

                leaf-list apply-groups-exclude {
                    type leafref {
                        path "../../../groups/group/name";
                    }
                    max-elements 8;
                    ordered-by user;
                    description "Exclude a configuration group at this level";
                }

                container peer-endpoint {
                    description "Enter the peer-endpoint context";

                    choice endpoint-choice {
                        case sap {

                            container sap {
                                presence "Enable the sap context";
                                description "Enable the sap context";

                                leaf sap-id {
                                    type types-sros:sap;
                                    mandatory true;
                                    description "AARP peer endpoint SAP ID";
                                }

                                leaf encap-type {
                                    type types-port:ethernet-encap-type;
                                    mandatory true;
                                    description "Encapsulation type for peer endpoint SAP";
                                }

                            } // container sap

                        }
                        case spoke-sdp {

                            leaf spoke-sdp {
                                type types-services:sdp-bind-id;
                                description "AARP peer endpoint spoke SDP";
                            }

                        }
                    }
                } // container peer-endpoint

            } // list aarp

            container cflowd {
                description "Enter the cflowd context";

                list field {
                    key "field-name";
                    description "Enter the field list instance";

                    leaf field-name {
                        type types-sros:named-item;
                        description "Cflowd record field name";
                    }

                    leaf comment {
                        type types-sros:named-item;
                        description "User information comment";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                } // list field

            } // container cflowd

            container flow-attribute {
                description "Enter the flow-attribute context";

                list attribute {
                    key "attribute-name";
                    description "Enter the attribute list instance";

                    leaf attribute-name {
                        type types-sros:named-item;
                        description "Attribute name";
                    }

                    leaf comment {
                        type types-sros:named-item;
                        description "User information comment";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                } // list attribute

            } // container flow-attribute

            container http-enrich {
                description "Enter the http-enrich context";

                list field {
                    key "field-name";
                    description "Enter the field list instance";

                    leaf field-name {
                        type types-sros:named-item;
                        description "HTTP enrich field name (void, do not use)";
                    }

                    leaf comment {
                        type types-sros:named-item;
                        description "User information comment";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                } // list field

            } // container http-enrich

            container http-error-redirect {
                description "Enter the http-error-redirect context";

                list error-code {
                    key "error-code-number";
                    description "Enter the error-code list instance";

                    leaf error-code-number {
                        type uint32 {
                            range "400..999";
                        }
                        description "Error code for HTTP error redirection";
                    }

                    leaf comment {
                        type types-sros:named-item;
                        description "User information comment";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                } // list error-code

                list template {
                    key "template-id";
                    description "Enter the template list instance";

                    leaf template-id {
                        type uint32;
                        description "HTTP error redirect template ID";
                    }

                    leaf comment {
                        type types-sros:named-item;
                        description "User information comment";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                } // list template

            } // container http-error-redirect

            container http-notification {
                description "Enter the http-notification context";

                list template {
                    key "template-id";
                    description "Enter the template list instance";

                    leaf template-id {
                        type uint32;
                        description "HTTP notification template ID";
                    }

                    leaf comment {
                        type types-sros:named-item;
                        description "User information comment";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                } // list template

            } // container http-notification

            container http-redirect {
                description "Enter the http-redirect context";

                list template {
                    key "template-id";
                    description "Enter the template list instance";

                    leaf template-id {
                        type uint32;
                        description "HTTP redirect template ID";
                    }

                    leaf comment {
                        type types-sros:named-item;
                        description "User information comment";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                } // list template

            } // container http-redirect

            list protocol {
                key "protocol-name";
                description "Enter the protocol list instance";

                leaf protocol-name {
                    type types-sros:named-item;
                    description "AA protocol name";
                }

                leaf admin-state {
                    type types-sros:admin-state;
                    description "Administrative state of the protocol";
                }

                leaf-list apply-groups {
                    type leafref {
                        path "../../../groups/group/name";
                    }
                    max-elements 8;
                    ordered-by user;
                    description "Apply a configuration group at this level";
                }

                leaf-list apply-groups-exclude {
                    type leafref {
                        path "../../../groups/group/name";
                    }
                    max-elements 8;
                    ordered-by user;
                    description "Exclude a configuration group at this level";
                }

            } // list protocol

            list radius-accounting-policy {
                key "rad-acct-plcy-name";
                max-elements 8;
                description "Enter the radius-accounting-policy list instance";

                leaf rad-acct-plcy-name {
                    type types-sros:named-item;
                    description "AA RADIUS accounting policy name";
                }

                leaf description {
                    type types-sros:description;
                    description "Text description";
                }

                leaf interim-update-interval {
                    type uint32 {
                        range "5..1080";
                    }
                    units "minutes";
                    description "AA RADIUS accounting policy interim update interval";
                }

                leaf significant-change {
                    type uint32 {
                        range "1";
                    }
                    description "Change delta for RADIUS accounting record updates";
                }

                leaf-list apply-groups {
                    type leafref {
                        path "../../../groups/group/name";
                    }
                    max-elements 8;
                    ordered-by user;
                    description "Apply a configuration group at this level";
                }

                leaf-list apply-groups-exclude {
                    type leafref {
                        path "../../../groups/group/name";
                    }
                    max-elements 8;
                    ordered-by user;
                    description "Exclude a configuration group at this level";
                }

                container radius-accounting-server {
                    description "Enter the radius-accounting-server context";

                    leaf access-algorithm {
                        type enumeration {
                            enum direct                         { value 1; }
                            enum round-robin                    { value 2; }
                        }
                        default "direct";
                        description "Access algorithm for the list of RADIUS servers";
                    }

                    leaf retry {
                        type uint32 {
                            range "1..10";
                        }
                        default "3";
                        description "Number of retries for contacting the RADIUS server";
                    }

                    leaf router-instance {
                        type string;
                        description "Router or VPRN service name";
                    }

                    leaf source-address {
                        type types-sros:ipv4-unicast-address;
                        description "Source IP address of RADIUS packets";
                    }

                    leaf timeout {
                        type uint32 {
                            range "1..90";
                        }
                        units "seconds";
                        default "5";
                        description "RADIUS accounting server response timeout";
                    }

                    list server {
                        key "server-index";
                        max-elements 5;
                        description "Enter the server list instance";

                        leaf server-index {
                            type uint32 {
                                range "1..5";
                            }
                            description "RADIUS accounting server index";
                        }

                        leaf address {
                            type types-sros:ipv4-unicast-address;
                            mandatory true;
                            description "RADIUS server IP address";
                        }

                        leaf port {
                            type uint16 {
                                range "1..65535";
                            }
                            default "1813";
                            description "RADIUS server UDP port used for authentication";
                        }

                        leaf secret {
                            type types-sros:encrypted-leaf {
                                length "1..54";
                            }
                            mandatory true;
                            description "RADIUS server secret key";
                        }

                        leaf-list apply-groups {
                            type leafref {
                                path "../../../../../groups/group/name";
                            }
                            max-elements 8;
                            ordered-by user;
                            description "Apply a configuration group at this level";
                        }

                        leaf-list apply-groups-exclude {
                            type leafref {
                                path "../../../../../groups/group/name";
                            }
                            max-elements 8;
                            ordered-by user;
                            description "Exclude a configuration group at this level";
                        }

                    } // list server

                } // container radius-accounting-server

            } // list radius-accounting-policy

            uses conf-aa-group;
        } // container application-assurance

    } // grouping conf-application-assurance

}
