submodule nokia-conf-log {

    yang-version "1.1";

    belongs-to nokia-conf { prefix "conf"; }

    import nokia-sros-yang-extensions     { prefix "sros-ext"; }
    import nokia-types-log                { prefix "types-log"; }
    import nokia-types-qos                { prefix "types-qos"; }
    import nokia-types-sros               { prefix "types-sros"; }

    include nokia-conf-groups;
    include nokia-conf-python;
    include nokia-conf-service;
    include nokia-conf-svc-vprn;
    include nokia-conf-system;
    include nokia-conf-system-script-control;
    include nokia-conf-system-security;
    include nokia-conf-system-security-tls;

    sros-ext:sros-major-release "rel25";
    organization "Nokia";
    contact
        "Nokia SR OS Support
         Web: <http://www.nokia.com>";
    description
        "Nokia YANG Data model to configure event stream logging on SR OS based routers.

         Copyright 2016 Nokia. All rights reserved. Reproduction of this document
         is authorized on the condition that the foregoing copyright notice is included.

         This nokia-conf-log YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";
    revision "2025-04-23";

    grouping conf-log {
        container log {
            description "Enter the log context";

            leaf event-damping {
                type boolean;
                default "true";
                description "Allow event damping algorithm to suppress QoS or filter change events";
            }

            leaf encryption-key {
                type types-sros:encrypted-leaf {
                    length "1..71";
                }
                description "Secret key for the encryption of log files";
            }

            leaf-list apply-groups {
                type leafref {
                    path "../../groups/group/name";
                }
                max-elements 8;
                ordered-by user;
                description "Apply a configuration group at this level";
            }

            leaf-list apply-groups-exclude {
                type leafref {
                    path "../../groups/group/name";
                }
                max-elements 8;
                ordered-by user;
                description "Exclude a configuration group at this level";
            }

            container file-storage-control {
                description "Enter the file-storage-control context";

                leaf log-files-total-size {
                    type uint32 {
                        range "50..4194304";
                    }
                    units "megabytes";
                    description "Per CF total log file storage limit";
                }

                leaf accounting-files-total-size {
                    type uint32 {
                        range "50..4194304";
                    }
                    units "megabytes";
                    description "Per CF total accounting file storage limit";
                }

            } // container file-storage-control

            list accounting-policy {
                key "policy-id";
                description "Enter the accounting-policy list instance";

                leaf policy-id {
                    type types-log:log-policy-id;
                    description "Accounting policy unique ID";
                }

                leaf admin-state {
                    type types-sros:admin-state;
                    default "disable";
                    description "Administrative state of the accounting policy";
                }

                leaf description {
                    type types-sros:description;
                    description "Text description";
                }

                leaf collection-interval {
                    type int32 {
                        range "1..120";
                    }
                    units "minutes";
                    description "Accounting collection interval";
                }

                leaf default {
                    type boolean;
                    sros-ext:auto-restart-to-modify;
                    default "false";
                    description "Default accounting policy for all objects that do not have an accounting policy";
                }

                leaf include-system-info {
                    type boolean;
                    default "false";
                    description "Include system information in accounting policy records";
                }

                leaf record {
                    type types-log:accounting-record-type;
                    sros-ext:immutable;
                    sros-ext:auto-restart-to-modify;
                    description "Accounting policy record type";
                }

                leaf align {
                    type boolean;
                    default "false";
                    description "Align statistics collection interval to absolute time";
                }

                leaf-list apply-groups {
                    type leafref {
                        path "../../../groups/group/name";
                    }
                    max-elements 8;
                    ordered-by user;
                    description "Apply a configuration group at this level";
                }

                leaf-list apply-groups-exclude {
                    type leafref {
                        path "../../../groups/group/name";
                    }
                    max-elements 8;
                    ordered-by user;
                    description "Exclude a configuration group at this level";
                }

                container custom-record {
                    description "Enter the custom-record context";

                    leaf significant-change {
                        type uint32 {
                            range "0..max";
                        }
                        description "Significant change required to generate the record";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                    container aa-specific {
                        description "Enter the aa-specific context";

                        container aa-sub-attributes {
                            description "Enter the aa-sub-attributes context";

                            leaf app-profile {
                                type boolean;
                                default "false";
                                description "Include application profile to be exported";
                            }

                            leaf app-service-options {
                                type boolean;
                                default "false";
                                description "Include application service options";
                            }

                        } // container aa-sub-attributes

                        container aa-sub-counters {
                            description "Enter the aa-sub-counters context";

                            leaf long-duration-flow-count {
                                type boolean;
                                default "false";
                                description "Include the long duration flow count";
                            }

                            leaf medium-duration-flow-count {
                                type boolean;
                                default "false";
                                description "Include the medium duration flow";
                            }

                            leaf short-duration-flow-count {
                                type boolean;
                                default "false";
                                description "Include the short duration flow count";
                            }

                            leaf total-flow-duration {
                                type boolean;
                                default "false";
                                description "Include the total flow duration count";
                            }

                            leaf total-flows-completed-count {
                                type boolean;
                                default "false";
                                description "Include the total of completed flows count";
                            }

                        } // container aa-sub-counters

                        container from-aa-sub-counters {
                            description "Enter the from-aa-sub-counters context";

                            leaf flows-active-count {
                                type boolean;
                                default "false";
                                description "Include the active flows";
                            }

                            leaf flows-admitted-count {
                                type boolean;
                                default "false";
                                description "Include the admitted flows";
                            }

                            leaf flows-denied-count {
                                type boolean;
                                default "false";
                                description "Include the denied flows";
                            }

                            leaf forwarding-class {
                                type boolean;
                                default "false";
                                description "Include forwarding class";
                            }

                            leaf max-throughput-octet-count {
                                type boolean;
                                default "false";
                                description "Include maximum throughput as measured in octet count";
                            }

                            leaf max-throughput-packet-count {
                                type boolean;
                                default "false";
                                description "Include maximum throughput as measured in packet count";
                            }

                            leaf max-throughput-timestamp {
                                type boolean;
                                default "false";
                                description "Include timestamp of the maximum throughput";
                            }

                            leaf octets-admitted-count {
                                type boolean;
                                default "false";
                                description "Include the admitted octets count";
                            }

                            leaf octets-denied-count {
                                type boolean;
                                default "false";
                                description "Include the denied octets count";
                            }

                            leaf packets-admitted-count {
                                type boolean;
                                default "false";
                                description "Include the admitted packets count";
                            }

                            leaf packets-denied-count {
                                type boolean;
                                default "false";
                                description "Include the denied packets count";
                            }

                        } // container from-aa-sub-counters

                        container to-aa-sub-counters {
                            description "Enter the to-aa-sub-counters context";

                            leaf flows-active-count {
                                type boolean;
                                default "false";
                                description "Include the active flows";
                            }

                            leaf flows-admitted-count {
                                type boolean;
                                default "false";
                                description "Include the admitted flows";
                            }

                            leaf flows-denied-count {
                                type boolean;
                                default "false";
                                description "Include the denied flows";
                            }

                            leaf forwarding-class {
                                type boolean;
                                default "false";
                                description "Include forwarding class";
                            }

                            leaf max-throughput-octet-count {
                                type boolean;
                                default "false";
                                description "Include maximum throughput as measured in octet count";
                            }

                            leaf max-throughput-packet-count {
                                type boolean;
                                default "false";
                                description "Include maximum throughput as measured in packet count";
                            }

                            leaf max-throughput-timestamp {
                                type boolean;
                                default "false";
                                description "Include timestamp of the maximum throughput";
                            }

                            leaf octets-admitted-count {
                                type boolean;
                                default "false";
                                description "Include the admitted octets count";
                            }

                            leaf octets-denied-count {
                                type boolean;
                                default "false";
                                description "Include the denied octets count";
                            }

                            leaf packets-admitted-count {
                                type boolean;
                                default "false";
                                description "Include the admitted packets count";
                            }

                            leaf packets-denied-count {
                                type boolean;
                                default "false";
                                description "Include the denied packets count";
                            }

                        } // container to-aa-sub-counters

                    } // container aa-specific

                    list override-counter {
                        status obsolete;
                        key "id";
                        description "Enter the override-counter list instance";

                        leaf id {
                            status obsolete;
                            type uint32 {
                                range "1..8";
                            }
                            description "Override counter ID";
                        }

                        leaf-list apply-groups {
                            status obsolete;
                            type leafref {
                                path "../../../../../groups/group/name";
                            }
                            max-elements 8;
                            ordered-by user;
                            description "Apply a configuration group at this level";
                        }

                        leaf-list apply-groups-exclude {
                            status obsolete;
                            type leafref {
                                path "../../../../../groups/group/name";
                            }
                            max-elements 8;
                            ordered-by user;
                            description "Exclude a configuration group at this level";
                        }

                        container e-counters {
                            status obsolete;
                            description "Enter the e-counters context";

                            leaf in-profile-octets-discarded-count {
                                status obsolete;
                                type boolean;
                                default "false";
                                description "Include the in-profile octets discarded count";
                            }

                            leaf in-profile-octets-forwarded-count {
                                status obsolete;
                                type boolean;
                                default "false";
                                description "Include the in-profile octets forwarded count";
                            }

                            leaf in-profile-packets-discarded-count {
                                status obsolete;
                                type boolean;
                                default "false";
                                description "Include the in-profile packets discarded count";
                            }

                            leaf in-profile-packets-forwarded-count {
                                status obsolete;
                                type boolean;
                                default "false";
                                description "Include the in-profile packets forwarded count";
                            }

                            leaf out-profile-octets-discarded-count {
                                status obsolete;
                                type boolean;
                                default "false";
                                description "Include the out-profile octets discarded count";
                            }

                            leaf out-profile-octets-forwarded-count {
                                status obsolete;
                                type boolean;
                                default "false";
                                description "Include the out-of-profile octets forwarded count";
                            }

                            leaf out-profile-packets-discarded-count {
                                status obsolete;
                                type boolean;
                                default "false";
                                description "Include the out-profile packets discarded count";
                            }

                            leaf out-profile-packets-forwarded-count {
                                status obsolete;
                                type boolean;
                                default "false";
                                description "Include the out-of-profile packets forwarded count";
                            }

                        } // container e-counters

                        container i-counters {
                            status obsolete;
                            description "Enter the i-counters context";

                            leaf all-octets-offered-count {
                                status obsolete;
                                type boolean;
                                default "false";
                                description "Include the all octets offered count";
                            }

                            leaf all-packets-offered-count {
                                status obsolete;
                                type boolean;
                                default "false";
                                description "Include all packets offered count";
                            }

                            leaf high-octets-discarded-count {
                                status obsolete;
                                type boolean;
                                default "false";
                                description "Include the high octets discarded count";
                            }

                            leaf high-packets-discarded-count {
                                status obsolete;
                                type boolean;
                                default "false";
                                description "Include the high packets discarded count";
                            }

                            leaf in-profile-octets-forwarded-count {
                                status obsolete;
                                type boolean;
                                default "false";
                                description "Include the in-profile octets forwarded count";
                            }

                            leaf in-profile-packets-forwarded-count {
                                status obsolete;
                                type boolean;
                                default "false";
                                description "Include the in-profile packets forwarded count";
                            }

                            leaf low-octets-discarded-count {
                                status obsolete;
                                type boolean;
                                default "false";
                                description "Include the low octets discarded count";
                            }

                            leaf low-packets-discarded-count {
                                status obsolete;
                                type boolean;
                                default "false";
                                description "Include the low packets discarded count";
                            }

                            leaf out-profile-octets-forwarded-count {
                                status obsolete;
                                type boolean;
                                default "false";
                                description "Include the out-of-profile octets forwarded count";
                            }

                            leaf out-profile-packets-forwarded-count {
                                status obsolete;
                                type boolean;
                                default "false";
                                description "Include the out-of-profile packets forwarded count";
                            }

                        } // container i-counters

                    } // list override-counter

                    list policer {
                        key "id";
                        description "Enter the policer list instance";

                        leaf id {
                            type uint32 {
                                range "1..63";
                            }
                            description "Policer ID";
                        }

                        leaf-list apply-groups {
                            type leafref {
                                path "../../../../../groups/group/name";
                            }
                            max-elements 8;
                            ordered-by user;
                            description "Apply a configuration group at this level";
                        }

                        leaf-list apply-groups-exclude {
                            type leafref {
                                path "../../../../../groups/group/name";
                            }
                            max-elements 8;
                            ordered-by user;
                            description "Exclude a configuration group at this level";
                        }

                        container e-counters {
                            description "Enter the e-counters context";

                            leaf in-profile-octets-discarded-count {
                                type boolean;
                                default "false";
                                description "Include the in profile octets discarded count";
                            }

                            leaf in-profile-octets-offered-count {
                                type boolean;
                                default "false";
                                description "Include the in profile octets offered count";
                            }

                            leaf in-profile-packets-discarded-count {
                                type boolean;
                                default "false";
                                description "Include the in profile packets discarded count";
                            }

                            leaf in-profile-packets-offered-count {
                                type boolean;
                                default "false";
                                description "Include the in profile packets offered count";
                            }

                            leaf in-profile-octets-forwarded-count {
                                type boolean;
                                default "false";
                                description "Include the in profile octets forwarded count";
                            }

                            leaf in-profile-packets-forwarded-count {
                                type boolean;
                                default "false";
                                description "Include the in profile packets forwarded count";
                            }

                            leaf out-profile-octets-discarded-count {
                                type boolean;
                                default "false";
                                description "Include the out profile octets discarded count";
                            }

                            leaf out-profile-octets-offered-count {
                                type boolean;
                                default "false";
                                description "Include the out profile octets offered count";
                            }

                            leaf out-profile-packets-discarded-count {
                                type boolean;
                                default "false";
                                description "Include the out profile packets discarded count";
                            }

                            leaf out-profile-packets-offered-count {
                                type boolean;
                                default "false";
                                description "Include the out profile packets offered count";
                            }

                            leaf out-profile-octets-forwarded-count {
                                type boolean;
                                default "false";
                                description "Include the out profile octets forwarded count";
                            }

                            leaf out-profile-packets-forwarded-count {
                                type boolean;
                                default "false";
                                description "Include the out profile packets forwarded count";
                            }

                            leaf uncoloured-octets-offered-count {
                                type boolean;
                                default "false";
                                description "Include the uncolored octets offered count";
                            }

                            leaf uncoloured-packets-offered-count {
                                type boolean;
                                default "false";
                                description "Include the uncolored packets offered count";
                            }

                            leaf exceed-profile-octets-discarded-count {
                                type boolean;
                                default "false";
                                description "Include the exceed profile octets discarded count";
                            }

                            leaf exceed-profile-octets-forwarded-count {
                                type boolean;
                                default "false";
                                description "Include the exceed profile octets forwarded count";
                            }

                            leaf exceed-profile-octets-offered-count {
                                type boolean;
                                default "false";
                                description "Include the exceed profile octets offered count";
                            }

                            leaf exceed-profile-packets-discarded-count {
                                type boolean;
                                default "false";
                                description "Include the exceed profile packets discarded count";
                            }

                            leaf exceed-profile-packets-forwarded-count {
                                type boolean;
                                default "false";
                                description "Include the exceed profile packets forwarded count";
                            }

                            leaf exceed-profile-packets-offered-count {
                                type boolean;
                                default "false";
                                description "Include the exceed profile packets offered count";
                            }

                            leaf in-plus-profile-octets-discarded-count {
                                type boolean;
                                default "false";
                                description "Include the in-plus profile octets discarded count";
                            }

                            leaf in-plus-profile-octets-forwarded-count {
                                type boolean;
                                default "false";
                                description "Include the in-plus profile octets forwarded count";
                            }

                            leaf in-plus-profile-octets-offered-count {
                                type boolean;
                                default "false";
                                description "Include the in-plus profile octets offered count";
                            }

                            leaf in-plus-profile-packets-discarded-count {
                                type boolean;
                                default "false";
                                description "Include the in-plus profile packets discarded count";
                            }

                            leaf in-plus-profile-packets-forwarded-count {
                                type boolean;
                                default "false";
                                description "Include the in-plus profile packets forwarded count";
                            }

                            leaf in-plus-profile-packets-offered-count {
                                type boolean;
                                default "false";
                                description "Include the in-plus profile packets offered count";
                            }

                        } // container e-counters

                        container i-counters {
                            description "Enter the i-counters context";

                            leaf in-profile-octets-discarded-count {
                                type boolean;
                                default "false";
                                description "Include the in profile octets discarded count";
                            }

                            leaf in-profile-octets-offered-count {
                                type boolean;
                                default "false";
                                description "Include the in profile octets offered count";
                            }

                            leaf in-profile-packets-discarded-count {
                                type boolean;
                                default "false";
                                description "Include the in profile packets discarded count";
                            }

                            leaf in-profile-packets-offered-count {
                                type boolean;
                                default "false";
                                description "Include the in profile packets offered count";
                            }

                            leaf in-profile-octets-forwarded-count {
                                type boolean;
                                default "false";
                                description "Include the in profile octets forwarded count";
                            }

                            leaf in-profile-packets-forwarded-count {
                                type boolean;
                                default "false";
                                description "Include the in profile packets forwarded count";
                            }

                            leaf out-profile-octets-discarded-count {
                                type boolean;
                                default "false";
                                description "Include the out profile octets discarded count";
                            }

                            leaf out-profile-octets-offered-count {
                                type boolean;
                                default "false";
                                description "Include the out profile octets offered count";
                            }

                            leaf out-profile-packets-discarded-count {
                                type boolean;
                                default "false";
                                description "Include the out profile packets discarded count";
                            }

                            leaf out-profile-packets-offered-count {
                                type boolean;
                                default "false";
                                description "Include the out profile packets offered count";
                            }

                            leaf out-profile-octets-forwarded-count {
                                type boolean;
                                default "false";
                                description "Include the out profile octets forwarded count";
                            }

                            leaf out-profile-packets-forwarded-count {
                                type boolean;
                                default "false";
                                description "Include the out profile packets forwarded count";
                            }

                            leaf uncoloured-octets-offered-count {
                                type boolean;
                                default "false";
                                description "Include the uncolored octets offered count";
                            }

                            leaf uncoloured-packets-offered-count {
                                type boolean;
                                default "false";
                                description "Include the uncolored packets offered count";
                            }

                        } // container i-counters

                    } // list policer

                    list queue {
                        key "id";
                        description "Enter the queue list instance";

                        leaf id {
                            type uint32 {
                                range "1..32";
                            }
                            description "Queue ID for which counters are collected in the record";
                        }

                        leaf-list apply-groups {
                            type leafref {
                                path "../../../../../groups/group/name";
                            }
                            max-elements 8;
                            ordered-by user;
                            description "Apply a configuration group at this level";
                        }

                        leaf-list apply-groups-exclude {
                            type leafref {
                                path "../../../../../groups/group/name";
                            }
                            max-elements 8;
                            ordered-by user;
                            description "Exclude a configuration group at this level";
                        }

                        container e-counters {
                            description "Enter the e-counters context";

                            leaf in-profile-octets-discarded-count {
                                type boolean;
                                default "false";
                                description "Include the in-profile octets discarded count";
                            }

                            leaf in-profile-octets-forwarded-count {
                                type boolean;
                                default "false";
                                description "Include the in-profile octets forwarded count";
                            }

                            leaf in-profile-packets-discarded-count {
                                type boolean;
                                default "false";
                                description "Include the in-profile packets discarded count";
                            }

                            leaf in-profile-packets-forwarded-count {
                                type boolean;
                                default "false";
                                description "Include the in-profile packets forwarded count";
                            }

                            leaf out-profile-octets-discarded-count {
                                type boolean;
                                default "false";
                                description "Include the out-profile octets discarded count";
                            }

                            leaf out-profile-octets-forwarded-count {
                                type boolean;
                                default "false";
                                description "Include the out-of-profile octets forwarded count";
                            }

                            leaf out-profile-packets-discarded-count {
                                type boolean;
                                default "false";
                                description "Include the out-profile packets discarded count";
                            }

                            leaf out-profile-packets-forwarded-count {
                                type boolean;
                                default "false";
                                description "Include the out-of-profile packets forwarded count";
                            }

                        } // container e-counters

                        container i-counters {
                            description "Enter the i-counters context";

                            leaf all-octets-offered-count {
                                type boolean;
                                default "false";
                                description "Include the all octets offered count";
                            }

                            leaf all-packets-offered-count {
                                type boolean;
                                default "false";
                                description "Include all packets offered count";
                            }

                            leaf high-octets-discarded-count {
                                type boolean;
                                default "false";
                                description "Include the high octets discarded count";
                            }

                            leaf high-packets-discarded-count {
                                type boolean;
                                default "false";
                                description "Include the high packets discarded count";
                            }

                            leaf in-profile-octets-forwarded-count {
                                type boolean;
                                default "false";
                                description "Include the in-profile octets forwarded count";
                            }

                            leaf in-profile-packets-forwarded-count {
                                type boolean;
                                default "false";
                                description "Include the in-profile packets forwarded count";
                            }

                            leaf low-octets-discarded-count {
                                type boolean;
                                default "false";
                                description "Include the low octets discarded count";
                            }

                            leaf low-packets-discarded-count {
                                type boolean;
                                default "false";
                                description "Include the low packets discarded count";
                            }

                            leaf out-profile-octets-forwarded-count {
                                type boolean;
                                default "false";
                                description "Include the out-of-profile octets forwarded count";
                            }

                            leaf out-profile-packets-forwarded-count {
                                type boolean;
                                default "false";
                                description "Include the out-of-profile packets forwarded count";
                            }

                            leaf high-octets-offered-count {
                                type boolean;
                                default "false";
                                description "Include the high octets offered count";
                            }

                            leaf high-packets-offered-count {
                                type boolean;
                                default "false";
                                description "Include the high packets offered count";
                            }

                            leaf low-octets-offered-count {
                                type boolean;
                                default "false";
                                description "Include the low octets offered count";
                            }

                            leaf low-packets-offered-count {
                                type boolean;
                                default "false";
                                description "Include the low packets offered count";
                            }

                            leaf uncoloured-octets-offered-count {
                                type boolean;
                                default "false";
                                description "Include the uncolored octets offered count";
                            }

                            leaf uncoloured-packets-offered-count {
                                type boolean;
                                default "false";
                                description "Include the uncolored packets offered count";
                            }

                        } // container i-counters

                    } // list queue

                    container ref-aa-specific-counter {
                        description "Enter the ref-aa-specific-counter context";

                        leaf any {
                            type boolean;
                            default "false";
                            description "Report a change to any counter";
                        }

                    } // container ref-aa-specific-counter

                    container ref-override-counter {
                        status obsolete;
                        description "Enter the ref-override-counter context";

                        choice counter {
                            status obsolete;
                            case id {
                                status obsolete;

                                leaf id {
                                    status obsolete;
                                    type leafref {
                                        path "../../override-counter/id";
                                    }
                                    description "Override counter ID";
                                }

                            }
                            case all {
                                status obsolete;

                                leaf all {
                                    status obsolete;
                                    type empty;
                                    description "Apply significant change for all override counter IDs";
                                }

                            }
                        }
                        container e-counters {
                            status obsolete;
                            description "Enter the e-counters context";

                            leaf in-profile-octets-discarded-count {
                                status obsolete;
                                type boolean;
                                default "false";
                                description "Include the in-profile octets discarded count";
                            }

                            leaf in-profile-octets-forwarded-count {
                                status obsolete;
                                type boolean;
                                default "false";
                                description "Include the in-profile octets forwarded count";
                            }

                            leaf in-profile-packets-discarded-count {
                                status obsolete;
                                type boolean;
                                default "false";
                                description "Include the in-profile packets discarded count";
                            }

                            leaf in-profile-packets-forwarded-count {
                                status obsolete;
                                type boolean;
                                default "false";
                                description "Include the in-profile packets forwarded count";
                            }

                            leaf out-profile-octets-discarded-count {
                                status obsolete;
                                type boolean;
                                default "false";
                                description "Include the out-profile octets discarded count";
                            }

                            leaf out-profile-octets-forwarded-count {
                                status obsolete;
                                type boolean;
                                default "false";
                                description "Include the out-of-profile octets forwarded count";
                            }

                            leaf out-profile-packets-discarded-count {
                                status obsolete;
                                type boolean;
                                default "false";
                                description "Include the out-profile packets discarded count";
                            }

                            leaf out-profile-packets-forwarded-count {
                                status obsolete;
                                type boolean;
                                default "false";
                                description "Include the out-of-profile packets forwarded count";
                            }

                        } // container e-counters

                        container i-counters {
                            status obsolete;
                            description "Enter the i-counters context";

                            leaf all-octets-offered-count {
                                status obsolete;
                                type boolean;
                                default "false";
                                description "Include the all octets offered count";
                            }

                            leaf all-packets-offered-count {
                                status obsolete;
                                type boolean;
                                default "false";
                                description "Include all packets offered count";
                            }

                            leaf high-octets-discarded-count {
                                status obsolete;
                                type boolean;
                                default "false";
                                description "Include the high octets discarded count";
                            }

                            leaf high-packets-discarded-count {
                                status obsolete;
                                type boolean;
                                default "false";
                                description "Include the high packets discarded count";
                            }

                            leaf in-profile-octets-forwarded-count {
                                status obsolete;
                                type boolean;
                                default "false";
                                description "Include the in-profile octets forwarded count";
                            }

                            leaf in-profile-packets-forwarded-count {
                                status obsolete;
                                type boolean;
                                default "false";
                                description "Include the in-profile packets forwarded count";
                            }

                            leaf low-octets-discarded-count {
                                status obsolete;
                                type boolean;
                                default "false";
                                description "Include the low octets discarded count";
                            }

                            leaf low-packets-discarded-count {
                                status obsolete;
                                type boolean;
                                default "false";
                                description "Include the low packets discarded count";
                            }

                            leaf out-profile-octets-forwarded-count {
                                status obsolete;
                                type boolean;
                                default "false";
                                description "Include the out-of-profile octets forwarded count";
                            }

                            leaf out-profile-packets-forwarded-count {
                                status obsolete;
                                type boolean;
                                default "false";
                                description "Include the out-of-profile packets forwarded count";
                            }

                        } // container i-counters

                    } // container ref-override-counter

                    container ref-policer {
                        description "Enter the ref-policer context";

                        choice policer {
                            case id {

                                leaf id {
                                    type leafref {
                                        path "../../policer/id";
                                    }
                                    description "Policer ID";
                                }

                            }
                            case all {

                                leaf all {
                                    type empty;
                                    description "Apply significant change to counters for all policers";
                                }

                            }
                        }
                        container e-counters {
                            description "Enter the e-counters context";

                            leaf in-profile-octets-discarded-count {
                                type boolean;
                                default "false";
                                description "Include the in profile octets discarded count";
                            }

                            leaf in-profile-octets-offered-count {
                                type boolean;
                                default "false";
                                description "Include the in profile octets offered count";
                            }

                            leaf in-profile-packets-discarded-count {
                                type boolean;
                                default "false";
                                description "Include the in profile packets discarded count";
                            }

                            leaf in-profile-packets-offered-count {
                                type boolean;
                                default "false";
                                description "Include the in profile packets offered count";
                            }

                            leaf in-profile-octets-forwarded-count {
                                type boolean;
                                default "false";
                                description "Include the in profile octets forwarded count";
                            }

                            leaf in-profile-packets-forwarded-count {
                                type boolean;
                                default "false";
                                description "Include the in profile packets forwarded count";
                            }

                            leaf out-profile-octets-discarded-count {
                                type boolean;
                                default "false";
                                description "Include the out profile octets discarded count";
                            }

                            leaf out-profile-octets-offered-count {
                                type boolean;
                                default "false";
                                description "Include the out profile octets offered count";
                            }

                            leaf out-profile-packets-discarded-count {
                                type boolean;
                                default "false";
                                description "Include the out profile packets discarded count";
                            }

                            leaf out-profile-packets-offered-count {
                                type boolean;
                                default "false";
                                description "Include the out profile packets offered count";
                            }

                            leaf out-profile-octets-forwarded-count {
                                type boolean;
                                default "false";
                                description "Include the out profile octets forwarded count";
                            }

                            leaf out-profile-packets-forwarded-count {
                                type boolean;
                                default "false";
                                description "Include the out profile packets forwarded count";
                            }

                            leaf uncoloured-octets-offered-count {
                                type boolean;
                                default "false";
                                description "Include the uncolored octets offered count";
                            }

                            leaf uncoloured-packets-offered-count {
                                type boolean;
                                default "false";
                                description "Include the uncolored packets offered count";
                            }

                            leaf exceed-profile-octets-discarded-count {
                                type boolean;
                                default "false";
                                description "Include the exceed profile octets discarded count";
                            }

                            leaf exceed-profile-octets-forwarded-count {
                                type boolean;
                                default "false";
                                description "Include the exceed profile octets forwarded count";
                            }

                            leaf exceed-profile-octets-offered-count {
                                type boolean;
                                default "false";
                                description "Include the exceed profile octets offered count";
                            }

                            leaf exceed-profile-packets-discarded-count {
                                type boolean;
                                default "false";
                                description "Include the exceed profile packets discarded count";
                            }

                            leaf exceed-profile-packets-forwarded-count {
                                type boolean;
                                default "false";
                                description "Include the exceed profile packets forwarded count";
                            }

                            leaf exceed-profile-packets-offered-count {
                                type boolean;
                                default "false";
                                description "Include the exceed profile packets offered count";
                            }

                            leaf in-plus-profile-octets-discarded-count {
                                type boolean;
                                default "false";
                                description "Include the in-plus profile octets discarded count";
                            }

                            leaf in-plus-profile-octets-forwarded-count {
                                type boolean;
                                default "false";
                                description "Include the in-plus profile octets forwarded count";
                            }

                            leaf in-plus-profile-octets-offered-count {
                                type boolean;
                                default "false";
                                description "Include the in-plus profile octets offered count";
                            }

                            leaf in-plus-profile-packets-discarded-count {
                                type boolean;
                                default "false";
                                description "Include the in-plus profile packets discarded count";
                            }

                            leaf in-plus-profile-packets-forwarded-count {
                                type boolean;
                                default "false";
                                description "Include the in-plus profile packets forwarded count";
                            }

                            leaf in-plus-profile-packets-offered-count {
                                type boolean;
                                default "false";
                                description "Include the in-plus profile packets offered count";
                            }

                        } // container e-counters

                        container i-counters {
                            description "Enter the i-counters context";

                            leaf in-profile-octets-discarded-count {
                                type boolean;
                                default "false";
                                description "Include the in profile octets discarded count";
                            }

                            leaf in-profile-octets-offered-count {
                                type boolean;
                                default "false";
                                description "Include the in profile octets offered count";
                            }

                            leaf in-profile-packets-discarded-count {
                                type boolean;
                                default "false";
                                description "Include the in profile packets discarded count";
                            }

                            leaf in-profile-packets-offered-count {
                                type boolean;
                                default "false";
                                description "Include the in profile packets offered count";
                            }

                            leaf in-profile-octets-forwarded-count {
                                type boolean;
                                default "false";
                                description "Include the in profile octets forwarded count";
                            }

                            leaf in-profile-packets-forwarded-count {
                                type boolean;
                                default "false";
                                description "Include the in profile packets forwarded count";
                            }

                            leaf out-profile-octets-discarded-count {
                                type boolean;
                                default "false";
                                description "Include the out profile octets discarded count";
                            }

                            leaf out-profile-octets-offered-count {
                                type boolean;
                                default "false";
                                description "Include the out profile octets offered count";
                            }

                            leaf out-profile-packets-discarded-count {
                                type boolean;
                                default "false";
                                description "Include the out profile packets discarded count";
                            }

                            leaf out-profile-packets-offered-count {
                                type boolean;
                                default "false";
                                description "Include the out profile packets offered count";
                            }

                            leaf out-profile-octets-forwarded-count {
                                type boolean;
                                default "false";
                                description "Include the out profile octets forwarded count";
                            }

                            leaf out-profile-packets-forwarded-count {
                                type boolean;
                                default "false";
                                description "Include the out profile packets forwarded count";
                            }

                            leaf uncoloured-octets-offered-count {
                                type boolean;
                                default "false";
                                description "Include the uncolored octets offered count";
                            }

                            leaf uncoloured-packets-offered-count {
                                type boolean;
                                default "false";
                                description "Include the uncolored packets offered count";
                            }

                        } // container i-counters

                    } // container ref-policer

                    container ref-queue {
                        description "Enter the ref-queue context";

                        choice queue {
                            case id {

                                leaf id {
                                    type leafref {
                                        path "../../queue/id";
                                    }
                                    description "Queue ID";
                                }

                            }
                            case all {

                                leaf all {
                                    type empty;
                                    description "Apply significant change to counters for all queues";
                                }

                            }
                        }
                        container e-counters {
                            description "Enter the e-counters context";

                            leaf in-profile-octets-discarded-count {
                                type boolean;
                                default "false";
                                description "Include the in-profile octets discarded count";
                            }

                            leaf in-profile-octets-forwarded-count {
                                type boolean;
                                default "false";
                                description "Include the in-profile octets forwarded count";
                            }

                            leaf in-profile-packets-discarded-count {
                                type boolean;
                                default "false";
                                description "Include the in-profile packets discarded count";
                            }

                            leaf in-profile-packets-forwarded-count {
                                type boolean;
                                default "false";
                                description "Include the in-profile packets forwarded count";
                            }

                            leaf out-profile-octets-discarded-count {
                                type boolean;
                                default "false";
                                description "Include the out-profile octets discarded count";
                            }

                            leaf out-profile-octets-forwarded-count {
                                type boolean;
                                default "false";
                                description "Include the out-of-profile octets forwarded count";
                            }

                            leaf out-profile-packets-discarded-count {
                                type boolean;
                                default "false";
                                description "Include the out-profile packets discarded count";
                            }

                            leaf out-profile-packets-forwarded-count {
                                type boolean;
                                default "false";
                                description "Include the out-of-profile packets forwarded count";
                            }

                        } // container e-counters

                        container i-counters {
                            description "Enter the i-counters context";

                            leaf all-octets-offered-count {
                                type boolean;
                                default "false";
                                description "Include the all octets offered count";
                            }

                            leaf all-packets-offered-count {
                                type boolean;
                                default "false";
                                description "Include all packets offered count";
                            }

                            leaf high-octets-discarded-count {
                                type boolean;
                                default "false";
                                description "Include the high octets discarded count";
                            }

                            leaf high-packets-discarded-count {
                                type boolean;
                                default "false";
                                description "Include the high packets discarded count";
                            }

                            leaf in-profile-octets-forwarded-count {
                                type boolean;
                                default "false";
                                description "Include the in-profile octets forwarded count";
                            }

                            leaf in-profile-packets-forwarded-count {
                                type boolean;
                                default "false";
                                description "Include the in-profile packets forwarded count";
                            }

                            leaf low-octets-discarded-count {
                                type boolean;
                                default "false";
                                description "Include the low octets discarded count";
                            }

                            leaf low-packets-discarded-count {
                                type boolean;
                                default "false";
                                description "Include the low packets discarded count";
                            }

                            leaf out-profile-octets-forwarded-count {
                                type boolean;
                                default "false";
                                description "Include the out-of-profile octets forwarded count";
                            }

                            leaf out-profile-packets-forwarded-count {
                                type boolean;
                                default "false";
                                description "Include the out-of-profile packets forwarded count";
                            }

                            leaf high-octets-offered-count {
                                type boolean;
                                default "false";
                                description "Include the high octets offered count";
                            }

                            leaf high-packets-offered-count {
                                type boolean;
                                default "false";
                                description "Include the high packets offered count";
                            }

                            leaf low-octets-offered-count {
                                type boolean;
                                default "false";
                                description "Include the low octets offered count";
                            }

                            leaf low-packets-offered-count {
                                type boolean;
                                default "false";
                                description "Include the low packets offered count";
                            }

                            leaf uncoloured-octets-offered-count {
                                type boolean;
                                default "false";
                                description "Include the uncolored octets offered count";
                            }

                            leaf uncoloured-packets-offered-count {
                                type boolean;
                                default "false";
                                description "Include the uncolored packets offered count";
                            }

                        } // container i-counters

                    } // container ref-queue

                } // container custom-record

                container destination {
                    description "Enter the destination context";

                    choice destination {
                        case file {

                            leaf file {
                                type leafref {
                                    path "../../../file/file-policy-name";
                                }
                                sros-ext:immutable;
                                sros-ext:auto-restart-to-modify;
                                description "Unique file identifier when creating a log or accounting file";
                            }

                        }
                        case null {

                            leaf null {
                                type empty;
                                sros-ext:immutable;
                                sros-ext:auto-restart-to-modify;
                                description "Indicate no destination for accounting policy records";
                            }

                        }
                    }
                } // container destination

            } // list accounting-policy

            container app-route-notifications {
                description "Enter the app-route-notifications context";

                leaf cold-start-wait {
                    type uint32 {
                        range "1..300";
                    }
                    description "Time delay before notifying specific CPM applications for available route";
                }

                leaf route-recovery-wait {
                    type uint32 {
                        range "1..100";
                    }
                    description "Time delay before notifying specific CPM applications after route recovery or change";
                }

            } // container app-route-notifications

            container log-events {
                description "Enter the log-events context";

                list adp {
                    key "event";
                    description "Enter the adp list instance";

                    leaf event {
                        type types-log:adp-events;
                        description "Log event as a trigger for one or more EHS handlers";
                    }

                    leaf severity {
                        type enumeration {
                            enum cleared                        { value 1; }
                            enum indeterminate                  { value 2; }
                            enum critical                       { value 3; }
                            enum major                          { value 4; }
                            enum minor                          { value 5; }
                            enum warning                        { value 6; }
                        }
                        description "Severity level associated with event type";
                    }

                    leaf generate {
                        type boolean;
                        description "Generate log events when the event occurs";
                    }

                    leaf throttle {
                        type boolean;
                        description "Throttle log events of this type";
                    }

                    leaf specific-throttle {
                        type boolean;
                        description "Use parameters to throttle the specific event";
                    }

                    leaf specific-throttle-limit {
                        type uint32 {
                            range "1..20000";
                        }
                        description "Throttle limit within which events can be logged";
                    }

                    leaf specific-throttle-interval {
                        type uint32 {
                            range "1..1200";
                        }
                        description "Duration of the event specific throttling interval";
                    }

                    leaf repeat {
                        type boolean;
                        default "false";
                        description "Repeat the log event until the condition is cleared";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                } // list adp

                list anysec {
                    key "event";
                    description "Enter the anysec list instance";

                    leaf event {
                        type types-log:anysec-events;
                        description "ANYSec module event";
                    }

                    leaf severity {
                        type enumeration {
                            enum cleared                        { value 1; }
                            enum indeterminate                  { value 2; }
                            enum critical                       { value 3; }
                            enum major                          { value 4; }
                            enum minor                          { value 5; }
                            enum warning                        { value 6; }
                        }
                        description "Severity level associated with event type";
                    }

                    leaf generate {
                        type boolean;
                        description "Generate log events when the event occurs";
                    }

                    leaf throttle {
                        type boolean;
                        description "Throttle log events of this type";
                    }

                    leaf specific-throttle {
                        type boolean;
                        description "Use parameters to throttle the specific event";
                    }

                    leaf specific-throttle-limit {
                        type uint32 {
                            range "1..20000";
                        }
                        description "Throttle limit within which events can be logged";
                    }

                    leaf specific-throttle-interval {
                        type uint32 {
                            range "1..1200";
                        }
                        description "Duration of the event specific throttling interval";
                    }

                    leaf repeat {
                        type boolean;
                        default "false";
                        description "Repeat the log event until the condition is cleared";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                } // list anysec

                list application-assurance {
                    key "event";
                    description "Enter the application-assurance list instance";

                    leaf event {
                        type types-log:application-assurance-events;
                        description "Log event as a trigger for one or more EHS handlers";
                    }

                    leaf severity {
                        type enumeration {
                            enum cleared                        { value 1; }
                            enum indeterminate                  { value 2; }
                            enum critical                       { value 3; }
                            enum major                          { value 4; }
                            enum minor                          { value 5; }
                            enum warning                        { value 6; }
                        }
                        description "Severity level associated with event type";
                    }

                    leaf generate {
                        type boolean;
                        description "Generate log events when the event occurs";
                    }

                    leaf throttle {
                        type boolean;
                        description "Throttle log events of this type";
                    }

                    leaf specific-throttle {
                        type boolean;
                        description "Use parameters to throttle the specific event";
                    }

                    leaf specific-throttle-limit {
                        type uint32 {
                            range "1..20000";
                        }
                        description "Throttle limit within which events can be logged";
                    }

                    leaf specific-throttle-interval {
                        type uint32 {
                            range "1..1200";
                        }
                        description "Duration of the event specific throttling interval";
                    }

                    leaf repeat {
                        type boolean;
                        default "false";
                        description "Repeat the log event until the condition is cleared";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                } // list application-assurance

                list aps {
                    key "event";
                    description "Enter the aps list instance";

                    leaf event {
                        type types-log:aps-events;
                        description "Log event as a trigger for one or more EHS handlers";
                    }

                    leaf severity {
                        type enumeration {
                            enum cleared                        { value 1; }
                            enum indeterminate                  { value 2; }
                            enum critical                       { value 3; }
                            enum major                          { value 4; }
                            enum minor                          { value 5; }
                            enum warning                        { value 6; }
                        }
                        description "Severity level associated with event type";
                    }

                    leaf generate {
                        type boolean;
                        description "Generate log events when the event occurs";
                    }

                    leaf throttle {
                        type boolean;
                        description "Throttle log events of this type";
                    }

                    leaf specific-throttle {
                        type boolean;
                        description "Use parameters to throttle the specific event";
                    }

                    leaf specific-throttle-limit {
                        type uint32 {
                            range "1..20000";
                        }
                        description "Throttle limit within which events can be logged";
                    }

                    leaf specific-throttle-interval {
                        type uint32 {
                            range "1..1200";
                        }
                        description "Duration of the event specific throttling interval";
                    }

                    leaf repeat {
                        type boolean;
                        default "false";
                        description "Repeat the log event until the condition is cleared";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                } // list aps

                list auto-prov {
                    key "event";
                    description "Enter the auto-prov list instance";

                    leaf event {
                        type types-log:auto-prov-events;
                        description "Log event as a trigger for one or more EHS handlers";
                    }

                    leaf severity {
                        type enumeration {
                            enum cleared                        { value 1; }
                            enum indeterminate                  { value 2; }
                            enum critical                       { value 3; }
                            enum major                          { value 4; }
                            enum minor                          { value 5; }
                            enum warning                        { value 6; }
                        }
                        description "Severity level associated with event type";
                    }

                    leaf generate {
                        type boolean;
                        description "Generate log events when the event occurs";
                    }

                    leaf throttle {
                        type boolean;
                        description "Throttle log events of this type";
                    }

                    leaf specific-throttle {
                        type boolean;
                        description "Use parameters to throttle the specific event";
                    }

                    leaf specific-throttle-limit {
                        type uint32 {
                            range "1..20000";
                        }
                        description "Throttle limit within which events can be logged";
                    }

                    leaf specific-throttle-interval {
                        type uint32 {
                            range "1..1200";
                        }
                        description "Duration of the event specific throttling interval";
                    }

                    leaf repeat {
                        type boolean;
                        default "false";
                        description "Repeat the log event until the condition is cleared";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                } // list auto-prov

                list bfd {
                    key "event";
                    description "Enter the bfd list instance";

                    leaf event {
                        type types-log:bfd-events;
                        description "Log event as a trigger for one or more EHS handlers";
                    }

                    leaf severity {
                        type enumeration {
                            enum cleared                        { value 1; }
                            enum indeterminate                  { value 2; }
                            enum critical                       { value 3; }
                            enum major                          { value 4; }
                            enum minor                          { value 5; }
                            enum warning                        { value 6; }
                        }
                        description "Severity level associated with event type";
                    }

                    leaf generate {
                        type boolean;
                        description "Generate log events when the event occurs";
                    }

                    leaf throttle {
                        type boolean;
                        description "Throttle log events of this type";
                    }

                    leaf specific-throttle {
                        type boolean;
                        description "Use parameters to throttle the specific event";
                    }

                    leaf specific-throttle-limit {
                        type uint32 {
                            range "1..20000";
                        }
                        description "Throttle limit within which events can be logged";
                    }

                    leaf specific-throttle-interval {
                        type uint32 {
                            range "1..1200";
                        }
                        description "Duration of the event specific throttling interval";
                    }

                    leaf repeat {
                        type boolean;
                        default "false";
                        description "Repeat the log event until the condition is cleared";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                } // list bfd

                list bgp {
                    key "event";
                    description "Enter the bgp list instance";

                    leaf event {
                        type types-log:bgp-events;
                        description "Log event as a trigger for one or more EHS handlers";
                    }

                    leaf severity {
                        type enumeration {
                            enum cleared                        { value 1; }
                            enum indeterminate                  { value 2; }
                            enum critical                       { value 3; }
                            enum major                          { value 4; }
                            enum minor                          { value 5; }
                            enum warning                        { value 6; }
                        }
                        description "Severity level associated with event type";
                    }

                    leaf generate {
                        type boolean;
                        description "Generate log events when the event occurs";
                    }

                    leaf throttle {
                        type boolean;
                        description "Throttle log events of this type";
                    }

                    leaf specific-throttle {
                        type boolean;
                        description "Use parameters that throttle this specific event";
                    }

                    leaf specific-throttle-limit {
                        type uint32 {
                            range "1..20000";
                        }
                        description "Throttle limit within which events can be logged";
                    }

                    leaf specific-throttle-interval {
                        type uint32 {
                            range "1..1200";
                        }
                        description "Duration of the event specific throttling interval";
                    }

                    leaf repeat {
                        type boolean;
                        default "false";
                        description "Repeat the log event until the condition is cleared";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                } // list bgp

                list bier {
                    key "event";
                    description "Enter the bier list instance";

                    leaf event {
                        type types-log:bier-events;
                        description "Log event as a trigger for one or more EHS handlers";
                    }

                    leaf severity {
                        type enumeration {
                            enum cleared                        { value 1; }
                            enum indeterminate                  { value 2; }
                            enum critical                       { value 3; }
                            enum major                          { value 4; }
                            enum minor                          { value 5; }
                            enum warning                        { value 6; }
                        }
                        description "Severity level associated with event type";
                    }

                    leaf generate {
                        type boolean;
                        description "Generate log events when the event occurs";
                    }

                    leaf throttle {
                        type boolean;
                        description "Throttle log events of this type";
                    }

                    leaf specific-throttle {
                        type boolean;
                        description "Use parameters to throttle the specific event";
                    }

                    leaf specific-throttle-limit {
                        type uint32 {
                            range "1..20000";
                        }
                        description "Throttle limit within which events can be logged";
                    }

                    leaf specific-throttle-interval {
                        type uint32 {
                            range "1..1200";
                        }
                        description "Duration of the event specific throttling interval";
                    }

                    leaf repeat {
                        type boolean;
                        default "false";
                        description "Repeat the log event until the condition is cleared";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                } // list bier

                list calltrace {
                    key "event";
                    description "Enter the calltrace list instance";

                    leaf event {
                        type types-log:calltrace-events;
                        description "Log event as a trigger for one or more EHS handlers";
                    }

                    leaf severity {
                        type enumeration {
                            enum cleared                        { value 1; }
                            enum indeterminate                  { value 2; }
                            enum critical                       { value 3; }
                            enum major                          { value 4; }
                            enum minor                          { value 5; }
                            enum warning                        { value 6; }
                        }
                        description "Severity level associated with event type";
                    }

                    leaf generate {
                        type boolean;
                        description "Generate log events when the event occurs";
                    }

                    leaf throttle {
                        type boolean;
                        description "Throttle log events of this type";
                    }

                    leaf specific-throttle {
                        type boolean;
                        description "Use parameters to throttle the specific event";
                    }

                    leaf specific-throttle-limit {
                        type uint32 {
                            range "1..20000";
                        }
                        description "Throttle limit within which events can be logged";
                    }

                    leaf specific-throttle-interval {
                        type uint32 {
                            range "1..1200";
                        }
                        description "Duration of the event specific throttling interval";
                    }

                    leaf repeat {
                        type boolean;
                        default "false";
                        description "Repeat the log event until the condition is cleared";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                } // list calltrace

                list cflowd {
                    key "event";
                    description "Enter the cflowd list instance";

                    leaf event {
                        type types-log:cflowd-events;
                        description "Log event as a trigger for one or more EHS handlers";
                    }

                    leaf severity {
                        type enumeration {
                            enum cleared                        { value 1; }
                            enum indeterminate                  { value 2; }
                            enum critical                       { value 3; }
                            enum major                          { value 4; }
                            enum minor                          { value 5; }
                            enum warning                        { value 6; }
                        }
                        description "Severity level associated with event type";
                    }

                    leaf generate {
                        type boolean;
                        description "Generate log events when the event occurs";
                    }

                    leaf throttle {
                        type boolean;
                        description "Throttle log events of this type";
                    }

                    leaf specific-throttle {
                        type boolean;
                        description "Use parameters to throttle the specific event";
                    }

                    leaf specific-throttle-limit {
                        type uint32 {
                            range "1..20000";
                        }
                        description "Throttle limit within which events can be logged";
                    }

                    leaf specific-throttle-interval {
                        type uint32 {
                            range "1..1200";
                        }
                        description "Duration of the event specific throttling interval";
                    }

                    leaf repeat {
                        type boolean;
                        default "false";
                        description "Repeat the log event until the condition is cleared";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                } // list cflowd

                list chassis {
                    key "event";
                    description "Enter the chassis list instance";

                    leaf event {
                        type types-log:chassis-events;
                        description "Log event as a trigger for one or more EHS handlers";
                    }

                    leaf severity {
                        type enumeration {
                            enum cleared                        { value 1; }
                            enum indeterminate                  { value 2; }
                            enum critical                       { value 3; }
                            enum major                          { value 4; }
                            enum minor                          { value 5; }
                            enum warning                        { value 6; }
                        }
                        description "Severity level associated with event type";
                    }

                    leaf generate {
                        type boolean;
                        description "Generate log events when the event occurs";
                    }

                    leaf throttle {
                        type boolean;
                        description "Throttle log events of this type";
                    }

                    leaf specific-throttle {
                        type boolean;
                        description "Use parameters to throttle the specific event";
                    }

                    leaf specific-throttle-limit {
                        type uint32 {
                            range "1..20000";
                        }
                        description "Throttle limit within which events can be logged";
                    }

                    leaf specific-throttle-interval {
                        type uint32 {
                            range "1..1200";
                        }
                        description "Duration of the event specific throttling interval";
                    }

                    leaf repeat {
                        type boolean;
                        default "false";
                        description "Repeat the log event until the condition is cleared";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                } // list chassis

                list debug {
                    key "event";
                    description "Enter the debug list instance";

                    leaf event {
                        type types-log:debug-events;
                        description "Log event as a trigger for one or more EHS handlers";
                    }

                    leaf severity {
                        type enumeration {
                            enum cleared                        { value 1; }
                            enum indeterminate                  { value 2; }
                            enum critical                       { value 3; }
                            enum major                          { value 4; }
                            enum minor                          { value 5; }
                            enum warning                        { value 6; }
                        }
                        description "Severity level associated with event type";
                    }

                    leaf generate {
                        type boolean;
                        description "Generate log events when the event occurs";
                    }

                    leaf throttle {
                        type boolean;
                        description "Throttle log events of this type";
                    }

                    leaf specific-throttle {
                        type boolean;
                        description "Use parameters to throttle the specific event";
                    }

                    leaf specific-throttle-limit {
                        type uint32 {
                            range "1..20000";
                        }
                        description "Throttle limit within which events can be logged";
                    }

                    leaf specific-throttle-interval {
                        type uint32 {
                            range "1..1200";
                        }
                        description "Duration of the event specific throttling interval";
                    }

                    leaf repeat {
                        type boolean;
                        default "false";
                        description "Repeat the log event until the condition is cleared";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                } // list debug

                list dhcp {
                    key "event";
                    description "Enter the dhcp list instance";

                    leaf event {
                        type types-log:dhcp-events;
                        description "Log event as a trigger for one or more EHS handlers";
                    }

                    leaf severity {
                        type enumeration {
                            enum cleared                        { value 1; }
                            enum indeterminate                  { value 2; }
                            enum critical                       { value 3; }
                            enum major                          { value 4; }
                            enum minor                          { value 5; }
                            enum warning                        { value 6; }
                        }
                        description "Severity level associated with event type";
                    }

                    leaf generate {
                        type boolean;
                        description "Generate log events when the event occurs";
                    }

                    leaf throttle {
                        type boolean;
                        description "Throttle log events of this type";
                    }

                    leaf specific-throttle {
                        type boolean;
                        description "Use parameters to throttle the specific event";
                    }

                    leaf specific-throttle-limit {
                        type uint32 {
                            range "1..20000";
                        }
                        description "Throttle limit within which events can be logged";
                    }

                    leaf specific-throttle-interval {
                        type uint32 {
                            range "1..1200";
                        }
                        description "Duration of the event specific throttling interval";
                    }

                    leaf repeat {
                        type boolean;
                        default "false";
                        description "Repeat the log event until the condition is cleared";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                } // list dhcp

                list dhcps {
                    key "event";
                    description "Enter the dhcps list instance";

                    leaf event {
                        type types-log:dhcps-events;
                        description "Log event as a trigger for one or more EHS handlers";
                    }

                    leaf severity {
                        type enumeration {
                            enum cleared                        { value 1; }
                            enum indeterminate                  { value 2; }
                            enum critical                       { value 3; }
                            enum major                          { value 4; }
                            enum minor                          { value 5; }
                            enum warning                        { value 6; }
                        }
                        description "Severity level associated with event type";
                    }

                    leaf generate {
                        type boolean;
                        description "Generate log events when the event occurs";
                    }

                    leaf throttle {
                        type boolean;
                        description "Throttle log events of this type";
                    }

                    leaf specific-throttle {
                        type boolean;
                        description "Use parameters to throttle the specific event";
                    }

                    leaf specific-throttle-limit {
                        type uint32 {
                            range "1..20000";
                        }
                        description "Throttle limit within which events can be logged";
                    }

                    leaf specific-throttle-interval {
                        type uint32 {
                            range "1..1200";
                        }
                        description "Duration of the event specific throttling interval";
                    }

                    leaf repeat {
                        type boolean;
                        default "false";
                        description "Repeat the log event until the condition is cleared";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                } // list dhcps

                list diameter {
                    key "event";
                    description "Enter the diameter list instance";

                    leaf event {
                        type types-log:diameter-events;
                        description "Log event as a trigger for one or more EHS handlers";
                    }

                    leaf severity {
                        type enumeration {
                            enum cleared                        { value 1; }
                            enum indeterminate                  { value 2; }
                            enum critical                       { value 3; }
                            enum major                          { value 4; }
                            enum minor                          { value 5; }
                            enum warning                        { value 6; }
                        }
                        description "Severity level associated with event type";
                    }

                    leaf generate {
                        type boolean;
                        description "Generate log events when the event occurs";
                    }

                    leaf throttle {
                        type boolean;
                        description "Throttle log events of this type";
                    }

                    leaf specific-throttle {
                        type boolean;
                        description "Use parameters to throttle the specific event";
                    }

                    leaf specific-throttle-limit {
                        type uint32 {
                            range "1..20000";
                        }
                        description "Throttle limit within which events can be logged";
                    }

                    leaf specific-throttle-interval {
                        type uint32 {
                            range "1..1200";
                        }
                        description "Duration of the event specific throttling interval";
                    }

                    leaf repeat {
                        type boolean;
                        default "false";
                        description "Repeat the log event until the condition is cleared";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                } // list diameter

                list dot1x {
                    key "event";
                    description "Enter the dot1x list instance";

                    leaf event {
                        type types-log:dot1x-events;
                        description "Events for dynsvc module";
                    }

                    leaf severity {
                        type enumeration {
                            enum cleared                        { value 1; }
                            enum indeterminate                  { value 2; }
                            enum critical                       { value 3; }
                            enum major                          { value 4; }
                            enum minor                          { value 5; }
                            enum warning                        { value 6; }
                        }
                        description "Severity level associated with event type";
                    }

                    leaf generate {
                        type boolean;
                        description "Generate log events when the event occurs";
                    }

                    leaf throttle {
                        type boolean;
                        description "Throttle log events of this type";
                    }

                    leaf specific-throttle {
                        type boolean;
                        description "Use parameters to throttle the specific event";
                    }

                    leaf specific-throttle-limit {
                        type uint32 {
                            range "1..20000";
                        }
                        description "Throttle limit within which events can be logged";
                    }

                    leaf specific-throttle-interval {
                        type uint32 {
                            range "1..1200";
                        }
                        description "Duration of the event specific throttling interval";
                    }

                    leaf repeat {
                        type boolean;
                        default "false";
                        description "Repeat the log event until the condition is cleared";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                } // list dot1x

                list dynsvc {
                    key "event";
                    description "Enter the dynsvc list instance";

                    leaf event {
                        type types-log:dynsvc-events;
                        description "Log event as a trigger for one or more EHS handlers";
                    }

                    leaf severity {
                        type enumeration {
                            enum cleared                        { value 1; }
                            enum indeterminate                  { value 2; }
                            enum critical                       { value 3; }
                            enum major                          { value 4; }
                            enum minor                          { value 5; }
                            enum warning                        { value 6; }
                        }
                        description "Severity level associated with event type";
                    }

                    leaf generate {
                        type boolean;
                        description "Generate log events when the event occurs";
                    }

                    leaf throttle {
                        type boolean;
                        description "Throttle log events of this type";
                    }

                    leaf specific-throttle {
                        type boolean;
                        description "Use parameters to throttle the specific event";
                    }

                    leaf specific-throttle-limit {
                        type uint32 {
                            range "1..20000";
                        }
                        description "Throttle limit within which events can be logged";
                    }

                    leaf specific-throttle-interval {
                        type uint32 {
                            range "1..1200";
                        }
                        description "Duration of the event specific throttling interval";
                    }

                    leaf repeat {
                        type boolean;
                        default "false";
                        description "Repeat the log event until the condition is cleared";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                } // list dynsvc

                list efm-oam {
                    key "event";
                    description "Enter the efm-oam list instance";

                    leaf event {
                        type types-log:efm-oam-events;
                        description "Log event as a trigger for one or more EHS handlers";
                    }

                    leaf severity {
                        type enumeration {
                            enum cleared                        { value 1; }
                            enum indeterminate                  { value 2; }
                            enum critical                       { value 3; }
                            enum major                          { value 4; }
                            enum minor                          { value 5; }
                            enum warning                        { value 6; }
                        }
                        description "Severity level associated with event type";
                    }

                    leaf generate {
                        type boolean;
                        description "Generate log events when the event occurs";
                    }

                    leaf throttle {
                        type boolean;
                        description "Throttle log events of this type";
                    }

                    leaf specific-throttle {
                        type boolean;
                        description "Use parameters to throttle the specific event";
                    }

                    leaf specific-throttle-limit {
                        type uint32 {
                            range "1..20000";
                        }
                        description "Throttle limit within which events can be logged";
                    }

                    leaf specific-throttle-interval {
                        type uint32 {
                            range "1..1200";
                        }
                        description "Duration of the event specific throttling interval";
                    }

                    leaf repeat {
                        type boolean;
                        default "false";
                        description "Repeat the log event until the condition is cleared";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                } // list efm-oam

                list elmi {
                    key "event";
                    description "Enter the elmi list instance";

                    leaf event {
                        type types-log:elmi-events;
                        description "Log event as a trigger for one or more EHS handlers";
                    }

                    leaf severity {
                        type enumeration {
                            enum cleared                        { value 1; }
                            enum indeterminate                  { value 2; }
                            enum critical                       { value 3; }
                            enum major                          { value 4; }
                            enum minor                          { value 5; }
                            enum warning                        { value 6; }
                        }
                        description "Severity level associated with event type";
                    }

                    leaf generate {
                        type boolean;
                        description "Generate log events when the event occurs";
                    }

                    leaf throttle {
                        type boolean;
                        description "Throttle log events of this type";
                    }

                    leaf specific-throttle {
                        type boolean;
                        description "Use parameters to throttle the specific event";
                    }

                    leaf specific-throttle-limit {
                        type uint32 {
                            range "1..20000";
                        }
                        description "Throttle limit within which events can be logged";
                    }

                    leaf specific-throttle-interval {
                        type uint32 {
                            range "1..1200";
                        }
                        description "Duration of the event specific throttling interval";
                    }

                    leaf repeat {
                        type boolean;
                        default "false";
                        description "Repeat the log event until the condition is cleared";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                } // list elmi

                list ering {
                    key "event";
                    description "Enter the ering list instance";

                    leaf event {
                        type types-log:ethring-events;
                        description "Log event as a trigger for one or more EHS handlers";
                    }

                    leaf severity {
                        type enumeration {
                            enum cleared                        { value 1; }
                            enum indeterminate                  { value 2; }
                            enum critical                       { value 3; }
                            enum major                          { value 4; }
                            enum minor                          { value 5; }
                            enum warning                        { value 6; }
                        }
                        description "Severity level associated with event type";
                    }

                    leaf generate {
                        type boolean;
                        description "Generate log events when the event occurs";
                    }

                    leaf throttle {
                        type boolean;
                        description "Throttle log events of this type";
                    }

                    leaf specific-throttle {
                        type boolean;
                        description "Use parameters to throttle the specific event";
                    }

                    leaf specific-throttle-limit {
                        type uint32 {
                            range "1..20000";
                        }
                        description "Throttle limit within which events can be logged";
                    }

                    leaf specific-throttle-interval {
                        type uint32 {
                            range "1..1200";
                        }
                        description "Duration of the event specific throttling interval";
                    }

                    leaf repeat {
                        type boolean;
                        default "false";
                        description "Repeat the log event until the condition is cleared";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                } // list ering

                list eth-cfm {
                    key "event";
                    description "Enter the eth-cfm list instance";

                    leaf event {
                        type types-log:ethcfm-events;
                        description "Log event as a trigger for one or more EHS handlers";
                    }

                    leaf severity {
                        type enumeration {
                            enum cleared                        { value 1; }
                            enum indeterminate                  { value 2; }
                            enum critical                       { value 3; }
                            enum major                          { value 4; }
                            enum minor                          { value 5; }
                            enum warning                        { value 6; }
                        }
                        description "Severity level associated with event type";
                    }

                    leaf generate {
                        type boolean;
                        description "Generate log events when the event occurs";
                    }

                    leaf throttle {
                        type boolean;
                        description "Throttle log events of this type";
                    }

                    leaf specific-throttle {
                        type boolean;
                        description "Use parameters to throttle the specific event";
                    }

                    leaf specific-throttle-limit {
                        type uint32 {
                            range "1..20000";
                        }
                        description "Throttle limit within which events can be logged";
                    }

                    leaf specific-throttle-interval {
                        type uint32 {
                            range "1..1200";
                        }
                        description "Duration of the event specific throttling interval";
                    }

                    leaf repeat {
                        type boolean;
                        default "false";
                        description "Repeat the log event until the condition is cleared";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                } // list eth-cfm

                list etun {
                    key "event";
                    description "Enter the etun list instance";

                    leaf event {
                        type types-log:etun-events;
                        description "Log event as a trigger for one or more EHS handlers";
                    }

                    leaf severity {
                        type enumeration {
                            enum cleared                        { value 1; }
                            enum indeterminate                  { value 2; }
                            enum critical                       { value 3; }
                            enum major                          { value 4; }
                            enum minor                          { value 5; }
                            enum warning                        { value 6; }
                        }
                        description "Severity level associated with event type";
                    }

                    leaf generate {
                        type boolean;
                        description "Generate log events when the event occurs";
                    }

                    leaf throttle {
                        type boolean;
                        description "Throttle log events of this type";
                    }

                    leaf specific-throttle {
                        type boolean;
                        description "Use parameters to throttle the specific event";
                    }

                    leaf specific-throttle-limit {
                        type uint32 {
                            range "1..20000";
                        }
                        description "Throttle limit within which events can be logged";
                    }

                    leaf specific-throttle-interval {
                        type uint32 {
                            range "1..1200";
                        }
                        description "Duration of the event specific throttling interval";
                    }

                    leaf repeat {
                        type boolean;
                        default "false";
                        description "Repeat the log event until the condition is cleared";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                } // list etun

                list filter {
                    key "event";
                    description "Enter the filter list instance";

                    leaf event {
                        type types-log:filter-events;
                        description "Log event as a trigger for one or more EHS handlers";
                    }

                    leaf severity {
                        type enumeration {
                            enum cleared                        { value 1; }
                            enum indeterminate                  { value 2; }
                            enum critical                       { value 3; }
                            enum major                          { value 4; }
                            enum minor                          { value 5; }
                            enum warning                        { value 6; }
                        }
                        description "Severity level associated with event type";
                    }

                    leaf generate {
                        type boolean;
                        description "Generate log events when the event occurs";
                    }

                    leaf throttle {
                        type boolean;
                        description "Throttle log events of this type";
                    }

                    leaf specific-throttle {
                        type boolean;
                        description "Use parameters to throttle the specific event";
                    }

                    leaf specific-throttle-limit {
                        type uint32 {
                            range "1..20000";
                        }
                        description "Throttle limit within which events can be logged";
                    }

                    leaf specific-throttle-interval {
                        type uint32 {
                            range "1..1200";
                        }
                        description "Duration of the event specific throttling interval";
                    }

                    leaf repeat {
                        type boolean;
                        default "false";
                        description "Repeat the log event until the condition is cleared";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                } // list filter

                list gsmp {
                    key "event";
                    description "Enter the gsmp list instance";

                    leaf event {
                        type types-log:gsmp-events;
                        description "Log event as a trigger for one or more EHS handlers";
                    }

                    leaf severity {
                        type enumeration {
                            enum cleared                        { value 1; }
                            enum indeterminate                  { value 2; }
                            enum critical                       { value 3; }
                            enum major                          { value 4; }
                            enum minor                          { value 5; }
                            enum warning                        { value 6; }
                        }
                        description "Severity level associated with event type";
                    }

                    leaf generate {
                        type boolean;
                        description "Generate log events when the event occurs";
                    }

                    leaf throttle {
                        type boolean;
                        description "Throttle log events of this type";
                    }

                    leaf specific-throttle {
                        type boolean;
                        description "Use parameters to throttle the specific event";
                    }

                    leaf specific-throttle-limit {
                        type uint32 {
                            range "1..20000";
                        }
                        description "Throttle limit within which events can be logged";
                    }

                    leaf specific-throttle-interval {
                        type uint32 {
                            range "1..1200";
                        }
                        description "Duration of the event specific throttling interval";
                    }

                    leaf repeat {
                        type boolean;
                        default "false";
                        description "Repeat the log event until the condition is cleared";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                } // list gsmp

                list igmp {
                    key "event";
                    description "Enter the igmp list instance";

                    leaf event {
                        type types-log:igmp-events;
                        description "Log event as a trigger for one or more EHS handlers";
                    }

                    leaf severity {
                        type enumeration {
                            enum cleared                        { value 1; }
                            enum indeterminate                  { value 2; }
                            enum critical                       { value 3; }
                            enum major                          { value 4; }
                            enum minor                          { value 5; }
                            enum warning                        { value 6; }
                        }
                        description "Severity level associated with event type";
                    }

                    leaf generate {
                        type boolean;
                        description "Generate log events when the event occurs";
                    }

                    leaf throttle {
                        type boolean;
                        description "Throttle log events of this type";
                    }

                    leaf specific-throttle {
                        type boolean;
                        description "Use parameters to throttle the specific event";
                    }

                    leaf specific-throttle-limit {
                        type uint32 {
                            range "1..20000";
                        }
                        description "Throttle limit within which events can be logged";
                    }

                    leaf specific-throttle-interval {
                        type uint32 {
                            range "1..1200";
                        }
                        description "Duration of the event specific throttling interval";
                    }

                    leaf repeat {
                        type boolean;
                        default "false";
                        description "Repeat the log event until the condition is cleared";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                } // list igmp

                list igmp-snooping {
                    key "event";
                    description "Enter the igmp-snooping list instance";

                    leaf event {
                        type types-log:igmp-snooping-events;
                        description "Log event as a trigger for one or more EHS handlers";
                    }

                    leaf severity {
                        type enumeration {
                            enum cleared                        { value 1; }
                            enum indeterminate                  { value 2; }
                            enum critical                       { value 3; }
                            enum major                          { value 4; }
                            enum minor                          { value 5; }
                            enum warning                        { value 6; }
                        }
                        description "Severity level associated with event type";
                    }

                    leaf generate {
                        type boolean;
                        description "Generate log events when the event occurs";
                    }

                    leaf throttle {
                        type boolean;
                        description "Throttle log events of this type";
                    }

                    leaf specific-throttle {
                        type boolean;
                        description "Use parameters to throttle the specific event";
                    }

                    leaf specific-throttle-limit {
                        type uint32 {
                            range "1..20000";
                        }
                        description "Throttle limit within which events can be logged";
                    }

                    leaf specific-throttle-interval {
                        type uint32 {
                            range "1..1200";
                        }
                        description "Duration of the event specific throttling interval";
                    }

                    leaf repeat {
                        type boolean;
                        default "false";
                        description "Repeat the log event until the condition is cleared";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                } // list igmp-snooping

                list ip {
                    key "event";
                    description "Enter the ip list instance";

                    leaf event {
                        type types-log:ip-events;
                        description "Log event as a trigger for one or more EHS handlers";
                    }

                    leaf severity {
                        type enumeration {
                            enum cleared                        { value 1; }
                            enum indeterminate                  { value 2; }
                            enum critical                       { value 3; }
                            enum major                          { value 4; }
                            enum minor                          { value 5; }
                            enum warning                        { value 6; }
                        }
                        description "Severity level associated with event type";
                    }

                    leaf generate {
                        type boolean;
                        description "Generate log events when the event occurs";
                    }

                    leaf throttle {
                        type boolean;
                        description "Throttle log events of this type";
                    }

                    leaf specific-throttle {
                        type boolean;
                        description "Use parameters to throttle the specific event";
                    }

                    leaf specific-throttle-limit {
                        type uint32 {
                            range "1..20000";
                        }
                        description "Throttle limit within which events can be logged";
                    }

                    leaf specific-throttle-interval {
                        type uint32 {
                            range "1..1200";
                        }
                        description "Duration of the event specific throttling interval";
                    }

                    leaf repeat {
                        type boolean;
                        default "false";
                        description "Repeat the log event until the condition is cleared";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                } // list ip

                list ipsec {
                    key "event";
                    description "Enter the ipsec list instance";

                    leaf event {
                        type types-log:ipsec-events;
                        description "Log event as a trigger for one or more EHS handlers";
                    }

                    leaf severity {
                        type enumeration {
                            enum cleared                        { value 1; }
                            enum indeterminate                  { value 2; }
                            enum critical                       { value 3; }
                            enum major                          { value 4; }
                            enum minor                          { value 5; }
                            enum warning                        { value 6; }
                        }
                        description "Severity level associated with event type";
                    }

                    leaf generate {
                        type boolean;
                        description "Generate log events when the event occurs";
                    }

                    leaf throttle {
                        type boolean;
                        description "Throttle log events of this type";
                    }

                    leaf specific-throttle {
                        type boolean;
                        description "Use parameters to throttle the specific event";
                    }

                    leaf specific-throttle-limit {
                        type uint32 {
                            range "1..20000";
                        }
                        description "Throttle limit within which events can be logged";
                    }

                    leaf specific-throttle-interval {
                        type uint32 {
                            range "1..1200";
                        }
                        description "Duration of the event specific throttling interval";
                    }

                    leaf repeat {
                        type boolean;
                        default "false";
                        description "Repeat the log event until the condition is cleared";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                } // list ipsec

                list isis {
                    key "event";
                    description "Enter the isis list instance";

                    leaf event {
                        type types-log:isis-events;
                        description "Log event as a trigger for one or more EHS handlers";
                    }

                    leaf severity {
                        type enumeration {
                            enum cleared                        { value 1; }
                            enum indeterminate                  { value 2; }
                            enum critical                       { value 3; }
                            enum major                          { value 4; }
                            enum minor                          { value 5; }
                            enum warning                        { value 6; }
                        }
                        description "Severity level associated with event type";
                    }

                    leaf generate {
                        type boolean;
                        description "Generate log events when the event occurs";
                    }

                    leaf throttle {
                        type boolean;
                        description "Throttle log events of this type";
                    }

                    leaf specific-throttle {
                        type boolean;
                        description "Use parameters to throttle the specific event";
                    }

                    leaf specific-throttle-limit {
                        type uint32 {
                            range "1..20000";
                        }
                        description "Throttle limit within which events can be logged";
                    }

                    leaf specific-throttle-interval {
                        type uint32 {
                            range "1..1200";
                        }
                        description "Duration of the event specific throttling interval";
                    }

                    leaf repeat {
                        type boolean;
                        default "false";
                        description "Repeat the log event until the condition is cleared";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                } // list isis

                list l2tp {
                    key "event";
                    description "Enter the l2tp list instance";

                    leaf event {
                        type types-log:l2tp-events;
                        description "Log event as a trigger for one or more EHS handlers";
                    }

                    leaf severity {
                        type enumeration {
                            enum cleared                        { value 1; }
                            enum indeterminate                  { value 2; }
                            enum critical                       { value 3; }
                            enum major                          { value 4; }
                            enum minor                          { value 5; }
                            enum warning                        { value 6; }
                        }
                        description "Severity level associated with event type";
                    }

                    leaf generate {
                        type boolean;
                        description "Generate log events when the event occurs";
                    }

                    leaf throttle {
                        type boolean;
                        description "Throttle log events of this type";
                    }

                    leaf specific-throttle {
                        type boolean;
                        description "Use parameters to throttle the specific event";
                    }

                    leaf specific-throttle-limit {
                        type uint32 {
                            range "1..20000";
                        }
                        description "Throttle limit within which events can be logged";
                    }

                    leaf specific-throttle-interval {
                        type uint32 {
                            range "1..1200";
                        }
                        description "Duration of the event specific throttling interval";
                    }

                    leaf repeat {
                        type boolean;
                        default "false";
                        description "Repeat the log event until the condition is cleared";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                } // list l2tp

                list lag {
                    key "event";
                    description "Enter the lag list instance";

                    leaf event {
                        type types-log:lag-events;
                        description "Log event as a trigger for one or more EHS handlers";
                    }

                    leaf severity {
                        type enumeration {
                            enum cleared                        { value 1; }
                            enum indeterminate                  { value 2; }
                            enum critical                       { value 3; }
                            enum major                          { value 4; }
                            enum minor                          { value 5; }
                            enum warning                        { value 6; }
                        }
                        description "Severity level associated with event type";
                    }

                    leaf generate {
                        type boolean;
                        description "Generate log events when the event occurs";
                    }

                    leaf throttle {
                        type boolean;
                        description "Throttle log events of this type";
                    }

                    leaf specific-throttle {
                        type boolean;
                        description "Use parameters to throttle the specific event";
                    }

                    leaf specific-throttle-limit {
                        type uint32 {
                            range "1..20000";
                        }
                        description "Throttle limit within which events can be logged";
                    }

                    leaf specific-throttle-interval {
                        type uint32 {
                            range "1..1200";
                        }
                        description "Duration of the event specific throttling interval";
                    }

                    leaf repeat {
                        type boolean;
                        default "false";
                        description "Repeat the log event until the condition is cleared";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                } // list lag

                list ldap {
                    key "event";
                    description "Enter the ldap list instance";

                    leaf event {
                        type types-log:ldap-events;
                        description "Log event as a trigger for one or more EHS handlers";
                    }

                    leaf severity {
                        type enumeration {
                            enum cleared                        { value 1; }
                            enum indeterminate                  { value 2; }
                            enum critical                       { value 3; }
                            enum major                          { value 4; }
                            enum minor                          { value 5; }
                            enum warning                        { value 6; }
                        }
                        description "Severity level associated with event type";
                    }

                    leaf generate {
                        type boolean;
                        description "Generate log events when the event occurs";
                    }

                    leaf throttle {
                        type boolean;
                        description "Throttle log events of this type";
                    }

                    leaf specific-throttle {
                        type boolean;
                        description "Use parameters to throttle the specific event";
                    }

                    leaf specific-throttle-limit {
                        type uint32 {
                            range "1..20000";
                        }
                        description "Throttle limit within which events can be logged";
                    }

                    leaf specific-throttle-interval {
                        type uint32 {
                            range "1..1200";
                        }
                        description "Duration of the event specific throttling interval";
                    }

                    leaf repeat {
                        type boolean;
                        default "false";
                        description "Repeat the log event until the condition is cleared";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                } // list ldap

                list ldp {
                    key "event";
                    description "Enter the ldp list instance";

                    leaf event {
                        type types-log:ldp-events;
                        description "Log event as a trigger for one or more EHS handlers";
                    }

                    leaf severity {
                        type enumeration {
                            enum cleared                        { value 1; }
                            enum indeterminate                  { value 2; }
                            enum critical                       { value 3; }
                            enum major                          { value 4; }
                            enum minor                          { value 5; }
                            enum warning                        { value 6; }
                        }
                        description "Severity level associated with event type";
                    }

                    leaf generate {
                        type boolean;
                        description "Generate log events when the event occurs";
                    }

                    leaf throttle {
                        type boolean;
                        description "Throttle log events of this type";
                    }

                    leaf specific-throttle {
                        type boolean;
                        description "Use parameters to throttle the specific event";
                    }

                    leaf specific-throttle-limit {
                        type uint32 {
                            range "1..20000";
                        }
                        description "Throttle limit within which events can be logged";
                    }

                    leaf specific-throttle-interval {
                        type uint32 {
                            range "1..1200";
                        }
                        description "Duration of the event specific throttling interval";
                    }

                    leaf repeat {
                        type boolean;
                        default "false";
                        description "Repeat the log event until the condition is cleared";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                } // list ldp

                list li {
                    key "event";
                    description "Enter the li list instance";

                    leaf event {
                        type types-log:li-events;
                        description "Log event as a trigger for one or more EHS handlers";
                    }

                    leaf severity {
                        type enumeration {
                            enum cleared                        { value 1; }
                            enum indeterminate                  { value 2; }
                            enum critical                       { value 3; }
                            enum major                          { value 4; }
                            enum minor                          { value 5; }
                            enum warning                        { value 6; }
                        }
                        description "Severity level associated with event type";
                    }

                    leaf generate {
                        type boolean;
                        description "Generate log events when the event occurs";
                    }

                    leaf throttle {
                        type boolean;
                        description "Throttle log events of this type";
                    }

                    leaf specific-throttle {
                        type boolean;
                        description "Use parameters to throttle the specific event";
                    }

                    leaf specific-throttle-limit {
                        type uint32 {
                            range "1..20000";
                        }
                        description "Throttle limit within which events can be logged";
                    }

                    leaf specific-throttle-interval {
                        type uint32 {
                            range "1..1200";
                        }
                        description "Duration of the event specific throttling interval";
                    }

                    leaf repeat {
                        type boolean;
                        default "false";
                        description "Repeat the log event until the condition is cleared";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                } // list li

                list lldp {
                    key "event";
                    description "Enter the lldp list instance";

                    leaf event {
                        type types-log:lldp-events;
                        description "Log event as a trigger for one or more EHS handlers";
                    }

                    leaf severity {
                        type enumeration {
                            enum cleared                        { value 1; }
                            enum indeterminate                  { value 2; }
                            enum critical                       { value 3; }
                            enum major                          { value 4; }
                            enum minor                          { value 5; }
                            enum warning                        { value 6; }
                        }
                        description "Severity level associated with event type";
                    }

                    leaf generate {
                        type boolean;
                        description "Generate log events when the event occurs";
                    }

                    leaf throttle {
                        type boolean;
                        description "Throttle log events of this type";
                    }

                    leaf specific-throttle {
                        type boolean;
                        description "Use parameters to throttle the specific event";
                    }

                    leaf specific-throttle-limit {
                        type uint32 {
                            range "1..20000";
                        }
                        description "Throttle limit within which events can be logged";
                    }

                    leaf specific-throttle-interval {
                        type uint32 {
                            range "1..1200";
                        }
                        description "Duration of the event specific throttling interval";
                    }

                    leaf repeat {
                        type boolean;
                        default "false";
                        description "Repeat the log event until the condition is cleared";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                } // list lldp

                list logger {
                    key "event";
                    description "Enter the logger list instance";

                    leaf event {
                        type types-log:logger-events;
                        description "Log event as a trigger for one or more EHS handlers";
                    }

                    leaf severity {
                        type enumeration {
                            enum cleared                        { value 1; }
                            enum indeterminate                  { value 2; }
                            enum critical                       { value 3; }
                            enum major                          { value 4; }
                            enum minor                          { value 5; }
                            enum warning                        { value 6; }
                        }
                        description "Severity level associated with event type";
                    }

                    leaf generate {
                        type boolean;
                        description "Generate log events when the event occurs";
                    }

                    leaf throttle {
                        type boolean;
                        description "Throttle log events of this type";
                    }

                    leaf specific-throttle {
                        type boolean;
                        description "Use parameters to throttle the specific event";
                    }

                    leaf specific-throttle-limit {
                        type uint32 {
                            range "1..20000";
                        }
                        description "Throttle limit within which events can be logged";
                    }

                    leaf specific-throttle-interval {
                        type uint32 {
                            range "1..1200";
                        }
                        description "Duration of the event specific throttling interval";
                    }

                    leaf repeat {
                        type boolean;
                        default "false";
                        description "Repeat the log event until the condition is cleared";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                } // list logger

                list macsec {
                    key "event";
                    description "Enter the macsec list instance";

                    leaf event {
                        type types-log:macsec-events;
                        description "Log event as a trigger for one or more EHS handlers";
                    }

                    leaf severity {
                        type enumeration {
                            enum cleared                        { value 1; }
                            enum indeterminate                  { value 2; }
                            enum critical                       { value 3; }
                            enum major                          { value 4; }
                            enum minor                          { value 5; }
                            enum warning                        { value 6; }
                        }
                        description "Severity level associated with event type";
                    }

                    leaf generate {
                        type boolean;
                        description "Generate log events when the event occurs";
                    }

                    leaf throttle {
                        type boolean;
                        description "Throttle log events of this type";
                    }

                    leaf specific-throttle {
                        type boolean;
                        description "Use parameters to throttle the specific event";
                    }

                    leaf specific-throttle-limit {
                        type uint32 {
                            range "1..20000";
                        }
                        description "Throttle limit within which events can be logged";
                    }

                    leaf specific-throttle-interval {
                        type uint32 {
                            range "1..1200";
                        }
                        description "Duration of the event specific throttling interval";
                    }

                    leaf repeat {
                        type boolean;
                        default "false";
                        description "Repeat the log event until the condition is cleared";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                } // list macsec

                list mcpath {
                    key "event";
                    description "Enter the mcpath list instance";

                    leaf event {
                        type types-log:mcpath-events;
                        description "Log event as a trigger for one or more EHS handlers";
                    }

                    leaf severity {
                        type enumeration {
                            enum cleared                        { value 1; }
                            enum indeterminate                  { value 2; }
                            enum critical                       { value 3; }
                            enum major                          { value 4; }
                            enum minor                          { value 5; }
                            enum warning                        { value 6; }
                        }
                        description "Severity level associated with event type";
                    }

                    leaf generate {
                        type boolean;
                        description "Generate log events when the event occurs";
                    }

                    leaf throttle {
                        type boolean;
                        description "Throttle log events of this type";
                    }

                    leaf specific-throttle {
                        type boolean;
                        description "Use parameters to throttle the specific event";
                    }

                    leaf specific-throttle-limit {
                        type uint32 {
                            range "1..20000";
                        }
                        description "Throttle limit within which events can be logged";
                    }

                    leaf specific-throttle-interval {
                        type uint32 {
                            range "1..1200";
                        }
                        description "Duration of the event specific throttling interval";
                    }

                    leaf repeat {
                        type boolean;
                        default "false";
                        description "Repeat the log event until the condition is cleared";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                } // list mcpath

                list mc-redundancy {
                    key "event";
                    description "Enter the mc-redundancy list instance";

                    leaf event {
                        type types-log:mc-redundancy-events;
                        description "Log event as a trigger for one or more EHS handlers";
                    }

                    leaf severity {
                        type enumeration {
                            enum cleared                        { value 1; }
                            enum indeterminate                  { value 2; }
                            enum critical                       { value 3; }
                            enum major                          { value 4; }
                            enum minor                          { value 5; }
                            enum warning                        { value 6; }
                        }
                        description "Severity level associated with event type";
                    }

                    leaf generate {
                        type boolean;
                        description "Generate log events when the event occurs";
                    }

                    leaf throttle {
                        type boolean;
                        description "Throttle log events of this type";
                    }

                    leaf specific-throttle {
                        type boolean;
                        description "Use parameters to throttle the specific event";
                    }

                    leaf specific-throttle-limit {
                        type uint32 {
                            range "1..20000";
                        }
                        description "Throttle limit within which events can be logged";
                    }

                    leaf specific-throttle-interval {
                        type uint32 {
                            range "1..1200";
                        }
                        description "Duration of the event specific throttling interval";
                    }

                    leaf repeat {
                        type boolean;
                        default "false";
                        description "Repeat the log event until the condition is cleared";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                } // list mc-redundancy

                list mgmt-core {
                    key "event";
                    description "Enter the mgmt-core list instance";

                    leaf event {
                        type types-log:mgmt-core-events;
                        description "Log event as a trigger for one or more EHS handlers";
                    }

                    leaf severity {
                        type enumeration {
                            enum cleared                        { value 1; }
                            enum indeterminate                  { value 2; }
                            enum critical                       { value 3; }
                            enum major                          { value 4; }
                            enum minor                          { value 5; }
                            enum warning                        { value 6; }
                        }
                        description "Severity level associated with event type";
                    }

                    leaf generate {
                        type boolean;
                        description "Generate log events when the event occurs";
                    }

                    leaf throttle {
                        type boolean;
                        description "Throttle log events of this type";
                    }

                    leaf specific-throttle {
                        type boolean;
                        description "Use parameters to throttle the specific event";
                    }

                    leaf specific-throttle-limit {
                        type uint32 {
                            range "1..20000";
                        }
                        description "Throttle limit within which events can be logged";
                    }

                    leaf specific-throttle-interval {
                        type uint32 {
                            range "1..1200";
                        }
                        description "Duration of the event specific throttling interval";
                    }

                    leaf repeat {
                        type boolean;
                        default "false";
                        description "Repeat the log event until the condition is cleared";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                } // list mgmt-core

                list mirror {
                    key "event";
                    description "Enter the mirror list instance";

                    leaf event {
                        type types-log:mirror-events;
                        description "Log event as a trigger for one or more EHS handlers";
                    }

                    leaf severity {
                        type enumeration {
                            enum cleared                        { value 1; }
                            enum indeterminate                  { value 2; }
                            enum critical                       { value 3; }
                            enum major                          { value 4; }
                            enum minor                          { value 5; }
                            enum warning                        { value 6; }
                        }
                        description "Severity level associated with event type";
                    }

                    leaf generate {
                        type boolean;
                        description "Generate log events when the event occurs";
                    }

                    leaf throttle {
                        type boolean;
                        description "Throttle log events of this type";
                    }

                    leaf specific-throttle {
                        type boolean;
                        description "Use parameters to throttle the specific event";
                    }

                    leaf specific-throttle-limit {
                        type uint32 {
                            range "1..20000";
                        }
                        description "Throttle limit within which events can be logged";
                    }

                    leaf specific-throttle-interval {
                        type uint32 {
                            range "1..1200";
                        }
                        description "Duration of the event specific throttling interval";
                    }

                    leaf repeat {
                        type boolean;
                        default "false";
                        description "Repeat the log event until the condition is cleared";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                } // list mirror

                list mld {
                    key "event";
                    description "Enter the mld list instance";

                    leaf event {
                        type types-log:mld-events;
                        description "Log event as a trigger for one or more EHS handlers";
                    }

                    leaf severity {
                        type enumeration {
                            enum cleared                        { value 1; }
                            enum indeterminate                  { value 2; }
                            enum critical                       { value 3; }
                            enum major                          { value 4; }
                            enum minor                          { value 5; }
                            enum warning                        { value 6; }
                        }
                        description "Severity level associated with event type";
                    }

                    leaf generate {
                        type boolean;
                        description "Generate log events when the event occurs";
                    }

                    leaf throttle {
                        type boolean;
                        description "Throttle log events of this type";
                    }

                    leaf specific-throttle {
                        type boolean;
                        description "Use parameters to throttle the specific event";
                    }

                    leaf specific-throttle-limit {
                        type uint32 {
                            range "1..20000";
                        }
                        description "Throttle limit within which events can be logged";
                    }

                    leaf specific-throttle-interval {
                        type uint32 {
                            range "1..1200";
                        }
                        description "Duration of the event specific throttling interval";
                    }

                    leaf repeat {
                        type boolean;
                        default "false";
                        description "Repeat the log event until the condition is cleared";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                } // list mld

                list mld-snooping {
                    key "event";
                    description "Enter the mld-snooping list instance";

                    leaf event {
                        type types-log:mld-snooping-events;
                        description "Log event as a trigger for one or more EHS handlers";
                    }

                    leaf severity {
                        type enumeration {
                            enum cleared                        { value 1; }
                            enum indeterminate                  { value 2; }
                            enum critical                       { value 3; }
                            enum major                          { value 4; }
                            enum minor                          { value 5; }
                            enum warning                        { value 6; }
                        }
                        description "Severity level associated with event type";
                    }

                    leaf generate {
                        type boolean;
                        description "Generate log events when the event occurs";
                    }

                    leaf throttle {
                        type boolean;
                        description "Throttle log events of this type";
                    }

                    leaf specific-throttle {
                        type boolean;
                        description "Use parameters to throttle the specific event";
                    }

                    leaf specific-throttle-limit {
                        type uint32 {
                            range "1..20000";
                        }
                        description "Throttle limit within which events can be logged";
                    }

                    leaf specific-throttle-interval {
                        type uint32 {
                            range "1..1200";
                        }
                        description "Duration of the event specific throttling interval";
                    }

                    leaf repeat {
                        type boolean;
                        default "false";
                        description "Repeat the log event until the condition is cleared";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                } // list mld-snooping

                list mpls {
                    key "event";
                    description "Enter the mpls list instance";

                    leaf event {
                        type types-log:mpls-events;
                        description "Log event as a trigger for one or more EHS handlers";
                    }

                    leaf severity {
                        type enumeration {
                            enum cleared                        { value 1; }
                            enum indeterminate                  { value 2; }
                            enum critical                       { value 3; }
                            enum major                          { value 4; }
                            enum minor                          { value 5; }
                            enum warning                        { value 6; }
                        }
                        description "Severity level associated with event type";
                    }

                    leaf generate {
                        type boolean;
                        description "Generate log events when the event occurs";
                    }

                    leaf throttle {
                        type boolean;
                        description "Throttle log events of this type";
                    }

                    leaf specific-throttle {
                        type boolean;
                        description "Use parameters to throttle the specific event";
                    }

                    leaf specific-throttle-limit {
                        type uint32 {
                            range "1..20000";
                        }
                        description "Throttle limit within which events can be logged";
                    }

                    leaf specific-throttle-interval {
                        type uint32 {
                            range "1..1200";
                        }
                        description "Duration of the event specific throttling interval";
                    }

                    leaf repeat {
                        type boolean;
                        default "false";
                        description "Repeat the log event until the condition is cleared";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                } // list mpls

                list mpls-tp {
                    key "event";
                    description "Enter the mpls-tp list instance";

                    leaf event {
                        type types-log:mpls-tp-events;
                        description "Log event as a trigger for one or more EHS handlers";
                    }

                    leaf severity {
                        type enumeration {
                            enum cleared                        { value 1; }
                            enum indeterminate                  { value 2; }
                            enum critical                       { value 3; }
                            enum major                          { value 4; }
                            enum minor                          { value 5; }
                            enum warning                        { value 6; }
                        }
                        description "Severity level associated with event type";
                    }

                    leaf generate {
                        type boolean;
                        description "Generate log events when the event occurs";
                    }

                    leaf throttle {
                        type boolean;
                        description "Throttle log events of this type";
                    }

                    leaf specific-throttle {
                        type boolean;
                        description "Use parameters to throttle the specific event";
                    }

                    leaf specific-throttle-limit {
                        type uint32 {
                            range "1..20000";
                        }
                        description "Throttle limit within which events can be logged";
                    }

                    leaf specific-throttle-interval {
                        type uint32 {
                            range "1..1200";
                        }
                        description "Duration of the event specific throttling interval";
                    }

                    leaf repeat {
                        type boolean;
                        default "false";
                        description "Repeat the log event until the condition is cleared";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                } // list mpls-tp

                list msdp {
                    key "event";
                    description "Enter the msdp list instance";

                    leaf event {
                        type types-log:msdp-events;
                        description "Log event as a trigger for one or more EHS handlers";
                    }

                    leaf severity {
                        type enumeration {
                            enum cleared                        { value 1; }
                            enum indeterminate                  { value 2; }
                            enum critical                       { value 3; }
                            enum major                          { value 4; }
                            enum minor                          { value 5; }
                            enum warning                        { value 6; }
                        }
                        description "Severity level associated with event type";
                    }

                    leaf generate {
                        type boolean;
                        description "Generate log events when the event occurs";
                    }

                    leaf throttle {
                        type boolean;
                        description "Throttle log events of this type";
                    }

                    leaf specific-throttle {
                        type boolean;
                        description "Use parameters to throttle the specific event";
                    }

                    leaf specific-throttle-limit {
                        type uint32 {
                            range "1..20000";
                        }
                        description "Throttle limit within which events can be logged";
                    }

                    leaf specific-throttle-interval {
                        type uint32 {
                            range "1..1200";
                        }
                        description "Duration of the event specific throttling interval";
                    }

                    leaf repeat {
                        type boolean;
                        default "false";
                        description "Repeat the log event until the condition is cleared";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                } // list msdp

                list nat {
                    key "event";
                    description "Enter the nat list instance";

                    leaf event {
                        type types-log:nat-events;
                        description "Log event as a trigger for one or more EHS handlers";
                    }

                    leaf severity {
                        type enumeration {
                            enum cleared                        { value 1; }
                            enum indeterminate                  { value 2; }
                            enum critical                       { value 3; }
                            enum major                          { value 4; }
                            enum minor                          { value 5; }
                            enum warning                        { value 6; }
                        }
                        description "Severity level associated with event type";
                    }

                    leaf generate {
                        type boolean;
                        description "Generate log events when the event occurs";
                    }

                    leaf throttle {
                        type boolean;
                        description "Throttle log events of this type";
                    }

                    leaf specific-throttle {
                        type boolean;
                        description "Use parameters to throttle the specific event";
                    }

                    leaf specific-throttle-limit {
                        type uint32 {
                            range "1..20000";
                        }
                        description "Throttle limit within which events can be logged";
                    }

                    leaf specific-throttle-interval {
                        type uint32 {
                            range "1..1200";
                        }
                        description "Duration of the event specific throttling interval";
                    }

                    leaf repeat {
                        type boolean;
                        default "false";
                        description "Repeat the log event until the condition is cleared";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                } // list nat

                list ntp {
                    key "event";
                    description "Enter the ntp list instance";

                    leaf event {
                        type types-log:ntp-events;
                        description "Log event as a trigger for one or more EHS handlers";
                    }

                    leaf severity {
                        type enumeration {
                            enum cleared                        { value 1; }
                            enum indeterminate                  { value 2; }
                            enum critical                       { value 3; }
                            enum major                          { value 4; }
                            enum minor                          { value 5; }
                            enum warning                        { value 6; }
                        }
                        description "Severity level associated with event type";
                    }

                    leaf generate {
                        type boolean;
                        description "Generate log events when the event occurs";
                    }

                    leaf throttle {
                        type boolean;
                        description "Throttle log events of this type";
                    }

                    leaf specific-throttle {
                        type boolean;
                        description "Use parameters to throttle the specific event";
                    }

                    leaf specific-throttle-limit {
                        type uint32 {
                            range "1..20000";
                        }
                        description "Throttle limit within which events can be logged";
                    }

                    leaf specific-throttle-interval {
                        type uint32 {
                            range "1..1200";
                        }
                        description "Duration of the event specific throttling interval";
                    }

                    leaf repeat {
                        type boolean;
                        default "false";
                        description "Repeat the log event until the condition is cleared";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                } // list ntp

                list oam {
                    key "event";
                    description "Enter the oam list instance";

                    leaf event {
                        type types-log:oam-events;
                        description "Log event as a trigger for one or more EHS handlers";
                    }

                    leaf severity {
                        type enumeration {
                            enum cleared                        { value 1; }
                            enum indeterminate                  { value 2; }
                            enum critical                       { value 3; }
                            enum major                          { value 4; }
                            enum minor                          { value 5; }
                            enum warning                        { value 6; }
                        }
                        description "Severity level associated with event type";
                    }

                    leaf generate {
                        type boolean;
                        description "Generate log events when the event occurs";
                    }

                    leaf throttle {
                        type boolean;
                        description "Throttle log events of this type";
                    }

                    leaf specific-throttle {
                        type boolean;
                        description "Use parameters to throttle the specific event";
                    }

                    leaf specific-throttle-limit {
                        type uint32 {
                            range "1..20000";
                        }
                        description "Throttle limit within which events can be logged";
                    }

                    leaf specific-throttle-interval {
                        type uint32 {
                            range "1..1200";
                        }
                        description "Duration of the event specific throttling interval";
                    }

                    leaf repeat {
                        type boolean;
                        default "false";
                        description "Repeat the log event until the condition is cleared";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                } // list oam

                list openflow {
                    key "event";
                    description "Enter the openflow list instance";

                    leaf event {
                        type types-log:openflow-events;
                        description "Log event as a trigger for one or more EHS handlers";
                    }

                    leaf severity {
                        type enumeration {
                            enum cleared                        { value 1; }
                            enum indeterminate                  { value 2; }
                            enum critical                       { value 3; }
                            enum major                          { value 4; }
                            enum minor                          { value 5; }
                            enum warning                        { value 6; }
                        }
                        description "Severity level associated with event type";
                    }

                    leaf generate {
                        type boolean;
                        description "Generate log events when the event occurs";
                    }

                    leaf throttle {
                        type boolean;
                        description "Throttle log events of this type";
                    }

                    leaf specific-throttle {
                        type boolean;
                        description "Use parameters to throttle the specific event";
                    }

                    leaf specific-throttle-limit {
                        type uint32 {
                            range "1..20000";
                        }
                        description "Throttle limit within which events can be logged";
                    }

                    leaf specific-throttle-interval {
                        type uint32 {
                            range "1..1200";
                        }
                        description "Duration of the event specific throttling interval";
                    }

                    leaf repeat {
                        type boolean;
                        default "false";
                        description "Repeat the log event until the condition is cleared";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                } // list openflow

                list ospf {
                    key "event";
                    description "Enter the ospf list instance";

                    leaf event {
                        type types-log:ospf-events;
                        description "Log event as a trigger for one or more EHS handlers";
                    }

                    leaf severity {
                        type enumeration {
                            enum cleared                        { value 1; }
                            enum indeterminate                  { value 2; }
                            enum critical                       { value 3; }
                            enum major                          { value 4; }
                            enum minor                          { value 5; }
                            enum warning                        { value 6; }
                        }
                        description "Severity level associated with event type";
                    }

                    leaf generate {
                        type boolean;
                        description "Generate log events when the event occurs";
                    }

                    leaf throttle {
                        type boolean;
                        description "Throttle log events of this type";
                    }

                    leaf specific-throttle {
                        type boolean;
                        description "Use parameters to throttle the specific event";
                    }

                    leaf specific-throttle-limit {
                        type uint32 {
                            range "1..20000";
                        }
                        description "Throttle limit within which events can be logged";
                    }

                    leaf specific-throttle-interval {
                        type uint32 {
                            range "1..1200";
                        }
                        description "Duration of the event specific throttling interval";
                    }

                    leaf repeat {
                        type boolean;
                        default "false";
                        description "Repeat the log event until the condition is cleared";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                } // list ospf

                list pcap {
                    key "event";
                    description "Enter the pcap list instance";

                    leaf event {
                        type types-log:pcap-events;
                        description "Log event as a trigger for one or more EHS handlers";
                    }

                    leaf severity {
                        type enumeration {
                            enum cleared                        { value 1; }
                            enum indeterminate                  { value 2; }
                            enum critical                       { value 3; }
                            enum major                          { value 4; }
                            enum minor                          { value 5; }
                            enum warning                        { value 6; }
                        }
                        description "Severity level associated with event type";
                    }

                    leaf generate {
                        type boolean;
                        description "Generate log events when the event occurs";
                    }

                    leaf throttle {
                        type boolean;
                        description "Throttle log events of this type";
                    }

                    leaf specific-throttle {
                        type boolean;
                        description "Use parameters to throttle the specific event";
                    }

                    leaf specific-throttle-limit {
                        type uint32 {
                            range "1..20000";
                        }
                        description "Throttle limit within which events can be logged";
                    }

                    leaf specific-throttle-interval {
                        type uint32 {
                            range "1..1200";
                        }
                        description "Duration of the event specific throttling interval";
                    }

                    leaf repeat {
                        type boolean;
                        default "false";
                        description "Repeat the log event until the condition is cleared";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                } // list pcap

                list pcep {
                    key "event";
                    description "Enter the pcep list instance";

                    leaf event {
                        type types-log:pcep-events;
                        description "PCEP module events";
                    }

                    leaf severity {
                        type enumeration {
                            enum cleared                        { value 1; }
                            enum indeterminate                  { value 2; }
                            enum critical                       { value 3; }
                            enum major                          { value 4; }
                            enum minor                          { value 5; }
                            enum warning                        { value 6; }
                        }
                        description "Severity level associated with event type";
                    }

                    leaf generate {
                        type boolean;
                        description "Generate log events when the event occurs";
                    }

                    leaf throttle {
                        type boolean;
                        description "Throttle log events of this type";
                    }

                    leaf specific-throttle {
                        type boolean;
                        description "Use parameters to throttle the specific event";
                    }

                    leaf specific-throttle-limit {
                        type uint32 {
                            range "1..20000";
                        }
                        description "Throttle limit within which events can be logged";
                    }

                    leaf specific-throttle-interval {
                        type uint32 {
                            range "1..1200";
                        }
                        description "Duration of the event specific throttling interval";
                    }

                    leaf repeat {
                        type boolean;
                        default "false";
                        description "Repeat the log event until the condition is cleared";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                } // list pcep

                list pfcp {
                    key "event";
                    description "Enter the pfcp list instance";

                    leaf event {
                        type types-log:pfcp-events;
                        description "PFCP events";
                    }

                    leaf severity {
                        type enumeration {
                            enum cleared                        { value 1; }
                            enum indeterminate                  { value 2; }
                            enum critical                       { value 3; }
                            enum major                          { value 4; }
                            enum minor                          { value 5; }
                            enum warning                        { value 6; }
                        }
                        description "Severity level associated with event type";
                    }

                    leaf generate {
                        type boolean;
                        description "Generate log events when the event occurs";
                    }

                    leaf throttle {
                        type boolean;
                        description "Throttle log events of this type";
                    }

                    leaf specific-throttle {
                        type boolean;
                        description "Use parameters to throttle the specific event";
                    }

                    leaf specific-throttle-limit {
                        type uint32 {
                            range "1..20000";
                        }
                        description "Throttle limit within which events can be logged";
                    }

                    leaf specific-throttle-interval {
                        type uint32 {
                            range "1..1200";
                        }
                        description "Duration of the event specific throttling interval";
                    }

                    leaf repeat {
                        type boolean;
                        default "false";
                        description "Repeat the log event until the condition is cleared";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                } // list pfcp

                list pim {
                    key "event";
                    description "Enter the pim list instance";

                    leaf event {
                        type types-log:pim-events;
                        description "Log event as a trigger for one or more EHS handlers";
                    }

                    leaf severity {
                        type enumeration {
                            enum cleared                        { value 1; }
                            enum indeterminate                  { value 2; }
                            enum critical                       { value 3; }
                            enum major                          { value 4; }
                            enum minor                          { value 5; }
                            enum warning                        { value 6; }
                        }
                        description "Severity level associated with event type";
                    }

                    leaf generate {
                        type boolean;
                        description "Generate log events when the event occurs";
                    }

                    leaf throttle {
                        type boolean;
                        description "Throttle log events of this type";
                    }

                    leaf specific-throttle {
                        type boolean;
                        description "Use parameters to throttle the specific event";
                    }

                    leaf specific-throttle-limit {
                        type uint32 {
                            range "1..20000";
                        }
                        description "Throttle limit within which events can be logged";
                    }

                    leaf specific-throttle-interval {
                        type uint32 {
                            range "1..1200";
                        }
                        description "Duration of the event specific throttling interval";
                    }

                    leaf repeat {
                        type boolean;
                        default "false";
                        description "Repeat the log event until the condition is cleared";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                } // list pim

                list pim-snooping {
                    key "event";
                    description "Enter the pim-snooping list instance";

                    leaf event {
                        type types-log:pim-snooping-events;
                        description "Log event as a trigger for one or more EHS handlers";
                    }

                    leaf severity {
                        type enumeration {
                            enum cleared                        { value 1; }
                            enum indeterminate                  { value 2; }
                            enum critical                       { value 3; }
                            enum major                          { value 4; }
                            enum minor                          { value 5; }
                            enum warning                        { value 6; }
                        }
                        description "Severity level associated with event type";
                    }

                    leaf generate {
                        type boolean;
                        description "Generate log events when the event occurs";
                    }

                    leaf throttle {
                        type boolean;
                        description "Throttle log events of this type";
                    }

                    leaf specific-throttle {
                        type boolean;
                        description "Use parameters to throttle the specific event";
                    }

                    leaf specific-throttle-limit {
                        type uint32 {
                            range "1..20000";
                        }
                        description "Throttle limit within which events can be logged";
                    }

                    leaf specific-throttle-interval {
                        type uint32 {
                            range "1..1200";
                        }
                        description "Duration of the event specific throttling interval";
                    }

                    leaf repeat {
                        type boolean;
                        default "false";
                        description "Repeat the log event until the condition is cleared";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                } // list pim-snooping

                list port {
                    key "event";
                    description "Enter the port list instance";

                    leaf event {
                        type types-log:port-events;
                        description "Log event as a trigger for one or more EHS handlers";
                    }

                    leaf severity {
                        type enumeration {
                            enum cleared                        { value 1; }
                            enum indeterminate                  { value 2; }
                            enum critical                       { value 3; }
                            enum major                          { value 4; }
                            enum minor                          { value 5; }
                            enum warning                        { value 6; }
                        }
                        description "Severity level associated with event type";
                    }

                    leaf generate {
                        type boolean;
                        description "Generate log events when the event occurs";
                    }

                    leaf throttle {
                        type boolean;
                        description "Throttle log events of this type";
                    }

                    leaf specific-throttle {
                        type boolean;
                        description "Use parameters that throttle this specific event";
                    }

                    leaf specific-throttle-limit {
                        type uint32 {
                            range "1..20000";
                        }
                        description "Throttle limit within which events can be logged";
                    }

                    leaf specific-throttle-interval {
                        type uint32 {
                            range "1..1200";
                        }
                        description "Duration of the event specific throttling interval";
                    }

                    leaf repeat {
                        type boolean;
                        default "false";
                        description "Repeat the log event until the condition is cleared";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                } // list port

                list pppoe {
                    key "event";
                    description "Enter the pppoe list instance";

                    leaf event {
                        type types-log:pppoe-events;
                        description "Log event as a trigger for one or more EHS handlers";
                    }

                    leaf severity {
                        type enumeration {
                            enum cleared                        { value 1; }
                            enum indeterminate                  { value 2; }
                            enum critical                       { value 3; }
                            enum major                          { value 4; }
                            enum minor                          { value 5; }
                            enum warning                        { value 6; }
                        }
                        description "Severity level associated with event type";
                    }

                    leaf generate {
                        type boolean;
                        description "Generate log events when the event occurs";
                    }

                    leaf throttle {
                        type boolean;
                        description "Throttle log events of this type";
                    }

                    leaf specific-throttle {
                        type boolean;
                        description "Use parameters to throttle the specific event";
                    }

                    leaf specific-throttle-limit {
                        type uint32 {
                            range "1..20000";
                        }
                        description "Throttle limit within which events can be logged";
                    }

                    leaf specific-throttle-interval {
                        type uint32 {
                            range "1..1200";
                        }
                        description "Duration of the event specific throttling interval";
                    }

                    leaf repeat {
                        type boolean;
                        default "false";
                        description "Repeat the log event until the condition is cleared";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                } // list pppoe

                list pppoe-clnt {
                    key "event";
                    description "Enter the pppoe-clnt list instance";

                    leaf event {
                        type types-log:pppoe-clnt-events;
                        description "Log event as a trigger for one or more EHS handlers";
                    }

                    leaf severity {
                        type enumeration {
                            enum cleared                        { value 1; }
                            enum indeterminate                  { value 2; }
                            enum critical                       { value 3; }
                            enum major                          { value 4; }
                            enum minor                          { value 5; }
                            enum warning                        { value 6; }
                        }
                        description "Severity level associated with event type";
                    }

                    leaf generate {
                        type boolean;
                        description "Generate log events when the event occurs";
                    }

                    leaf throttle {
                        type boolean;
                        description "Throttle log events of this type";
                    }

                    leaf specific-throttle {
                        type boolean;
                        description "Use parameters to throttle the specific event";
                    }

                    leaf specific-throttle-limit {
                        type uint32 {
                            range "1..20000";
                        }
                        description "Throttle limit within which events can be logged";
                    }

                    leaf specific-throttle-interval {
                        type uint32 {
                            range "1..1200";
                        }
                        description "Duration of the event specific throttling interval";
                    }

                    leaf repeat {
                        type boolean;
                        default "false";
                        description "Repeat the log event until the condition is cleared";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                } // list pppoe-clnt

                list ptp {
                    key "event";
                    description "Enter the ptp list instance";

                    leaf event {
                        type types-log:ptp-events;
                        description "Log event as a trigger for one or more EHS handlers";
                    }

                    leaf severity {
                        type enumeration {
                            enum cleared                        { value 1; }
                            enum indeterminate                  { value 2; }
                            enum critical                       { value 3; }
                            enum major                          { value 4; }
                            enum minor                          { value 5; }
                            enum warning                        { value 6; }
                        }
                        description "Severity level associated with event type";
                    }

                    leaf generate {
                        type boolean;
                        description "Generate log events when the event occurs";
                    }

                    leaf throttle {
                        type boolean;
                        description "Throttle log events of this type";
                    }

                    leaf specific-throttle {
                        type boolean;
                        description "Use parameters to throttle the specific event";
                    }

                    leaf specific-throttle-limit {
                        type uint32 {
                            range "1..20000";
                        }
                        description "Throttle limit within which events can be logged";
                    }

                    leaf specific-throttle-interval {
                        type uint32 {
                            range "1..1200";
                        }
                        description "Duration of the event specific throttling interval";
                    }

                    leaf repeat {
                        type boolean;
                        default "false";
                        description "Repeat the log event until the condition is cleared";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                } // list ptp

                list python {
                    key "event";
                    description "Enter the python list instance";

                    leaf event {
                        type types-log:python-events;
                        description "Python module events";
                    }

                    leaf severity {
                        type enumeration {
                            enum cleared                        { value 1; }
                            enum indeterminate                  { value 2; }
                            enum critical                       { value 3; }
                            enum major                          { value 4; }
                            enum minor                          { value 5; }
                            enum warning                        { value 6; }
                        }
                        description "Severity level associated with event type";
                    }

                    leaf generate {
                        type boolean;
                        description "Generate log events when the event occurs";
                    }

                    leaf throttle {
                        type boolean;
                        description "Throttle log events of this type";
                    }

                    leaf specific-throttle {
                        type boolean;
                        description "Use parameters to throttle the specific event";
                    }

                    leaf specific-throttle-limit {
                        type uint32 {
                            range "1..20000";
                        }
                        description "Throttle limit within which events can be logged";
                    }

                    leaf specific-throttle-interval {
                        type uint32 {
                            range "1..1200";
                        }
                        description "Duration of the event specific throttling interval";
                    }

                    leaf repeat {
                        type boolean;
                        default "false";
                        description "Repeat the log event until the condition is cleared";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                } // list python

                list radius {
                    key "event";
                    description "Enter the radius list instance";

                    leaf event {
                        type types-log:radius-events;
                        description "Log event as a trigger for one or more EHS handlers";
                    }

                    leaf severity {
                        type enumeration {
                            enum cleared                        { value 1; }
                            enum indeterminate                  { value 2; }
                            enum critical                       { value 3; }
                            enum major                          { value 4; }
                            enum minor                          { value 5; }
                            enum warning                        { value 6; }
                        }
                        description "Severity level associated with event type";
                    }

                    leaf generate {
                        type boolean;
                        description "Generate log events when the event occurs";
                    }

                    leaf throttle {
                        type boolean;
                        description "Throttle log events of this type";
                    }

                    leaf specific-throttle {
                        type boolean;
                        description "Use parameters to throttle the specific event";
                    }

                    leaf specific-throttle-limit {
                        type uint32 {
                            range "1..20000";
                        }
                        description "Throttle limit within which events can be logged";
                    }

                    leaf specific-throttle-interval {
                        type uint32 {
                            range "1..1200";
                        }
                        description "Duration of the event specific throttling interval";
                    }

                    leaf repeat {
                        type boolean;
                        default "false";
                        description "Repeat the log event until the condition is cleared";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                } // list radius

                list rip {
                    key "event";
                    description "Enter the rip list instance";

                    leaf event {
                        type types-log:rip-events;
                        description "Log event as a trigger for one or more EHS handlers";
                    }

                    leaf severity {
                        type enumeration {
                            enum cleared                        { value 1; }
                            enum indeterminate                  { value 2; }
                            enum critical                       { value 3; }
                            enum major                          { value 4; }
                            enum minor                          { value 5; }
                            enum warning                        { value 6; }
                        }
                        description "Severity level associated with event type";
                    }

                    leaf generate {
                        type boolean;
                        description "Generate log events when the event occurs";
                    }

                    leaf throttle {
                        type boolean;
                        description "Throttle log events of this type";
                    }

                    leaf specific-throttle {
                        type boolean;
                        description "Use parameters to throttle the specific event";
                    }

                    leaf specific-throttle-limit {
                        type uint32 {
                            range "1..20000";
                        }
                        description "Throttle limit within which events can be logged";
                    }

                    leaf specific-throttle-interval {
                        type uint32 {
                            range "1..1200";
                        }
                        description "Duration of the event specific throttling interval";
                    }

                    leaf repeat {
                        type boolean;
                        default "false";
                        description "Repeat the log event until the condition is cleared";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                } // list rip

                list ripng {
                    key "event";
                    description "Enter the ripng list instance";

                    leaf event {
                        type types-log:ripng-events;
                        description "Log event as a trigger for one or more EHS handlers";
                    }

                    leaf severity {
                        type enumeration {
                            enum cleared                        { value 1; }
                            enum indeterminate                  { value 2; }
                            enum critical                       { value 3; }
                            enum major                          { value 4; }
                            enum minor                          { value 5; }
                            enum warning                        { value 6; }
                        }
                        description "Severity level associated with event type";
                    }

                    leaf generate {
                        type boolean;
                        description "Generate log events when the event occurs";
                    }

                    leaf throttle {
                        type boolean;
                        description "Throttle log events of this type";
                    }

                    leaf specific-throttle {
                        type boolean;
                        description "Use parameters to throttle the specific event";
                    }

                    leaf specific-throttle-limit {
                        type uint32 {
                            range "1..20000";
                        }
                        description "Throttle limit within which events can be logged";
                    }

                    leaf specific-throttle-interval {
                        type uint32 {
                            range "1..1200";
                        }
                        description "Duration of the event specific throttling interval";
                    }

                    leaf repeat {
                        type boolean;
                        default "false";
                        description "Repeat the log event until the condition is cleared";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                } // list ripng

                list route-policy {
                    key "event";
                    description "Enter the route-policy list instance";

                    leaf event {
                        type types-log:route-policy-events;
                        description "Log event as a trigger for one or more EHS handlers";
                    }

                    leaf severity {
                        type enumeration {
                            enum cleared                        { value 1; }
                            enum indeterminate                  { value 2; }
                            enum critical                       { value 3; }
                            enum major                          { value 4; }
                            enum minor                          { value 5; }
                            enum warning                        { value 6; }
                        }
                        description "Severity level associated with event type";
                    }

                    leaf generate {
                        type boolean;
                        description "Generate log events when the event occurs";
                    }

                    leaf throttle {
                        type boolean;
                        description "Throttle log events of this type";
                    }

                    leaf specific-throttle {
                        type boolean;
                        description "Use parameters to throttle the specific event";
                    }

                    leaf specific-throttle-limit {
                        type uint32 {
                            range "1..20000";
                        }
                        description "Throttle limit within which events can be logged";
                    }

                    leaf specific-throttle-interval {
                        type uint32 {
                            range "1..1200";
                        }
                        description "Duration of the event specific throttling interval";
                    }

                    leaf repeat {
                        type boolean;
                        default "false";
                        description "Repeat the log event until the condition is cleared";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                } // list route-policy

                list rpki {
                    key "event";
                    description "Enter the rpki list instance";

                    leaf event {
                        type types-log:rpki-events;
                        description "Log event as a trigger for one or more EHS handlers";
                    }

                    leaf severity {
                        type enumeration {
                            enum cleared                        { value 1; }
                            enum indeterminate                  { value 2; }
                            enum critical                       { value 3; }
                            enum major                          { value 4; }
                            enum minor                          { value 5; }
                            enum warning                        { value 6; }
                        }
                        description "Severity level associated with event type";
                    }

                    leaf generate {
                        type boolean;
                        description "Generate log events when the event occurs";
                    }

                    leaf throttle {
                        type boolean;
                        description "Throttle log events of this type";
                    }

                    leaf specific-throttle {
                        type boolean;
                        description "Use parameters to throttle the specific event";
                    }

                    leaf specific-throttle-limit {
                        type uint32 {
                            range "1..20000";
                        }
                        description "Throttle limit within which events can be logged";
                    }

                    leaf specific-throttle-interval {
                        type uint32 {
                            range "1..1200";
                        }
                        description "Duration of the event specific throttling interval";
                    }

                    leaf repeat {
                        type boolean;
                        default "false";
                        description "Repeat the log event until the condition is cleared";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                } // list rpki

                list rsvp {
                    key "event";
                    description "Enter the rsvp list instance";

                    leaf event {
                        type types-log:rsvp-events;
                        description "Log event as a trigger for one or more EHS handlers";
                    }

                    leaf severity {
                        type enumeration {
                            enum cleared                        { value 1; }
                            enum indeterminate                  { value 2; }
                            enum critical                       { value 3; }
                            enum major                          { value 4; }
                            enum minor                          { value 5; }
                            enum warning                        { value 6; }
                        }
                        description "Severity level associated with event type";
                    }

                    leaf generate {
                        type boolean;
                        description "Generate log events when the event occurs";
                    }

                    leaf throttle {
                        type boolean;
                        description "Throttle log events of this type";
                    }

                    leaf specific-throttle {
                        type boolean;
                        description "Use parameters to throttle the specific event";
                    }

                    leaf specific-throttle-limit {
                        type uint32 {
                            range "1..20000";
                        }
                        description "Throttle limit within which events can be logged";
                    }

                    leaf specific-throttle-interval {
                        type uint32 {
                            range "1..1200";
                        }
                        description "Duration of the event specific throttling interval";
                    }

                    leaf repeat {
                        type boolean;
                        default "false";
                        description "Repeat the log event until the condition is cleared";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                } // list rsvp

                list satellite {
                    key "event";
                    description "Enter the satellite list instance";

                    leaf event {
                        type types-log:satellite-events;
                        description "Log event as a trigger for one or more EHS handlers";
                    }

                    leaf severity {
                        type enumeration {
                            enum cleared                        { value 1; }
                            enum indeterminate                  { value 2; }
                            enum critical                       { value 3; }
                            enum major                          { value 4; }
                            enum minor                          { value 5; }
                            enum warning                        { value 6; }
                        }
                        description "Severity level associated with event type";
                    }

                    leaf generate {
                        type boolean;
                        description "Generate log events when the event occurs";
                    }

                    leaf throttle {
                        type boolean;
                        description "Throttle log events of this type";
                    }

                    leaf specific-throttle {
                        type boolean;
                        description "Use parameters to throttle the specific event";
                    }

                    leaf specific-throttle-limit {
                        type uint32 {
                            range "1..20000";
                        }
                        description "Throttle limit within which events can be logged";
                    }

                    leaf specific-throttle-interval {
                        type uint32 {
                            range "1..1200";
                        }
                        description "Duration of the event specific throttling interval";
                    }

                    leaf repeat {
                        type boolean;
                        default "false";
                        description "Repeat the log event until the condition is cleared";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                } // list satellite

                list security {
                    key "event";
                    description "Enter the security list instance";

                    leaf event {
                        type types-log:security-events;
                        description "Log event as a trigger for one or more EHS handlers";
                    }

                    leaf severity {
                        type enumeration {
                            enum cleared                        { value 1; }
                            enum indeterminate                  { value 2; }
                            enum critical                       { value 3; }
                            enum major                          { value 4; }
                            enum minor                          { value 5; }
                            enum warning                        { value 6; }
                        }
                        description "Severity level associated with event type";
                    }

                    leaf generate {
                        type boolean;
                        description "Generate log events when the event occurs";
                    }

                    leaf throttle {
                        type boolean;
                        description "Throttle log events of this type";
                    }

                    leaf specific-throttle {
                        type boolean;
                        description "Use parameters to throttle the specific event";
                    }

                    leaf specific-throttle-limit {
                        type uint32 {
                            range "1..20000";
                        }
                        description "Throttle limit within which events can be logged";
                    }

                    leaf specific-throttle-interval {
                        type uint32 {
                            range "1..1200";
                        }
                        description "Duration of the event specific throttling interval";
                    }

                    leaf repeat {
                        type boolean;
                        default "false";
                        description "Repeat the log event until the condition is cleared";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                } // list security

                list sflow {
                    key "event";
                    description "Enter the sflow list instance";

                    leaf event {
                        type types-log:sflow-events;
                        description "Log event as a trigger for one or more EHS handlers";
                    }

                    leaf severity {
                        type enumeration {
                            enum cleared                        { value 1; }
                            enum indeterminate                  { value 2; }
                            enum critical                       { value 3; }
                            enum major                          { value 4; }
                            enum minor                          { value 5; }
                            enum warning                        { value 6; }
                        }
                        description "Severity level associated with event type";
                    }

                    leaf generate {
                        type boolean;
                        description "Generate log events when the event occurs";
                    }

                    leaf throttle {
                        type boolean;
                        description "Throttle log events of this type";
                    }

                    leaf specific-throttle {
                        type boolean;
                        description "Use parameters to throttle the specific event";
                    }

                    leaf specific-throttle-limit {
                        type uint32 {
                            range "1..20000";
                        }
                        description "Throttle limit within which events can be logged";
                    }

                    leaf specific-throttle-interval {
                        type uint32 {
                            range "1..1200";
                        }
                        description "Duration of the event specific throttling interval";
                    }

                    leaf repeat {
                        type boolean;
                        default "false";
                        description "Repeat the log event until the condition is cleared";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                } // list sflow

                list snmp {
                    key "event";
                    description "Enter the snmp list instance";

                    leaf event {
                        type types-log:snmp-events;
                        description "Log event as a trigger for one or more EHS handlers";
                    }

                    leaf severity {
                        type enumeration {
                            enum cleared                        { value 1; }
                            enum indeterminate                  { value 2; }
                            enum critical                       { value 3; }
                            enum major                          { value 4; }
                            enum minor                          { value 5; }
                            enum warning                        { value 6; }
                        }
                        description "Severity level associated with event type";
                    }

                    leaf generate {
                        type boolean;
                        description "Generate log events when the event occurs";
                    }

                    leaf throttle {
                        type boolean;
                        description "Throttle log events of this type";
                    }

                    leaf specific-throttle {
                        type boolean;
                        description "Use parameters to throttle the specific event";
                    }

                    leaf specific-throttle-limit {
                        type uint32 {
                            range "1..20000";
                        }
                        description "Throttle limit within which events can be logged";
                    }

                    leaf specific-throttle-interval {
                        type uint32 {
                            range "1..1200";
                        }
                        description "Duration of the event specific throttling interval";
                    }

                    leaf repeat {
                        type boolean;
                        default "false";
                        description "Repeat the log event until the condition is cleared";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                } // list snmp

                list sr-mpls {
                    key "event";
                    description "Enter the sr-mpls list instance";

                    leaf event {
                        type types-log:sr-mpls-events;
                        description "SR MPLS event";
                    }

                    leaf severity {
                        type enumeration {
                            enum cleared                        { value 1; }
                            enum indeterminate                  { value 2; }
                            enum critical                       { value 3; }
                            enum major                          { value 4; }
                            enum minor                          { value 5; }
                            enum warning                        { value 6; }
                        }
                        description "Severity level associated with event type";
                    }

                    leaf generate {
                        type boolean;
                        description "Generate log events when the event occurs";
                    }

                    leaf throttle {
                        type boolean;
                        description "Throttle log events of this type";
                    }

                    leaf specific-throttle {
                        type boolean;
                        description "Use parameters to throttle the specific event";
                    }

                    leaf specific-throttle-limit {
                        type uint32 {
                            range "1..20000";
                        }
                        description "Throttle limit within which events can be logged";
                    }

                    leaf specific-throttle-interval {
                        type uint32 {
                            range "1..1200";
                        }
                        description "Duration of the event specific throttling interval";
                    }

                    leaf repeat {
                        type boolean;
                        default "false";
                        description "Repeat the log event until the condition is cleared";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                } // list sr-mpls

                list sr-policy {
                    key "event";
                    description "Enter the sr-policy list instance";

                    leaf event {
                        type types-log:sr-policy-events;
                        description "Events for SR policy module";
                    }

                    leaf severity {
                        type enumeration {
                            enum cleared                        { value 1; }
                            enum indeterminate                  { value 2; }
                            enum critical                       { value 3; }
                            enum major                          { value 4; }
                            enum minor                          { value 5; }
                            enum warning                        { value 6; }
                        }
                        description "Severity level associated with event type";
                    }

                    leaf generate {
                        type boolean;
                        description "Generate log events when the event occurs";
                    }

                    leaf throttle {
                        type boolean;
                        description "Throttle log events of this type";
                    }

                    leaf specific-throttle {
                        type boolean;
                        description "Use parameters to throttle the specific event";
                    }

                    leaf specific-throttle-limit {
                        type uint32 {
                            range "1..20000";
                        }
                        description "Throttle limit within which events can be logged";
                    }

                    leaf specific-throttle-interval {
                        type uint32 {
                            range "1..1200";
                        }
                        description "Duration of the event specific throttling interval";
                    }

                    leaf repeat {
                        type boolean;
                        default "false";
                        description "Repeat the log event until the condition is cleared";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                } // list sr-policy

                list srv6 {
                    key "event";
                    description "Enter the srv6 list instance";

                    leaf event {
                        type types-log:srv6-events;
                        description "Log event as a trigger for one or more EHS handlers";
                    }

                    leaf severity {
                        type enumeration {
                            enum cleared                        { value 1; }
                            enum indeterminate                  { value 2; }
                            enum critical                       { value 3; }
                            enum major                          { value 4; }
                            enum minor                          { value 5; }
                            enum warning                        { value 6; }
                        }
                        description "Severity level associated with event type";
                    }

                    leaf generate {
                        type boolean;
                        description "Generate log events when the event occurs";
                    }

                    leaf throttle {
                        type boolean;
                        description "Throttle log events of this type";
                    }

                    leaf specific-throttle {
                        type boolean;
                        description "Use parameters to throttle the specific event";
                    }

                    leaf specific-throttle-limit {
                        type uint32 {
                            range "1..20000";
                        }
                        description "Throttle limit within which events can be logged";
                    }

                    leaf specific-throttle-interval {
                        type uint32 {
                            range "1..1200";
                        }
                        description "Duration of the event specific throttling interval";
                    }

                    leaf repeat {
                        type boolean;
                        default "false";
                        description "Repeat the log event until the condition is cleared";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                } // list srv6

                list stp {
                    key "event";
                    description "Enter the stp list instance";

                    leaf event {
                        type types-log:stp-events;
                        description "Log event as a trigger for one or more EHS handlers";
                    }

                    leaf severity {
                        type enumeration {
                            enum cleared                        { value 1; }
                            enum indeterminate                  { value 2; }
                            enum critical                       { value 3; }
                            enum major                          { value 4; }
                            enum minor                          { value 5; }
                            enum warning                        { value 6; }
                        }
                        description "Severity level associated with event type";
                    }

                    leaf generate {
                        type boolean;
                        description "Generate log events when the event occurs";
                    }

                    leaf throttle {
                        type boolean;
                        description "Throttle log events of this type";
                    }

                    leaf specific-throttle {
                        type boolean;
                        description "Use parameters to throttle the specific event";
                    }

                    leaf specific-throttle-limit {
                        type uint32 {
                            range "1..20000";
                        }
                        description "Throttle limit within which events can be logged";
                    }

                    leaf specific-throttle-interval {
                        type uint32 {
                            range "1..1200";
                        }
                        description "Duration of the event specific throttling interval";
                    }

                    leaf repeat {
                        type boolean;
                        default "false";
                        description "Repeat the log event until the condition is cleared";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                } // list stp

                list svcmgr {
                    key "event";
                    description "Enter the svcmgr list instance";

                    leaf event {
                        type types-log:svcmgr-events;
                        description "Log event as a trigger for one or more EHS handlers";
                    }

                    leaf severity {
                        type enumeration {
                            enum cleared                        { value 1; }
                            enum indeterminate                  { value 2; }
                            enum critical                       { value 3; }
                            enum major                          { value 4; }
                            enum minor                          { value 5; }
                            enum warning                        { value 6; }
                        }
                        description "Severity level associated with event type";
                    }

                    leaf generate {
                        type boolean;
                        description "Generate log events when the event occurs";
                    }

                    leaf throttle {
                        type boolean;
                        description "Throttle log events of this type";
                    }

                    leaf specific-throttle {
                        type boolean;
                        description "Use parameters to throttle the specific event";
                    }

                    leaf specific-throttle-limit {
                        type uint32 {
                            range "1..20000";
                        }
                        description "Throttle limit within which events can be logged";
                    }

                    leaf specific-throttle-interval {
                        type uint32 {
                            range "1..1200";
                        }
                        description "Duration of the event specific throttling interval";
                    }

                    leaf repeat {
                        type boolean;
                        default "false";
                        description "Repeat the log event until the condition is cleared";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                } // list svcmgr

                list system {
                    key "event";
                    description "Enter the system list instance";

                    leaf event {
                        type types-log:system-events;
                        description "Log event as a trigger for one or more EHS handlers";
                    }

                    leaf severity {
                        type enumeration {
                            enum cleared                        { value 1; }
                            enum indeterminate                  { value 2; }
                            enum critical                       { value 3; }
                            enum major                          { value 4; }
                            enum minor                          { value 5; }
                            enum warning                        { value 6; }
                        }
                        description "Severity level associated with event type";
                    }

                    leaf generate {
                        type boolean;
                        description "Generate log events when the event occurs";
                    }

                    leaf throttle {
                        type boolean;
                        description "Throttle log events of this type";
                    }

                    leaf specific-throttle {
                        type boolean;
                        description "Use parameters to throttle the specific event";
                    }

                    leaf specific-throttle-limit {
                        type uint32 {
                            range "1..20000";
                        }
                        description "Throttle limit within which events can be logged";
                    }

                    leaf specific-throttle-interval {
                        type uint32 {
                            range "1..1200";
                        }
                        description "Duration of the event specific throttling interval";
                    }

                    leaf repeat {
                        type boolean;
                        default "false";
                        description "Repeat the log event until the condition is cleared";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                } // list system

                list tls {
                    key "event";
                    description "Enter the tls list instance";

                    leaf event {
                        type types-log:tls-events;
                        description "Log event as a trigger for one or more EHS handlers";
                    }

                    leaf severity {
                        type enumeration {
                            enum cleared                        { value 1; }
                            enum indeterminate                  { value 2; }
                            enum critical                       { value 3; }
                            enum major                          { value 4; }
                            enum minor                          { value 5; }
                            enum warning                        { value 6; }
                        }
                        description "Severity level associated with event type";
                    }

                    leaf generate {
                        type boolean;
                        description "Generate log events when the event occurs";
                    }

                    leaf throttle {
                        type boolean;
                        description "Throttle log events of this type";
                    }

                    leaf specific-throttle {
                        type boolean;
                        description "Use parameters to throttle the specific event";
                    }

                    leaf specific-throttle-limit {
                        type uint32 {
                            range "1..20000";
                        }
                        description "Throttle limit within which events can be logged";
                    }

                    leaf specific-throttle-interval {
                        type uint32 {
                            range "1..1200";
                        }
                        description "Duration of the event specific throttling interval";
                    }

                    leaf repeat {
                        type boolean;
                        default "false";
                        description "Repeat the log event until the condition is cleared";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                } // list tls

                list tree-sid {
                    key "event";
                    description "Enter the tree-sid list instance";

                    leaf event {
                        type types-log:treesid-events;
                        description "Log event as a trigger for one or more EHS handlers";
                    }

                    leaf severity {
                        type enumeration {
                            enum cleared                        { value 1; }
                            enum indeterminate                  { value 2; }
                            enum critical                       { value 3; }
                            enum major                          { value 4; }
                            enum minor                          { value 5; }
                            enum warning                        { value 6; }
                        }
                        description "Severity level associated with event type";
                    }

                    leaf generate {
                        type boolean;
                        description "Generate log events when the event occurs";
                    }

                    leaf throttle {
                        type boolean;
                        description "Throttle log events of this type";
                    }

                    leaf specific-throttle {
                        type boolean;
                        description "Use parameters to throttle the specific event";
                    }

                    leaf specific-throttle-limit {
                        type uint32 {
                            range "1..20000";
                        }
                        description "Throttle limit within which events can be logged";
                    }

                    leaf specific-throttle-interval {
                        type uint32 {
                            range "1..1200";
                        }
                        description "Duration of the event specific throttling interval";
                    }

                    leaf repeat {
                        type boolean;
                        default "false";
                        description "Repeat the log event until the condition is cleared";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                } // list tree-sid

                list user {
                    key "event";
                    description "Enter the user list instance";

                    leaf event {
                        type types-log:user-events;
                        description "Log event as a trigger for one or more EHS handlers";
                    }

                    leaf severity {
                        type enumeration {
                            enum cleared                        { value 1; }
                            enum indeterminate                  { value 2; }
                            enum critical                       { value 3; }
                            enum major                          { value 4; }
                            enum minor                          { value 5; }
                            enum warning                        { value 6; }
                        }
                        description "Severity level associated with event type";
                    }

                    leaf generate {
                        type boolean;
                        description "Generate log events when the event occurs";
                    }

                    leaf throttle {
                        type boolean;
                        description "Throttle log events of this type";
                    }

                    leaf specific-throttle {
                        type boolean;
                        description "Use parameters to throttle the specific event";
                    }

                    leaf specific-throttle-limit {
                        type uint32 {
                            range "1..20000";
                        }
                        description "Throttle limit within which events can be logged";
                    }

                    leaf specific-throttle-interval {
                        type uint32 {
                            range "1..1200";
                        }
                        description "Duration of the event specific throttling interval";
                    }

                    leaf repeat {
                        type boolean;
                        default "false";
                        description "Repeat the log event until the condition is cleared";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                } // list user

                list video {
                    key "event";
                    description "Enter the video list instance";

                    leaf event {
                        type types-log:video-events;
                        description "Log event as a trigger for one or more EHS handlers";
                    }

                    leaf severity {
                        type enumeration {
                            enum cleared                        { value 1; }
                            enum indeterminate                  { value 2; }
                            enum critical                       { value 3; }
                            enum major                          { value 4; }
                            enum minor                          { value 5; }
                            enum warning                        { value 6; }
                        }
                        description "Severity level associated with event type";
                    }

                    leaf generate {
                        type boolean;
                        description "Generate log events when the event occurs";
                    }

                    leaf throttle {
                        type boolean;
                        description "Throttle log events of this type";
                    }

                    leaf specific-throttle {
                        type boolean;
                        description "Use parameters to throttle the specific event";
                    }

                    leaf specific-throttle-limit {
                        type uint32 {
                            range "1..20000";
                        }
                        description "Throttle limit within which events can be logged";
                    }

                    leaf specific-throttle-interval {
                        type uint32 {
                            range "1..1200";
                        }
                        description "Duration of the event specific throttling interval";
                    }

                    leaf repeat {
                        type boolean;
                        default "false";
                        description "Repeat the log event until the condition is cleared";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                } // list video

                list vrrp {
                    key "event";
                    description "Enter the vrrp list instance";

                    leaf event {
                        type types-log:vrrp-events;
                        description "Log event as a trigger for one or more EHS handlers";
                    }

                    leaf severity {
                        type enumeration {
                            enum cleared                        { value 1; }
                            enum indeterminate                  { value 2; }
                            enum critical                       { value 3; }
                            enum major                          { value 4; }
                            enum minor                          { value 5; }
                            enum warning                        { value 6; }
                        }
                        description "Severity level associated with event type";
                    }

                    leaf generate {
                        type boolean;
                        description "Generate log events when the event occurs";
                    }

                    leaf throttle {
                        type boolean;
                        description "Throttle log events of this type";
                    }

                    leaf specific-throttle {
                        type boolean;
                        description "Use parameters to throttle the specific event";
                    }

                    leaf specific-throttle-limit {
                        type uint32 {
                            range "1..20000";
                        }
                        description "Throttle limit within which events can be logged";
                    }

                    leaf specific-throttle-interval {
                        type uint32 {
                            range "1..1200";
                        }
                        description "Duration of the event specific throttling interval";
                    }

                    leaf repeat {
                        type boolean;
                        default "false";
                        description "Repeat the log event until the condition is cleared";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                } // list vrrp

                list vrtr {
                    key "event";
                    description "Enter the vrtr list instance";

                    leaf event {
                        type types-log:vrtr-events;
                        description "Log event as a trigger for one or more EHS handlers";
                    }

                    leaf severity {
                        type enumeration {
                            enum cleared                        { value 1; }
                            enum indeterminate                  { value 2; }
                            enum critical                       { value 3; }
                            enum major                          { value 4; }
                            enum minor                          { value 5; }
                            enum warning                        { value 6; }
                        }
                        description "Severity level associated with event type";
                    }

                    leaf generate {
                        type boolean;
                        description "Generate log events when the event occurs";
                    }

                    leaf throttle {
                        type boolean;
                        description "Throttle log events of this type";
                    }

                    leaf specific-throttle {
                        type boolean;
                        description "Use parameters to throttle the specific event";
                    }

                    leaf specific-throttle-limit {
                        type uint32 {
                            range "1..20000";
                        }
                        description "Throttle limit within which events can be logged";
                    }

                    leaf specific-throttle-interval {
                        type uint32 {
                            range "1..1200";
                        }
                        description "Duration of the event specific throttling interval";
                    }

                    leaf repeat {
                        type boolean;
                        default "false";
                        description "Repeat the log event until the condition is cleared";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                } // list vrtr

                list wlan-gw {
                    key "event";
                    description "Enter the wlan-gw list instance";

                    leaf event {
                        type types-log:wlan-gw-events;
                        description "Log event as a trigger for one or more EHS handlers";
                    }

                    leaf severity {
                        type enumeration {
                            enum cleared                        { value 1; }
                            enum indeterminate                  { value 2; }
                            enum critical                       { value 3; }
                            enum major                          { value 4; }
                            enum minor                          { value 5; }
                            enum warning                        { value 6; }
                        }
                        description "Severity level associated with event type";
                    }

                    leaf generate {
                        type boolean;
                        description "Generate log events when the event occurs";
                    }

                    leaf throttle {
                        type boolean;
                        description "Throttle log events of this type";
                    }

                    leaf specific-throttle {
                        type boolean;
                        description "Use parameters to throttle the specific event";
                    }

                    leaf specific-throttle-limit {
                        type uint32 {
                            range "1..20000";
                        }
                        description "Throttle limit within which events can be logged";
                    }

                    leaf specific-throttle-interval {
                        type uint32 {
                            range "1..1200";
                        }
                        description "Duration of the event specific throttling interval";
                    }

                    leaf repeat {
                        type boolean;
                        default "false";
                        description "Repeat the log event until the condition is cleared";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                } // list wlan-gw

                list wpp {
                    key "event";
                    description "Enter the wpp list instance";

                    leaf event {
                        type types-log:wpp-events;
                        description "Log event as a trigger for one or more EHS handlers";
                    }

                    leaf severity {
                        type enumeration {
                            enum cleared                        { value 1; }
                            enum indeterminate                  { value 2; }
                            enum critical                       { value 3; }
                            enum major                          { value 4; }
                            enum minor                          { value 5; }
                            enum warning                        { value 6; }
                        }
                        description "Severity level associated with event type";
                    }

                    leaf generate {
                        type boolean;
                        description "Generate log events when the event occurs";
                    }

                    leaf throttle {
                        type boolean;
                        description "Throttle log events of this type";
                    }

                    leaf specific-throttle {
                        type boolean;
                        description "Use parameters to throttle the specific event";
                    }

                    leaf specific-throttle-limit {
                        type uint32 {
                            range "1..20000";
                        }
                        description "Throttle limit within which events can be logged";
                    }

                    leaf specific-throttle-interval {
                        type uint32 {
                            range "1..1200";
                        }
                        description "Duration of the event specific throttling interval";
                    }

                    leaf repeat {
                        type boolean;
                        default "false";
                        description "Repeat the log event until the condition is cleared";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                } // list wpp

            } // container log-events

            container event-handling {
                description "Enter the event-handling context";

                list handler {
                    key "name";
                    max-elements 1500;
                    description "Enter the handler list instance";

                    leaf name {
                        type types-sros:named-item;
                        description "EHS handler name";
                    }

                    leaf admin-state {
                        type types-sros:admin-state;
                        default "disable";
                        description "Administrative state of the EHS handler";
                    }

                    leaf description {
                        type types-sros:description;
                        description "Text description";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                    list entry {
                        key "id";
                        max-elements 1500;
                        description "Enter the entry list instance";

                        leaf id {
                            type uint32 {
                                range "1..1500";
                            }
                            description "EHS handler entry ID";
                        }

                        leaf admin-state {
                            type types-sros:admin-state;
                            default "enable";
                            description "Administrative state of the EHS handler entry";
                        }

                        leaf description {
                            type types-sros:description;
                            description "Text description";
                        }

                        leaf min-delay {
                            type uint32 {
                                range "1..604800";
                            }
                            units "seconds";
                            description "Minimum delay between subsequent executions of the script policy";
                        }

                        leaf-list apply-groups {
                            type leafref {
                                path "../../../../../groups/group/name";
                            }
                            max-elements 8;
                            ordered-by user;
                            description "Apply a configuration group at this level";
                        }

                        leaf-list apply-groups-exclude {
                            type leafref {
                                path "../../../../../groups/group/name";
                            }
                            max-elements 8;
                            ordered-by user;
                            description "Exclude a configuration group at this level";
                        }

                        container script-policy {
                            presence "Enable the script-policy context";
                            description "Enable the script-policy context";

                            leaf name {
                                type leafref {
                                    path "../../../../../../system/script-control/script-policy[owner=current()/../owner]/policy-name";
                                }
                                mandatory true;
                                description "Script policy name";
                            }

                            leaf owner {
                                type leafref {
                                    path "../../../../../../system/script-control/script-policy[policy-name=current()/../name]/owner";
                                }
                                default "TiMOS CLI";
                                description "Script policy owner";
                            }

                        } // container script-policy

                    } // list entry

                } // list handler

            } // container event-handling

            container event-trigger {
                description "Enter the event-trigger context";

                list adp {
                    key "event";
                    description "Enter the adp list instance";

                    leaf event {
                        type types-log:adp-events;
                        description "Log event as a trigger for one or more EHS handlers";
                    }

                    leaf admin-state {
                        type types-sros:admin-state;
                        default "disable";
                        description "Administrative state of the EHS event trigger";
                    }

                    leaf description {
                        type types-sros:description;
                        description "Text description";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                    list entry {
                        key "id";
                        description "Enter the entry list instance";

                        leaf id {
                            type uint32 {
                                range "1..1500";
                            }
                            description "ID of the EHS event trigger entry";
                        }

                        leaf admin-state {
                            type types-sros:admin-state;
                            default "enable";
                            description "Administrative state of the EHS event trigger entry";
                        }

                        leaf description {
                            type types-sros:description;
                            description "Text description";
                        }

                        leaf filter {
                            type leafref {
                                path "../../../../filter/filter-name";
                            }
                            description "Log filter for EHS event trigger entry";
                        }

                        leaf handler {
                            type leafref {
                                path "../../../../event-handling/handler/name";
                            }
                            description "Event handler for EHS event trigger entry";
                        }

                        leaf-list apply-groups {
                            type leafref {
                                path "../../../../../groups/group/name";
                            }
                            max-elements 8;
                            ordered-by user;
                            description "Apply a configuration group at this level";
                        }

                        leaf-list apply-groups-exclude {
                            type leafref {
                                path "../../../../../groups/group/name";
                            }
                            max-elements 8;
                            ordered-by user;
                            description "Exclude a configuration group at this level";
                        }

                        container debounce {
                            description "Enter the debounce context";

                            leaf value {
                                type uint32 {
                                    range "2..15";
                                }
                                description "Occurrences in time interval to trigger EHS response";
                            }

                            leaf time {
                                type uint32 {
                                    range "1..604800";
                                }
                                units "seconds";
                                description "Time window for events for EHS to trigger a response";
                            }

                        } // container debounce

                    } // list entry

                } // list adp

                list anysec {
                    key "event";
                    description "Enter the anysec list instance";

                    leaf event {
                        type types-log:anysec-events;
                        description "ANYSec module event";
                    }

                    leaf admin-state {
                        type types-sros:admin-state;
                        default "disable";
                        description "Administrative state of the EHS event trigger";
                    }

                    leaf description {
                        type types-sros:description;
                        description "Text description";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                    list entry {
                        key "id";
                        description "Enter the entry list instance";

                        leaf id {
                            type uint32 {
                                range "1..1500";
                            }
                            description "ID of the EHS event trigger entry";
                        }

                        leaf admin-state {
                            type types-sros:admin-state;
                            default "enable";
                            description "Administrative state of the EHS event trigger entry";
                        }

                        leaf description {
                            type types-sros:description;
                            description "Text description";
                        }

                        leaf filter {
                            type leafref {
                                path "../../../../filter/filter-name";
                            }
                            description "Log filter for EHS event trigger entry";
                        }

                        leaf handler {
                            type leafref {
                                path "../../../../event-handling/handler/name";
                            }
                            description "Event handler for EHS event trigger entry";
                        }

                        leaf-list apply-groups {
                            type leafref {
                                path "../../../../../groups/group/name";
                            }
                            max-elements 8;
                            ordered-by user;
                            description "Apply a configuration group at this level";
                        }

                        leaf-list apply-groups-exclude {
                            type leafref {
                                path "../../../../../groups/group/name";
                            }
                            max-elements 8;
                            ordered-by user;
                            description "Exclude a configuration group at this level";
                        }

                        container debounce {
                            description "Enter the debounce context";

                            leaf value {
                                type uint32 {
                                    range "2..15";
                                }
                                description "Occurrences in time interval to trigger EHS response";
                            }

                            leaf time {
                                type uint32 {
                                    range "1..604800";
                                }
                                units "seconds";
                                description "Time window for events for EHS to trigger a response";
                            }

                        } // container debounce

                    } // list entry

                } // list anysec

                list application-assurance {
                    key "event";
                    description "Enter the application-assurance list instance";

                    leaf event {
                        type types-log:application-assurance-events;
                        description "Log event as a trigger for one or more EHS handlers";
                    }

                    leaf admin-state {
                        type types-sros:admin-state;
                        default "disable";
                        description "Administrative state of the EHS event trigger";
                    }

                    leaf description {
                        type types-sros:description;
                        description "Text description";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                    list entry {
                        key "id";
                        description "Enter the entry list instance";

                        leaf id {
                            type uint32 {
                                range "1..1500";
                            }
                            description "ID of the EHS event trigger entry";
                        }

                        leaf admin-state {
                            type types-sros:admin-state;
                            default "enable";
                            description "Administrative state of the EHS event trigger entry";
                        }

                        leaf description {
                            type types-sros:description;
                            description "Text description";
                        }

                        leaf filter {
                            type leafref {
                                path "../../../../filter/filter-name";
                            }
                            description "Log filter for EHS event trigger entry";
                        }

                        leaf handler {
                            type leafref {
                                path "../../../../event-handling/handler/name";
                            }
                            description "Event handler for EHS event trigger entry";
                        }

                        leaf-list apply-groups {
                            type leafref {
                                path "../../../../../groups/group/name";
                            }
                            max-elements 8;
                            ordered-by user;
                            description "Apply a configuration group at this level";
                        }

                        leaf-list apply-groups-exclude {
                            type leafref {
                                path "../../../../../groups/group/name";
                            }
                            max-elements 8;
                            ordered-by user;
                            description "Exclude a configuration group at this level";
                        }

                        container debounce {
                            description "Enter the debounce context";

                            leaf value {
                                type uint32 {
                                    range "2..15";
                                }
                                description "Occurrences in time interval to trigger EHS response";
                            }

                            leaf time {
                                type uint32 {
                                    range "1..604800";
                                }
                                units "seconds";
                                description "Time window for events for EHS to trigger a response";
                            }

                        } // container debounce

                    } // list entry

                } // list application-assurance

                list aps {
                    key "event";
                    description "Enter the aps list instance";

                    leaf event {
                        type types-log:aps-events;
                        description "Log event as a trigger for one or more EHS handlers";
                    }

                    leaf admin-state {
                        type types-sros:admin-state;
                        default "disable";
                        description "Administrative state of the EHS event trigger";
                    }

                    leaf description {
                        type types-sros:description;
                        description "Text description";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                    list entry {
                        key "id";
                        description "Enter the entry list instance";

                        leaf id {
                            type uint32 {
                                range "1..1500";
                            }
                            description "ID of the EHS event trigger entry";
                        }

                        leaf admin-state {
                            type types-sros:admin-state;
                            default "enable";
                            description "Administrative state of the EHS event trigger entry";
                        }

                        leaf description {
                            type types-sros:description;
                            description "Text description";
                        }

                        leaf filter {
                            type leafref {
                                path "../../../../filter/filter-name";
                            }
                            description "Log filter for EHS event trigger entry";
                        }

                        leaf handler {
                            type leafref {
                                path "../../../../event-handling/handler/name";
                            }
                            description "Event handler for EHS event trigger entry";
                        }

                        leaf-list apply-groups {
                            type leafref {
                                path "../../../../../groups/group/name";
                            }
                            max-elements 8;
                            ordered-by user;
                            description "Apply a configuration group at this level";
                        }

                        leaf-list apply-groups-exclude {
                            type leafref {
                                path "../../../../../groups/group/name";
                            }
                            max-elements 8;
                            ordered-by user;
                            description "Exclude a configuration group at this level";
                        }

                        container debounce {
                            description "Enter the debounce context";

                            leaf value {
                                type uint32 {
                                    range "2..15";
                                }
                                description "Occurrences in time interval to trigger EHS response";
                            }

                            leaf time {
                                type uint32 {
                                    range "1..604800";
                                }
                                units "seconds";
                                description "Time window for events for EHS to trigger a response";
                            }

                        } // container debounce

                    } // list entry

                } // list aps

                list auto-prov {
                    key "event";
                    description "Enter the auto-prov list instance";

                    leaf event {
                        type types-log:auto-prov-events;
                        description "Log event as a trigger for one or more EHS handlers";
                    }

                    leaf admin-state {
                        type types-sros:admin-state;
                        default "disable";
                        description "Administrative state of the EHS event trigger";
                    }

                    leaf description {
                        type types-sros:description;
                        description "Text description";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                    list entry {
                        key "id";
                        description "Enter the entry list instance";

                        leaf id {
                            type uint32 {
                                range "1..1500";
                            }
                            description "ID of the EHS event trigger entry";
                        }

                        leaf admin-state {
                            type types-sros:admin-state;
                            default "enable";
                            description "Administrative state of the EHS event trigger entry";
                        }

                        leaf description {
                            type types-sros:description;
                            description "Text description";
                        }

                        leaf filter {
                            type leafref {
                                path "../../../../filter/filter-name";
                            }
                            description "Log filter for EHS event trigger entry";
                        }

                        leaf handler {
                            type leafref {
                                path "../../../../event-handling/handler/name";
                            }
                            description "Event handler for EHS event trigger entry";
                        }

                        leaf-list apply-groups {
                            type leafref {
                                path "../../../../../groups/group/name";
                            }
                            max-elements 8;
                            ordered-by user;
                            description "Apply a configuration group at this level";
                        }

                        leaf-list apply-groups-exclude {
                            type leafref {
                                path "../../../../../groups/group/name";
                            }
                            max-elements 8;
                            ordered-by user;
                            description "Exclude a configuration group at this level";
                        }

                        container debounce {
                            description "Enter the debounce context";

                            leaf value {
                                type uint32 {
                                    range "2..15";
                                }
                                description "Occurrences in time interval to trigger EHS response";
                            }

                            leaf time {
                                type uint32 {
                                    range "1..604800";
                                }
                                units "seconds";
                                description "Time window for events for EHS to trigger a response";
                            }

                        } // container debounce

                    } // list entry

                } // list auto-prov

                list bfd {
                    key "event";
                    description "Enter the bfd list instance";

                    leaf event {
                        type types-log:bfd-events;
                        description "Log event as a trigger for one or more EHS handlers";
                    }

                    leaf admin-state {
                        type types-sros:admin-state;
                        default "disable";
                        description "Administrative state of the EHS event trigger";
                    }

                    leaf description {
                        type types-sros:description;
                        description "Text description";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                    list entry {
                        key "id";
                        description "Enter the entry list instance";

                        leaf id {
                            type uint32 {
                                range "1..1500";
                            }
                            description "ID of the EHS event trigger entry";
                        }

                        leaf admin-state {
                            type types-sros:admin-state;
                            default "enable";
                            description "Administrative state of the EHS event trigger entry";
                        }

                        leaf description {
                            type types-sros:description;
                            description "Text description";
                        }

                        leaf filter {
                            type leafref {
                                path "../../../../filter/filter-name";
                            }
                            description "Log filter for EHS event trigger entry";
                        }

                        leaf handler {
                            type leafref {
                                path "../../../../event-handling/handler/name";
                            }
                            description "Event handler for EHS event trigger entry";
                        }

                        leaf-list apply-groups {
                            type leafref {
                                path "../../../../../groups/group/name";
                            }
                            max-elements 8;
                            ordered-by user;
                            description "Apply a configuration group at this level";
                        }

                        leaf-list apply-groups-exclude {
                            type leafref {
                                path "../../../../../groups/group/name";
                            }
                            max-elements 8;
                            ordered-by user;
                            description "Exclude a configuration group at this level";
                        }

                        container debounce {
                            description "Enter the debounce context";

                            leaf value {
                                type uint32 {
                                    range "2..15";
                                }
                                description "Occurrences in time interval to trigger EHS response";
                            }

                            leaf time {
                                type uint32 {
                                    range "1..604800";
                                }
                                units "seconds";
                                description "Time window for events for EHS to trigger a response";
                            }

                        } // container debounce

                    } // list entry

                } // list bfd

                list bgp {
                    key "event";
                    description "Enter the bgp list instance";

                    leaf event {
                        type types-log:bgp-events;
                        description "Log event as a trigger for one or more EHS handlers";
                    }

                    leaf admin-state {
                        type types-sros:admin-state;
                        default "disable";
                        description "Administrative state of the EHS event trigger";
                    }

                    leaf description {
                        type types-sros:description;
                        description "Text description";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                    list entry {
                        key "id";
                        description "Enter the entry list instance";

                        leaf id {
                            type uint32 {
                                range "1..1500";
                            }
                            description "ID of the EHS event trigger entry";
                        }

                        leaf admin-state {
                            type types-sros:admin-state;
                            default "enable";
                            description "Administrative state of the EHS event trigger entry";
                        }

                        leaf description {
                            type types-sros:description;
                            description "Text description";
                        }

                        leaf filter {
                            type leafref {
                                path "../../../../filter/filter-name";
                            }
                            description "Log filter for EHS event trigger entry";
                        }

                        leaf handler {
                            type leafref {
                                path "../../../../event-handling/handler/name";
                            }
                            description "Event handler for EHS event trigger entry";
                        }

                        leaf-list apply-groups {
                            type leafref {
                                path "../../../../../groups/group/name";
                            }
                            max-elements 8;
                            ordered-by user;
                            description "Apply a configuration group at this level";
                        }

                        leaf-list apply-groups-exclude {
                            type leafref {
                                path "../../../../../groups/group/name";
                            }
                            max-elements 8;
                            ordered-by user;
                            description "Exclude a configuration group at this level";
                        }

                        container debounce {
                            description "Enter the debounce context";

                            leaf value {
                                type uint32 {
                                    range "2..15";
                                }
                                description "Occurrences in time interval to trigger EHS response";
                            }

                            leaf time {
                                type uint32 {
                                    range "1..604800";
                                }
                                units "seconds";
                                description "Time window for events for EHS to trigger a response";
                            }

                        } // container debounce

                    } // list entry

                } // list bgp

                list bier {
                    key "event";
                    description "Enter the bier list instance";

                    leaf event {
                        type types-log:bier-events;
                        description "Log event as a trigger for one or more EHS handlers";
                    }

                    leaf admin-state {
                        type types-sros:admin-state;
                        default "disable";
                        description "Administrative state of the EHS event trigger";
                    }

                    leaf description {
                        type types-sros:description;
                        description "Text description";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                    list entry {
                        key "id";
                        description "Enter the entry list instance";

                        leaf id {
                            type uint32 {
                                range "1..1500";
                            }
                            description "ID of the EHS event trigger entry";
                        }

                        leaf admin-state {
                            type types-sros:admin-state;
                            default "enable";
                            description "Administrative state of the EHS event trigger entry";
                        }

                        leaf description {
                            type types-sros:description;
                            description "Text description";
                        }

                        leaf filter {
                            type leafref {
                                path "../../../../filter/filter-name";
                            }
                            description "Log filter for EHS event trigger entry";
                        }

                        leaf handler {
                            type leafref {
                                path "../../../../event-handling/handler/name";
                            }
                            description "Event handler for EHS event trigger entry";
                        }

                        leaf-list apply-groups {
                            type leafref {
                                path "../../../../../groups/group/name";
                            }
                            max-elements 8;
                            ordered-by user;
                            description "Apply a configuration group at this level";
                        }

                        leaf-list apply-groups-exclude {
                            type leafref {
                                path "../../../../../groups/group/name";
                            }
                            max-elements 8;
                            ordered-by user;
                            description "Exclude a configuration group at this level";
                        }

                        container debounce {
                            description "Enter the debounce context";

                            leaf value {
                                type uint32 {
                                    range "2..15";
                                }
                                description "Occurrences in time interval to trigger EHS response";
                            }

                            leaf time {
                                type uint32 {
                                    range "1..604800";
                                }
                                units "seconds";
                                description "Time window for events for EHS to trigger a response";
                            }

                        } // container debounce

                    } // list entry

                } // list bier

                list calltrace {
                    key "event";
                    description "Enter the calltrace list instance";

                    leaf event {
                        type types-log:calltrace-events;
                        description "Log event as a trigger for one or more EHS handlers";
                    }

                    leaf admin-state {
                        type types-sros:admin-state;
                        default "disable";
                        description "Administrative state of the EHS event trigger";
                    }

                    leaf description {
                        type types-sros:description;
                        description "Text description";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                    list entry {
                        key "id";
                        description "Enter the entry list instance";

                        leaf id {
                            type uint32 {
                                range "1..1500";
                            }
                            description "ID of the EHS event trigger entry";
                        }

                        leaf admin-state {
                            type types-sros:admin-state;
                            default "enable";
                            description "Administrative state of the EHS event trigger entry";
                        }

                        leaf description {
                            type types-sros:description;
                            description "Text description";
                        }

                        leaf filter {
                            type leafref {
                                path "../../../../filter/filter-name";
                            }
                            description "Log filter for EHS event trigger entry";
                        }

                        leaf handler {
                            type leafref {
                                path "../../../../event-handling/handler/name";
                            }
                            description "Event handler for EHS event trigger entry";
                        }

                        leaf-list apply-groups {
                            type leafref {
                                path "../../../../../groups/group/name";
                            }
                            max-elements 8;
                            ordered-by user;
                            description "Apply a configuration group at this level";
                        }

                        leaf-list apply-groups-exclude {
                            type leafref {
                                path "../../../../../groups/group/name";
                            }
                            max-elements 8;
                            ordered-by user;
                            description "Exclude a configuration group at this level";
                        }

                        container debounce {
                            description "Enter the debounce context";

                            leaf value {
                                type uint32 {
                                    range "2..15";
                                }
                                description "Occurrences in time interval to trigger EHS response";
                            }

                            leaf time {
                                type uint32 {
                                    range "1..604800";
                                }
                                units "seconds";
                                description "Time window for events for EHS to trigger a response";
                            }

                        } // container debounce

                    } // list entry

                } // list calltrace

                list cflowd {
                    key "event";
                    description "Enter the cflowd list instance";

                    leaf event {
                        type types-log:cflowd-events;
                        description "Log event as a trigger for one or more EHS handlers";
                    }

                    leaf admin-state {
                        type types-sros:admin-state;
                        default "disable";
                        description "Administrative state of the EHS event trigger";
                    }

                    leaf description {
                        type types-sros:description;
                        description "Text description";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                    list entry {
                        key "id";
                        description "Enter the entry list instance";

                        leaf id {
                            type uint32 {
                                range "1..1500";
                            }
                            description "ID of the EHS event trigger entry";
                        }

                        leaf admin-state {
                            type types-sros:admin-state;
                            default "enable";
                            description "Administrative state of the EHS event trigger entry";
                        }

                        leaf description {
                            type types-sros:description;
                            description "Text description";
                        }

                        leaf filter {
                            type leafref {
                                path "../../../../filter/filter-name";
                            }
                            description "Log filter for EHS event trigger entry";
                        }

                        leaf handler {
                            type leafref {
                                path "../../../../event-handling/handler/name";
                            }
                            description "Event handler for EHS event trigger entry";
                        }

                        leaf-list apply-groups {
                            type leafref {
                                path "../../../../../groups/group/name";
                            }
                            max-elements 8;
                            ordered-by user;
                            description "Apply a configuration group at this level";
                        }

                        leaf-list apply-groups-exclude {
                            type leafref {
                                path "../../../../../groups/group/name";
                            }
                            max-elements 8;
                            ordered-by user;
                            description "Exclude a configuration group at this level";
                        }

                        container debounce {
                            description "Enter the debounce context";

                            leaf value {
                                type uint32 {
                                    range "2..15";
                                }
                                description "Occurrences in time interval to trigger EHS response";
                            }

                            leaf time {
                                type uint32 {
                                    range "1..604800";
                                }
                                units "seconds";
                                description "Time window for events for EHS to trigger a response";
                            }

                        } // container debounce

                    } // list entry

                } // list cflowd

                list chassis {
                    key "event";
                    description "Enter the chassis list instance";

                    leaf event {
                        type types-log:chassis-events;
                        description "Log event as a trigger for one or more EHS handlers";
                    }

                    leaf admin-state {
                        type types-sros:admin-state;
                        default "disable";
                        description "Administrative state of the EHS event trigger";
                    }

                    leaf description {
                        type types-sros:description;
                        description "Text description";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                    list entry {
                        key "id";
                        description "Enter the entry list instance";

                        leaf id {
                            type uint32 {
                                range "1..1500";
                            }
                            description "ID of the EHS event trigger entry";
                        }

                        leaf admin-state {
                            type types-sros:admin-state;
                            default "enable";
                            description "Administrative state of the EHS event trigger entry";
                        }

                        leaf description {
                            type types-sros:description;
                            description "Text description";
                        }

                        leaf filter {
                            type leafref {
                                path "../../../../filter/filter-name";
                            }
                            description "Log filter for EHS event trigger entry";
                        }

                        leaf handler {
                            type leafref {
                                path "../../../../event-handling/handler/name";
                            }
                            description "Event handler for EHS event trigger entry";
                        }

                        leaf-list apply-groups {
                            type leafref {
                                path "../../../../../groups/group/name";
                            }
                            max-elements 8;
                            ordered-by user;
                            description "Apply a configuration group at this level";
                        }

                        leaf-list apply-groups-exclude {
                            type leafref {
                                path "../../../../../groups/group/name";
                            }
                            max-elements 8;
                            ordered-by user;
                            description "Exclude a configuration group at this level";
                        }

                        container debounce {
                            description "Enter the debounce context";

                            leaf value {
                                type uint32 {
                                    range "2..15";
                                }
                                description "Occurrences in time interval to trigger EHS response";
                            }

                            leaf time {
                                type uint32 {
                                    range "1..604800";
                                }
                                units "seconds";
                                description "Time window for events for EHS to trigger a response";
                            }

                        } // container debounce

                    } // list entry

                } // list chassis

                list debug {
                    key "event";
                    description "Enter the debug list instance";

                    leaf event {
                        type types-log:debug-events;
                        description "Log event as a trigger for one or more EHS handlers";
                    }

                    leaf admin-state {
                        type types-sros:admin-state;
                        default "disable";
                        description "Administrative state of the EHS event trigger";
                    }

                    leaf description {
                        type types-sros:description;
                        description "Text description";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                    list entry {
                        key "id";
                        description "Enter the entry list instance";

                        leaf id {
                            type uint32 {
                                range "1..1500";
                            }
                            description "ID of the EHS event trigger entry";
                        }

                        leaf admin-state {
                            type types-sros:admin-state;
                            default "enable";
                            description "Administrative state of the EHS event trigger entry";
                        }

                        leaf description {
                            type types-sros:description;
                            description "Text description";
                        }

                        leaf filter {
                            type leafref {
                                path "../../../../filter/filter-name";
                            }
                            description "Log filter for EHS event trigger entry";
                        }

                        leaf handler {
                            type leafref {
                                path "../../../../event-handling/handler/name";
                            }
                            description "Event handler for EHS event trigger entry";
                        }

                        leaf-list apply-groups {
                            type leafref {
                                path "../../../../../groups/group/name";
                            }
                            max-elements 8;
                            ordered-by user;
                            description "Apply a configuration group at this level";
                        }

                        leaf-list apply-groups-exclude {
                            type leafref {
                                path "../../../../../groups/group/name";
                            }
                            max-elements 8;
                            ordered-by user;
                            description "Exclude a configuration group at this level";
                        }

                        container debounce {
                            description "Enter the debounce context";

                            leaf value {
                                type uint32 {
                                    range "2..15";
                                }
                                description "Occurrences in time interval to trigger EHS response";
                            }

                            leaf time {
                                type uint32 {
                                    range "1..604800";
                                }
                                units "seconds";
                                description "Time window for events for EHS to trigger a response";
                            }

                        } // container debounce

                    } // list entry

                } // list debug

                list dhcp {
                    key "event";
                    description "Enter the dhcp list instance";

                    leaf event {
                        type types-log:dhcp-events;
                        description "Log event as a trigger for one or more EHS handlers";
                    }

                    leaf admin-state {
                        type types-sros:admin-state;
                        default "disable";
                        description "Administrative state of the EHS event trigger";
                    }

                    leaf description {
                        type types-sros:description;
                        description "Text description";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                    list entry {
                        key "id";
                        description "Enter the entry list instance";

                        leaf id {
                            type uint32 {
                                range "1..1500";
                            }
                            description "ID of the EHS event trigger entry";
                        }

                        leaf admin-state {
                            type types-sros:admin-state;
                            default "enable";
                            description "Administrative state of the EHS event trigger entry";
                        }

                        leaf description {
                            type types-sros:description;
                            description "Text description";
                        }

                        leaf filter {
                            type leafref {
                                path "../../../../filter/filter-name";
                            }
                            description "Log filter for EHS event trigger entry";
                        }

                        leaf handler {
                            type leafref {
                                path "../../../../event-handling/handler/name";
                            }
                            description "Event handler for EHS event trigger entry";
                        }

                        leaf-list apply-groups {
                            type leafref {
                                path "../../../../../groups/group/name";
                            }
                            max-elements 8;
                            ordered-by user;
                            description "Apply a configuration group at this level";
                        }

                        leaf-list apply-groups-exclude {
                            type leafref {
                                path "../../../../../groups/group/name";
                            }
                            max-elements 8;
                            ordered-by user;
                            description "Exclude a configuration group at this level";
                        }

                        container debounce {
                            description "Enter the debounce context";

                            leaf value {
                                type uint32 {
                                    range "2..15";
                                }
                                description "Occurrences in time interval to trigger EHS response";
                            }

                            leaf time {
                                type uint32 {
                                    range "1..604800";
                                }
                                units "seconds";
                                description "Time window for events for EHS to trigger a response";
                            }

                        } // container debounce

                    } // list entry

                } // list dhcp

                list dhcps {
                    key "event";
                    description "Enter the dhcps list instance";

                    leaf event {
                        type types-log:dhcps-events;
                        description "Log event as a trigger for one or more EHS handlers";
                    }

                    leaf admin-state {
                        type types-sros:admin-state;
                        default "disable";
                        description "Administrative state of the EHS event trigger";
                    }

                    leaf description {
                        type types-sros:description;
                        description "Text description";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                    list entry {
                        key "id";
                        description "Enter the entry list instance";

                        leaf id {
                            type uint32 {
                                range "1..1500";
                            }
                            description "ID of the EHS event trigger entry";
                        }

                        leaf admin-state {
                            type types-sros:admin-state;
                            default "enable";
                            description "Administrative state of the EHS event trigger entry";
                        }

                        leaf description {
                            type types-sros:description;
                            description "Text description";
                        }

                        leaf filter {
                            type leafref {
                                path "../../../../filter/filter-name";
                            }
                            description "Log filter for EHS event trigger entry";
                        }

                        leaf handler {
                            type leafref {
                                path "../../../../event-handling/handler/name";
                            }
                            description "Event handler for EHS event trigger entry";
                        }

                        leaf-list apply-groups {
                            type leafref {
                                path "../../../../../groups/group/name";
                            }
                            max-elements 8;
                            ordered-by user;
                            description "Apply a configuration group at this level";
                        }

                        leaf-list apply-groups-exclude {
                            type leafref {
                                path "../../../../../groups/group/name";
                            }
                            max-elements 8;
                            ordered-by user;
                            description "Exclude a configuration group at this level";
                        }

                        container debounce {
                            description "Enter the debounce context";

                            leaf value {
                                type uint32 {
                                    range "2..15";
                                }
                                description "Occurrences in time interval to trigger EHS response";
                            }

                            leaf time {
                                type uint32 {
                                    range "1..604800";
                                }
                                units "seconds";
                                description "Time window for events for EHS to trigger a response";
                            }

                        } // container debounce

                    } // list entry

                } // list dhcps

                list diameter {
                    key "event";
                    description "Enter the diameter list instance";

                    leaf event {
                        type types-log:diameter-events;
                        description "Log event as a trigger for one or more EHS handlers";
                    }

                    leaf admin-state {
                        type types-sros:admin-state;
                        default "disable";
                        description "Administrative state of the EHS event trigger";
                    }

                    leaf description {
                        type types-sros:description;
                        description "Text description";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                    list entry {
                        key "id";
                        description "Enter the entry list instance";

                        leaf id {
                            type uint32 {
                                range "1..1500";
                            }
                            description "ID of the EHS event trigger entry";
                        }

                        leaf admin-state {
                            type types-sros:admin-state;
                            default "enable";
                            description "Administrative state of the EHS event trigger entry";
                        }

                        leaf description {
                            type types-sros:description;
                            description "Text description";
                        }

                        leaf filter {
                            type leafref {
                                path "../../../../filter/filter-name";
                            }
                            description "Log filter for EHS event trigger entry";
                        }

                        leaf handler {
                            type leafref {
                                path "../../../../event-handling/handler/name";
                            }
                            description "Event handler for EHS event trigger entry";
                        }

                        leaf-list apply-groups {
                            type leafref {
                                path "../../../../../groups/group/name";
                            }
                            max-elements 8;
                            ordered-by user;
                            description "Apply a configuration group at this level";
                        }

                        leaf-list apply-groups-exclude {
                            type leafref {
                                path "../../../../../groups/group/name";
                            }
                            max-elements 8;
                            ordered-by user;
                            description "Exclude a configuration group at this level";
                        }

                        container debounce {
                            description "Enter the debounce context";

                            leaf value {
                                type uint32 {
                                    range "2..15";
                                }
                                description "Occurrences in time interval to trigger EHS response";
                            }

                            leaf time {
                                type uint32 {
                                    range "1..604800";
                                }
                                units "seconds";
                                description "Time window for events for EHS to trigger a response";
                            }

                        } // container debounce

                    } // list entry

                } // list diameter

                list dot1x {
                    key "event";
                    description "Enter the dot1x list instance";

                    leaf event {
                        type types-log:dot1x-events;
                        description "Events for dynsvc module";
                    }

                    leaf admin-state {
                        type types-sros:admin-state;
                        default "disable";
                        description "Administrative state of the EHS event trigger";
                    }

                    leaf description {
                        type types-sros:description;
                        description "Text description";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                    list entry {
                        key "id";
                        description "Enter the entry list instance";

                        leaf id {
                            type uint32 {
                                range "1..1500";
                            }
                            description "ID of the EHS event trigger entry";
                        }

                        leaf admin-state {
                            type types-sros:admin-state;
                            default "enable";
                            description "Administrative state of the EHS event trigger entry";
                        }

                        leaf description {
                            type types-sros:description;
                            description "Text description";
                        }

                        leaf filter {
                            type leafref {
                                path "../../../../filter/filter-name";
                            }
                            description "Log filter for EHS event trigger entry";
                        }

                        leaf handler {
                            type leafref {
                                path "../../../../event-handling/handler/name";
                            }
                            description "Event handler for EHS event trigger entry";
                        }

                        leaf-list apply-groups {
                            type leafref {
                                path "../../../../../groups/group/name";
                            }
                            max-elements 8;
                            ordered-by user;
                            description "Apply a configuration group at this level";
                        }

                        leaf-list apply-groups-exclude {
                            type leafref {
                                path "../../../../../groups/group/name";
                            }
                            max-elements 8;
                            ordered-by user;
                            description "Exclude a configuration group at this level";
                        }

                        container debounce {
                            description "Enter the debounce context";

                            leaf value {
                                type uint32 {
                                    range "2..15";
                                }
                                description "Occurrences in time interval to trigger EHS response";
                            }

                            leaf time {
                                type uint32 {
                                    range "1..604800";
                                }
                                units "seconds";
                                description "Time window for events for EHS to trigger a response";
                            }

                        } // container debounce

                    } // list entry

                } // list dot1x

                list dynsvc {
                    key "event";
                    description "Enter the dynsvc list instance";

                    leaf event {
                        type types-log:dynsvc-events;
                        description "Log event as a trigger for one or more EHS handlers";
                    }

                    leaf admin-state {
                        type types-sros:admin-state;
                        default "disable";
                        description "Administrative state of the EHS event trigger";
                    }

                    leaf description {
                        type types-sros:description;
                        description "Text description";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                    list entry {
                        key "id";
                        description "Enter the entry list instance";

                        leaf id {
                            type uint32 {
                                range "1..1500";
                            }
                            description "ID of the EHS event trigger entry";
                        }

                        leaf admin-state {
                            type types-sros:admin-state;
                            default "enable";
                            description "Administrative state of the EHS event trigger entry";
                        }

                        leaf description {
                            type types-sros:description;
                            description "Text description";
                        }

                        leaf filter {
                            type leafref {
                                path "../../../../filter/filter-name";
                            }
                            description "Log filter for EHS event trigger entry";
                        }

                        leaf handler {
                            type leafref {
                                path "../../../../event-handling/handler/name";
                            }
                            description "Event handler for EHS event trigger entry";
                        }

                        leaf-list apply-groups {
                            type leafref {
                                path "../../../../../groups/group/name";
                            }
                            max-elements 8;
                            ordered-by user;
                            description "Apply a configuration group at this level";
                        }

                        leaf-list apply-groups-exclude {
                            type leafref {
                                path "../../../../../groups/group/name";
                            }
                            max-elements 8;
                            ordered-by user;
                            description "Exclude a configuration group at this level";
                        }

                        container debounce {
                            description "Enter the debounce context";

                            leaf value {
                                type uint32 {
                                    range "2..15";
                                }
                                description "Occurrences in time interval to trigger EHS response";
                            }

                            leaf time {
                                type uint32 {
                                    range "1..604800";
                                }
                                units "seconds";
                                description "Time window for events for EHS to trigger a response";
                            }

                        } // container debounce

                    } // list entry

                } // list dynsvc

                list efm-oam {
                    key "event";
                    description "Enter the efm-oam list instance";

                    leaf event {
                        type types-log:efm-oam-events;
                        description "Log event as a trigger for one or more EHS handlers";
                    }

                    leaf admin-state {
                        type types-sros:admin-state;
                        default "disable";
                        description "Administrative state of the EHS event trigger";
                    }

                    leaf description {
                        type types-sros:description;
                        description "Text description";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                    list entry {
                        key "id";
                        description "Enter the entry list instance";

                        leaf id {
                            type uint32 {
                                range "1..1500";
                            }
                            description "ID of the EHS event trigger entry";
                        }

                        leaf admin-state {
                            type types-sros:admin-state;
                            default "enable";
                            description "Administrative state of the EHS event trigger entry";
                        }

                        leaf description {
                            type types-sros:description;
                            description "Text description";
                        }

                        leaf filter {
                            type leafref {
                                path "../../../../filter/filter-name";
                            }
                            description "Log filter for EHS event trigger entry";
                        }

                        leaf handler {
                            type leafref {
                                path "../../../../event-handling/handler/name";
                            }
                            description "Event handler for EHS event trigger entry";
                        }

                        leaf-list apply-groups {
                            type leafref {
                                path "../../../../../groups/group/name";
                            }
                            max-elements 8;
                            ordered-by user;
                            description "Apply a configuration group at this level";
                        }

                        leaf-list apply-groups-exclude {
                            type leafref {
                                path "../../../../../groups/group/name";
                            }
                            max-elements 8;
                            ordered-by user;
                            description "Exclude a configuration group at this level";
                        }

                        container debounce {
                            description "Enter the debounce context";

                            leaf value {
                                type uint32 {
                                    range "2..15";
                                }
                                description "Occurrences in time interval to trigger EHS response";
                            }

                            leaf time {
                                type uint32 {
                                    range "1..604800";
                                }
                                units "seconds";
                                description "Time window for events for EHS to trigger a response";
                            }

                        } // container debounce

                    } // list entry

                } // list efm-oam

                list elmi {
                    key "event";
                    description "Enter the elmi list instance";

                    leaf event {
                        type types-log:elmi-events;
                        description "Log event as a trigger for one or more EHS handlers";
                    }

                    leaf admin-state {
                        type types-sros:admin-state;
                        default "disable";
                        description "Administrative state of the EHS event trigger";
                    }

                    leaf description {
                        type types-sros:description;
                        description "Text description";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                    list entry {
                        key "id";
                        description "Enter the entry list instance";

                        leaf id {
                            type uint32 {
                                range "1..1500";
                            }
                            description "ID of the EHS event trigger entry";
                        }

                        leaf admin-state {
                            type types-sros:admin-state;
                            default "enable";
                            description "Administrative state of the EHS event trigger entry";
                        }

                        leaf description {
                            type types-sros:description;
                            description "Text description";
                        }

                        leaf filter {
                            type leafref {
                                path "../../../../filter/filter-name";
                            }
                            description "Log filter for EHS event trigger entry";
                        }

                        leaf handler {
                            type leafref {
                                path "../../../../event-handling/handler/name";
                            }
                            description "Event handler for EHS event trigger entry";
                        }

                        leaf-list apply-groups {
                            type leafref {
                                path "../../../../../groups/group/name";
                            }
                            max-elements 8;
                            ordered-by user;
                            description "Apply a configuration group at this level";
                        }

                        leaf-list apply-groups-exclude {
                            type leafref {
                                path "../../../../../groups/group/name";
                            }
                            max-elements 8;
                            ordered-by user;
                            description "Exclude a configuration group at this level";
                        }

                        container debounce {
                            description "Enter the debounce context";

                            leaf value {
                                type uint32 {
                                    range "2..15";
                                }
                                description "Occurrences in time interval to trigger EHS response";
                            }

                            leaf time {
                                type uint32 {
                                    range "1..604800";
                                }
                                units "seconds";
                                description "Time window for events for EHS to trigger a response";
                            }

                        } // container debounce

                    } // list entry

                } // list elmi

                list ering {
                    key "event";
                    description "Enter the ering list instance";

                    leaf event {
                        type types-log:ethring-events;
                        description "Log event as a trigger for one or more EHS handlers";
                    }

                    leaf admin-state {
                        type types-sros:admin-state;
                        default "disable";
                        description "Administrative state of the EHS event trigger";
                    }

                    leaf description {
                        type types-sros:description;
                        description "Text description";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                    list entry {
                        key "id";
                        description "Enter the entry list instance";

                        leaf id {
                            type uint32 {
                                range "1..1500";
                            }
                            description "ID of the EHS event trigger entry";
                        }

                        leaf admin-state {
                            type types-sros:admin-state;
                            default "enable";
                            description "Administrative state of the EHS event trigger entry";
                        }

                        leaf description {
                            type types-sros:description;
                            description "Text description";
                        }

                        leaf filter {
                            type leafref {
                                path "../../../../filter/filter-name";
                            }
                            description "Log filter for EHS event trigger entry";
                        }

                        leaf handler {
                            type leafref {
                                path "../../../../event-handling/handler/name";
                            }
                            description "Event handler for EHS event trigger entry";
                        }

                        leaf-list apply-groups {
                            type leafref {
                                path "../../../../../groups/group/name";
                            }
                            max-elements 8;
                            ordered-by user;
                            description "Apply a configuration group at this level";
                        }

                        leaf-list apply-groups-exclude {
                            type leafref {
                                path "../../../../../groups/group/name";
                            }
                            max-elements 8;
                            ordered-by user;
                            description "Exclude a configuration group at this level";
                        }

                        container debounce {
                            description "Enter the debounce context";

                            leaf value {
                                type uint32 {
                                    range "2..15";
                                }
                                description "Occurrences in time interval to trigger EHS response";
                            }

                            leaf time {
                                type uint32 {
                                    range "1..604800";
                                }
                                units "seconds";
                                description "Time window for events for EHS to trigger a response";
                            }

                        } // container debounce

                    } // list entry

                } // list ering

                list eth-cfm {
                    key "event";
                    description "Enter the eth-cfm list instance";

                    leaf event {
                        type types-log:ethcfm-events;
                        description "Log event as a trigger for one or more EHS handlers";
                    }

                    leaf admin-state {
                        type types-sros:admin-state;
                        default "disable";
                        description "Administrative state of the EHS event trigger";
                    }

                    leaf description {
                        type types-sros:description;
                        description "Text description";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                    list entry {
                        key "id";
                        description "Enter the entry list instance";

                        leaf id {
                            type uint32 {
                                range "1..1500";
                            }
                            description "ID of the EHS event trigger entry";
                        }

                        leaf admin-state {
                            type types-sros:admin-state;
                            default "enable";
                            description "Administrative state of the EHS event trigger entry";
                        }

                        leaf description {
                            type types-sros:description;
                            description "Text description";
                        }

                        leaf filter {
                            type leafref {
                                path "../../../../filter/filter-name";
                            }
                            description "Log filter for EHS event trigger entry";
                        }

                        leaf handler {
                            type leafref {
                                path "../../../../event-handling/handler/name";
                            }
                            description "Event handler for EHS event trigger entry";
                        }

                        leaf-list apply-groups {
                            type leafref {
                                path "../../../../../groups/group/name";
                            }
                            max-elements 8;
                            ordered-by user;
                            description "Apply a configuration group at this level";
                        }

                        leaf-list apply-groups-exclude {
                            type leafref {
                                path "../../../../../groups/group/name";
                            }
                            max-elements 8;
                            ordered-by user;
                            description "Exclude a configuration group at this level";
                        }

                        container debounce {
                            description "Enter the debounce context";

                            leaf value {
                                type uint32 {
                                    range "2..15";
                                }
                                description "Occurrences in time interval to trigger EHS response";
                            }

                            leaf time {
                                type uint32 {
                                    range "1..604800";
                                }
                                units "seconds";
                                description "Time window for events for EHS to trigger a response";
                            }

                        } // container debounce

                    } // list entry

                } // list eth-cfm

                list etun {
                    key "event";
                    description "Enter the etun list instance";

                    leaf event {
                        type types-log:etun-events;
                        description "Log event as a trigger for one or more EHS handlers";
                    }

                    leaf admin-state {
                        type types-sros:admin-state;
                        default "disable";
                        description "Administrative state of the EHS event trigger";
                    }

                    leaf description {
                        type types-sros:description;
                        description "Text description";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                    list entry {
                        key "id";
                        description "Enter the entry list instance";

                        leaf id {
                            type uint32 {
                                range "1..1500";
                            }
                            description "ID of the EHS event trigger entry";
                        }

                        leaf admin-state {
                            type types-sros:admin-state;
                            default "enable";
                            description "Administrative state of the EHS event trigger entry";
                        }

                        leaf description {
                            type types-sros:description;
                            description "Text description";
                        }

                        leaf filter {
                            type leafref {
                                path "../../../../filter/filter-name";
                            }
                            description "Log filter for EHS event trigger entry";
                        }

                        leaf handler {
                            type leafref {
                                path "../../../../event-handling/handler/name";
                            }
                            description "Event handler for EHS event trigger entry";
                        }

                        leaf-list apply-groups {
                            type leafref {
                                path "../../../../../groups/group/name";
                            }
                            max-elements 8;
                            ordered-by user;
                            description "Apply a configuration group at this level";
                        }

                        leaf-list apply-groups-exclude {
                            type leafref {
                                path "../../../../../groups/group/name";
                            }
                            max-elements 8;
                            ordered-by user;
                            description "Exclude a configuration group at this level";
                        }

                        container debounce {
                            description "Enter the debounce context";

                            leaf value {
                                type uint32 {
                                    range "2..15";
                                }
                                description "Occurrences in time interval to trigger EHS response";
                            }

                            leaf time {
                                type uint32 {
                                    range "1..604800";
                                }
                                units "seconds";
                                description "Time window for events for EHS to trigger a response";
                            }

                        } // container debounce

                    } // list entry

                } // list etun

                list filter {
                    key "event";
                    description "Enter the filter list instance";

                    leaf event {
                        type types-log:filter-events;
                        description "Log event as a trigger for one or more EHS handlers";
                    }

                    leaf admin-state {
                        type types-sros:admin-state;
                        default "disable";
                        description "Administrative state of the EHS event trigger";
                    }

                    leaf description {
                        type types-sros:description;
                        description "Text description";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                    list entry {
                        key "id";
                        description "Enter the entry list instance";

                        leaf id {
                            type uint32 {
                                range "1..1500";
                            }
                            description "ID of the EHS event trigger entry";
                        }

                        leaf admin-state {
                            type types-sros:admin-state;
                            default "enable";
                            description "Administrative state of the EHS event trigger entry";
                        }

                        leaf description {
                            type types-sros:description;
                            description "Text description";
                        }

                        leaf filter {
                            type leafref {
                                path "../../../../filter/filter-name";
                            }
                            description "Log filter for EHS event trigger entry";
                        }

                        leaf handler {
                            type leafref {
                                path "../../../../event-handling/handler/name";
                            }
                            description "Event handler for EHS event trigger entry";
                        }

                        leaf-list apply-groups {
                            type leafref {
                                path "../../../../../groups/group/name";
                            }
                            max-elements 8;
                            ordered-by user;
                            description "Apply a configuration group at this level";
                        }

                        leaf-list apply-groups-exclude {
                            type leafref {
                                path "../../../../../groups/group/name";
                            }
                            max-elements 8;
                            ordered-by user;
                            description "Exclude a configuration group at this level";
                        }

                        container debounce {
                            description "Enter the debounce context";

                            leaf value {
                                type uint32 {
                                    range "2..15";
                                }
                                description "Occurrences in time interval to trigger EHS response";
                            }

                            leaf time {
                                type uint32 {
                                    range "1..604800";
                                }
                                units "seconds";
                                description "Time window for events for EHS to trigger a response";
                            }

                        } // container debounce

                    } // list entry

                } // list filter

                list gsmp {
                    key "event";
                    description "Enter the gsmp list instance";

                    leaf event {
                        type types-log:gsmp-events;
                        description "Log event as a trigger for one or more EHS handlers";
                    }

                    leaf admin-state {
                        type types-sros:admin-state;
                        default "disable";
                        description "Administrative state of the EHS event trigger";
                    }

                    leaf description {
                        type types-sros:description;
                        description "Text description";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                    list entry {
                        key "id";
                        description "Enter the entry list instance";

                        leaf id {
                            type uint32 {
                                range "1..1500";
                            }
                            description "ID of the EHS event trigger entry";
                        }

                        leaf admin-state {
                            type types-sros:admin-state;
                            default "enable";
                            description "Administrative state of the EHS event trigger entry";
                        }

                        leaf description {
                            type types-sros:description;
                            description "Text description";
                        }

                        leaf filter {
                            type leafref {
                                path "../../../../filter/filter-name";
                            }
                            description "Log filter for EHS event trigger entry";
                        }

                        leaf handler {
                            type leafref {
                                path "../../../../event-handling/handler/name";
                            }
                            description "Event handler for EHS event trigger entry";
                        }

                        leaf-list apply-groups {
                            type leafref {
                                path "../../../../../groups/group/name";
                            }
                            max-elements 8;
                            ordered-by user;
                            description "Apply a configuration group at this level";
                        }

                        leaf-list apply-groups-exclude {
                            type leafref {
                                path "../../../../../groups/group/name";
                            }
                            max-elements 8;
                            ordered-by user;
                            description "Exclude a configuration group at this level";
                        }

                        container debounce {
                            description "Enter the debounce context";

                            leaf value {
                                type uint32 {
                                    range "2..15";
                                }
                                description "Occurrences in time interval to trigger EHS response";
                            }

                            leaf time {
                                type uint32 {
                                    range "1..604800";
                                }
                                units "seconds";
                                description "Time window for events for EHS to trigger a response";
                            }

                        } // container debounce

                    } // list entry

                } // list gsmp

                list igmp {
                    key "event";
                    description "Enter the igmp list instance";

                    leaf event {
                        type types-log:igmp-events;
                        description "Log event as a trigger for one or more EHS handlers";
                    }

                    leaf admin-state {
                        type types-sros:admin-state;
                        default "disable";
                        description "Administrative state of the EHS event trigger";
                    }

                    leaf description {
                        type types-sros:description;
                        description "Text description";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                    list entry {
                        key "id";
                        description "Enter the entry list instance";

                        leaf id {
                            type uint32 {
                                range "1..1500";
                            }
                            description "ID of the EHS event trigger entry";
                        }

                        leaf admin-state {
                            type types-sros:admin-state;
                            default "enable";
                            description "Administrative state of the EHS event trigger entry";
                        }

                        leaf description {
                            type types-sros:description;
                            description "Text description";
                        }

                        leaf filter {
                            type leafref {
                                path "../../../../filter/filter-name";
                            }
                            description "Log filter for EHS event trigger entry";
                        }

                        leaf handler {
                            type leafref {
                                path "../../../../event-handling/handler/name";
                            }
                            description "Event handler for EHS event trigger entry";
                        }

                        leaf-list apply-groups {
                            type leafref {
                                path "../../../../../groups/group/name";
                            }
                            max-elements 8;
                            ordered-by user;
                            description "Apply a configuration group at this level";
                        }

                        leaf-list apply-groups-exclude {
                            type leafref {
                                path "../../../../../groups/group/name";
                            }
                            max-elements 8;
                            ordered-by user;
                            description "Exclude a configuration group at this level";
                        }

                        container debounce {
                            description "Enter the debounce context";

                            leaf value {
                                type uint32 {
                                    range "2..15";
                                }
                                description "Occurrences in time interval to trigger EHS response";
                            }

                            leaf time {
                                type uint32 {
                                    range "1..604800";
                                }
                                units "seconds";
                                description "Time window for events for EHS to trigger a response";
                            }

                        } // container debounce

                    } // list entry

                } // list igmp

                list igmp-snooping {
                    key "event";
                    description "Enter the igmp-snooping list instance";

                    leaf event {
                        type types-log:igmp-snooping-events;
                        description "Log event as a trigger for one or more EHS handlers";
                    }

                    leaf admin-state {
                        type types-sros:admin-state;
                        default "disable";
                        description "Administrative state of the EHS event trigger";
                    }

                    leaf description {
                        type types-sros:description;
                        description "Text description";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                    list entry {
                        key "id";
                        description "Enter the entry list instance";

                        leaf id {
                            type uint32 {
                                range "1..1500";
                            }
                            description "ID of the EHS event trigger entry";
                        }

                        leaf admin-state {
                            type types-sros:admin-state;
                            default "enable";
                            description "Administrative state of the EHS event trigger entry";
                        }

                        leaf description {
                            type types-sros:description;
                            description "Text description";
                        }

                        leaf filter {
                            type leafref {
                                path "../../../../filter/filter-name";
                            }
                            description "Log filter for EHS event trigger entry";
                        }

                        leaf handler {
                            type leafref {
                                path "../../../../event-handling/handler/name";
                            }
                            description "Event handler for EHS event trigger entry";
                        }

                        leaf-list apply-groups {
                            type leafref {
                                path "../../../../../groups/group/name";
                            }
                            max-elements 8;
                            ordered-by user;
                            description "Apply a configuration group at this level";
                        }

                        leaf-list apply-groups-exclude {
                            type leafref {
                                path "../../../../../groups/group/name";
                            }
                            max-elements 8;
                            ordered-by user;
                            description "Exclude a configuration group at this level";
                        }

                        container debounce {
                            description "Enter the debounce context";

                            leaf value {
                                type uint32 {
                                    range "2..15";
                                }
                                description "Occurrences in time interval to trigger EHS response";
                            }

                            leaf time {
                                type uint32 {
                                    range "1..604800";
                                }
                                units "seconds";
                                description "Time window for events for EHS to trigger a response";
                            }

                        } // container debounce

                    } // list entry

                } // list igmp-snooping

                list ip {
                    key "event";
                    description "Enter the ip list instance";

                    leaf event {
                        type types-log:ip-events;
                        description "Log event as a trigger for one or more EHS handlers";
                    }

                    leaf admin-state {
                        type types-sros:admin-state;
                        default "disable";
                        description "Administrative state of the EHS event trigger";
                    }

                    leaf description {
                        type types-sros:description;
                        description "Text description";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                    list entry {
                        key "id";
                        description "Enter the entry list instance";

                        leaf id {
                            type uint32 {
                                range "1..1500";
                            }
                            description "ID of the EHS event trigger entry";
                        }

                        leaf admin-state {
                            type types-sros:admin-state;
                            default "enable";
                            description "Administrative state of the EHS event trigger entry";
                        }

                        leaf description {
                            type types-sros:description;
                            description "Text description";
                        }

                        leaf filter {
                            type leafref {
                                path "../../../../filter/filter-name";
                            }
                            description "Log filter for EHS event trigger entry";
                        }

                        leaf handler {
                            type leafref {
                                path "../../../../event-handling/handler/name";
                            }
                            description "Event handler for EHS event trigger entry";
                        }

                        leaf-list apply-groups {
                            type leafref {
                                path "../../../../../groups/group/name";
                            }
                            max-elements 8;
                            ordered-by user;
                            description "Apply a configuration group at this level";
                        }

                        leaf-list apply-groups-exclude {
                            type leafref {
                                path "../../../../../groups/group/name";
                            }
                            max-elements 8;
                            ordered-by user;
                            description "Exclude a configuration group at this level";
                        }

                        container debounce {
                            description "Enter the debounce context";

                            leaf value {
                                type uint32 {
                                    range "2..15";
                                }
                                description "Occurrences in time interval to trigger EHS response";
                            }

                            leaf time {
                                type uint32 {
                                    range "1..604800";
                                }
                                units "seconds";
                                description "Time window for events for EHS to trigger a response";
                            }

                        } // container debounce

                    } // list entry

                } // list ip

                list ipsec {
                    key "event";
                    description "Enter the ipsec list instance";

                    leaf event {
                        type types-log:ipsec-events;
                        description "Log event as a trigger for one or more EHS handlers";
                    }

                    leaf admin-state {
                        type types-sros:admin-state;
                        default "disable";
                        description "Administrative state of the EHS event trigger";
                    }

                    leaf description {
                        type types-sros:description;
                        description "Text description";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                    list entry {
                        key "id";
                        description "Enter the entry list instance";

                        leaf id {
                            type uint32 {
                                range "1..1500";
                            }
                            description "ID of the EHS event trigger entry";
                        }

                        leaf admin-state {
                            type types-sros:admin-state;
                            default "enable";
                            description "Administrative state of the EHS event trigger entry";
                        }

                        leaf description {
                            type types-sros:description;
                            description "Text description";
                        }

                        leaf filter {
                            type leafref {
                                path "../../../../filter/filter-name";
                            }
                            description "Log filter for EHS event trigger entry";
                        }

                        leaf handler {
                            type leafref {
                                path "../../../../event-handling/handler/name";
                            }
                            description "Event handler for EHS event trigger entry";
                        }

                        leaf-list apply-groups {
                            type leafref {
                                path "../../../../../groups/group/name";
                            }
                            max-elements 8;
                            ordered-by user;
                            description "Apply a configuration group at this level";
                        }

                        leaf-list apply-groups-exclude {
                            type leafref {
                                path "../../../../../groups/group/name";
                            }
                            max-elements 8;
                            ordered-by user;
                            description "Exclude a configuration group at this level";
                        }

                        container debounce {
                            description "Enter the debounce context";

                            leaf value {
                                type uint32 {
                                    range "2..15";
                                }
                                description "Occurrences in time interval to trigger EHS response";
                            }

                            leaf time {
                                type uint32 {
                                    range "1..604800";
                                }
                                units "seconds";
                                description "Time window for events for EHS to trigger a response";
                            }

                        } // container debounce

                    } // list entry

                } // list ipsec

                list isis {
                    key "event";
                    description "Enter the isis list instance";

                    leaf event {
                        type types-log:isis-events;
                        description "Log event as a trigger for one or more EHS handlers";
                    }

                    leaf admin-state {
                        type types-sros:admin-state;
                        default "disable";
                        description "Administrative state of the EHS event trigger";
                    }

                    leaf description {
                        type types-sros:description;
                        description "Text description";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                    list entry {
                        key "id";
                        description "Enter the entry list instance";

                        leaf id {
                            type uint32 {
                                range "1..1500";
                            }
                            description "ID of the EHS event trigger entry";
                        }

                        leaf admin-state {
                            type types-sros:admin-state;
                            default "enable";
                            description "Administrative state of the EHS event trigger entry";
                        }

                        leaf description {
                            type types-sros:description;
                            description "Text description";
                        }

                        leaf filter {
                            type leafref {
                                path "../../../../filter/filter-name";
                            }
                            description "Log filter for EHS event trigger entry";
                        }

                        leaf handler {
                            type leafref {
                                path "../../../../event-handling/handler/name";
                            }
                            description "Event handler for EHS event trigger entry";
                        }

                        leaf-list apply-groups {
                            type leafref {
                                path "../../../../../groups/group/name";
                            }
                            max-elements 8;
                            ordered-by user;
                            description "Apply a configuration group at this level";
                        }

                        leaf-list apply-groups-exclude {
                            type leafref {
                                path "../../../../../groups/group/name";
                            }
                            max-elements 8;
                            ordered-by user;
                            description "Exclude a configuration group at this level";
                        }

                        container debounce {
                            description "Enter the debounce context";

                            leaf value {
                                type uint32 {
                                    range "2..15";
                                }
                                description "Occurrences in time interval to trigger EHS response";
                            }

                            leaf time {
                                type uint32 {
                                    range "1..604800";
                                }
                                units "seconds";
                                description "Time window for events for EHS to trigger a response";
                            }

                        } // container debounce

                    } // list entry

                } // list isis

                list l2tp {
                    key "event";
                    description "Enter the l2tp list instance";

                    leaf event {
                        type types-log:l2tp-events;
                        description "Log event as a trigger for one or more EHS handlers";
                    }

                    leaf admin-state {
                        type types-sros:admin-state;
                        default "disable";
                        description "Administrative state of the EHS event trigger";
                    }

                    leaf description {
                        type types-sros:description;
                        description "Text description";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                    list entry {
                        key "id";
                        description "Enter the entry list instance";

                        leaf id {
                            type uint32 {
                                range "1..1500";
                            }
                            description "ID of the EHS event trigger entry";
                        }

                        leaf admin-state {
                            type types-sros:admin-state;
                            default "enable";
                            description "Administrative state of the EHS event trigger entry";
                        }

                        leaf description {
                            type types-sros:description;
                            description "Text description";
                        }

                        leaf filter {
                            type leafref {
                                path "../../../../filter/filter-name";
                            }
                            description "Log filter for EHS event trigger entry";
                        }

                        leaf handler {
                            type leafref {
                                path "../../../../event-handling/handler/name";
                            }
                            description "Event handler for EHS event trigger entry";
                        }

                        leaf-list apply-groups {
                            type leafref {
                                path "../../../../../groups/group/name";
                            }
                            max-elements 8;
                            ordered-by user;
                            description "Apply a configuration group at this level";
                        }

                        leaf-list apply-groups-exclude {
                            type leafref {
                                path "../../../../../groups/group/name";
                            }
                            max-elements 8;
                            ordered-by user;
                            description "Exclude a configuration group at this level";
                        }

                        container debounce {
                            description "Enter the debounce context";

                            leaf value {
                                type uint32 {
                                    range "2..15";
                                }
                                description "Occurrences in time interval to trigger EHS response";
                            }

                            leaf time {
                                type uint32 {
                                    range "1..604800";
                                }
                                units "seconds";
                                description "Time window for events for EHS to trigger a response";
                            }

                        } // container debounce

                    } // list entry

                } // list l2tp

                list lag {
                    key "event";
                    description "Enter the lag list instance";

                    leaf event {
                        type types-log:lag-events;
                        description "Log event as a trigger for one or more EHS handlers";
                    }

                    leaf admin-state {
                        type types-sros:admin-state;
                        default "disable";
                        description "Administrative state of the EHS event trigger";
                    }

                    leaf description {
                        type types-sros:description;
                        description "Text description";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                    list entry {
                        key "id";
                        description "Enter the entry list instance";

                        leaf id {
                            type uint32 {
                                range "1..1500";
                            }
                            description "ID of the EHS event trigger entry";
                        }

                        leaf admin-state {
                            type types-sros:admin-state;
                            default "enable";
                            description "Administrative state of the EHS event trigger entry";
                        }

                        leaf description {
                            type types-sros:description;
                            description "Text description";
                        }

                        leaf filter {
                            type leafref {
                                path "../../../../filter/filter-name";
                            }
                            description "Log filter for EHS event trigger entry";
                        }

                        leaf handler {
                            type leafref {
                                path "../../../../event-handling/handler/name";
                            }
                            description "Event handler for EHS event trigger entry";
                        }

                        leaf-list apply-groups {
                            type leafref {
                                path "../../../../../groups/group/name";
                            }
                            max-elements 8;
                            ordered-by user;
                            description "Apply a configuration group at this level";
                        }

                        leaf-list apply-groups-exclude {
                            type leafref {
                                path "../../../../../groups/group/name";
                            }
                            max-elements 8;
                            ordered-by user;
                            description "Exclude a configuration group at this level";
                        }

                        container debounce {
                            description "Enter the debounce context";

                            leaf value {
                                type uint32 {
                                    range "2..15";
                                }
                                description "Occurrences in time interval to trigger EHS response";
                            }

                            leaf time {
                                type uint32 {
                                    range "1..604800";
                                }
                                units "seconds";
                                description "Time window for events for EHS to trigger a response";
                            }

                        } // container debounce

                    } // list entry

                } // list lag

                list ldap {
                    key "event";
                    description "Enter the ldap list instance";

                    leaf event {
                        type types-log:ldap-events;
                        description "Log event as a trigger for one or more EHS handlers";
                    }

                    leaf admin-state {
                        type types-sros:admin-state;
                        default "disable";
                        description "Administrative state of the EHS event trigger";
                    }

                    leaf description {
                        type types-sros:description;
                        description "Text description";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                    list entry {
                        key "id";
                        description "Enter the entry list instance";

                        leaf id {
                            type uint32 {
                                range "1..1500";
                            }
                            description "ID of the EHS event trigger entry";
                        }

                        leaf admin-state {
                            type types-sros:admin-state;
                            default "enable";
                            description "Administrative state of the EHS event trigger entry";
                        }

                        leaf description {
                            type types-sros:description;
                            description "Text description";
                        }

                        leaf filter {
                            type leafref {
                                path "../../../../filter/filter-name";
                            }
                            description "Log filter for EHS event trigger entry";
                        }

                        leaf handler {
                            type leafref {
                                path "../../../../event-handling/handler/name";
                            }
                            description "Event handler for EHS event trigger entry";
                        }

                        leaf-list apply-groups {
                            type leafref {
                                path "../../../../../groups/group/name";
                            }
                            max-elements 8;
                            ordered-by user;
                            description "Apply a configuration group at this level";
                        }

                        leaf-list apply-groups-exclude {
                            type leafref {
                                path "../../../../../groups/group/name";
                            }
                            max-elements 8;
                            ordered-by user;
                            description "Exclude a configuration group at this level";
                        }

                        container debounce {
                            description "Enter the debounce context";

                            leaf value {
                                type uint32 {
                                    range "2..15";
                                }
                                description "Occurrences in time interval to trigger EHS response";
                            }

                            leaf time {
                                type uint32 {
                                    range "1..604800";
                                }
                                units "seconds";
                                description "Time window for events for EHS to trigger a response";
                            }

                        } // container debounce

                    } // list entry

                } // list ldap

                list ldp {
                    key "event";
                    description "Enter the ldp list instance";

                    leaf event {
                        type types-log:ldp-events;
                        description "Log event as a trigger for one or more EHS handlers";
                    }

                    leaf admin-state {
                        type types-sros:admin-state;
                        default "disable";
                        description "Administrative state of the EHS event trigger";
                    }

                    leaf description {
                        type types-sros:description;
                        description "Text description";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                    list entry {
                        key "id";
                        description "Enter the entry list instance";

                        leaf id {
                            type uint32 {
                                range "1..1500";
                            }
                            description "ID of the EHS event trigger entry";
                        }

                        leaf admin-state {
                            type types-sros:admin-state;
                            default "enable";
                            description "Administrative state of the EHS event trigger entry";
                        }

                        leaf description {
                            type types-sros:description;
                            description "Text description";
                        }

                        leaf filter {
                            type leafref {
                                path "../../../../filter/filter-name";
                            }
                            description "Log filter for EHS event trigger entry";
                        }

                        leaf handler {
                            type leafref {
                                path "../../../../event-handling/handler/name";
                            }
                            description "Event handler for EHS event trigger entry";
                        }

                        leaf-list apply-groups {
                            type leafref {
                                path "../../../../../groups/group/name";
                            }
                            max-elements 8;
                            ordered-by user;
                            description "Apply a configuration group at this level";
                        }

                        leaf-list apply-groups-exclude {
                            type leafref {
                                path "../../../../../groups/group/name";
                            }
                            max-elements 8;
                            ordered-by user;
                            description "Exclude a configuration group at this level";
                        }

                        container debounce {
                            description "Enter the debounce context";

                            leaf value {
                                type uint32 {
                                    range "2..15";
                                }
                                description "Occurrences in time interval to trigger EHS response";
                            }

                            leaf time {
                                type uint32 {
                                    range "1..604800";
                                }
                                units "seconds";
                                description "Time window for events for EHS to trigger a response";
                            }

                        } // container debounce

                    } // list entry

                } // list ldp

                list li {
                    key "event";
                    description "Enter the li list instance";

                    leaf event {
                        type types-log:li-events;
                        description "Log event as a trigger for one or more EHS handlers";
                    }

                    leaf admin-state {
                        type types-sros:admin-state;
                        default "disable";
                        description "Administrative state of the EHS event trigger";
                    }

                    leaf description {
                        type types-sros:description;
                        description "Text description";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                    list entry {
                        key "id";
                        description "Enter the entry list instance";

                        leaf id {
                            type uint32 {
                                range "1..1500";
                            }
                            description "ID of the EHS event trigger entry";
                        }

                        leaf admin-state {
                            type types-sros:admin-state;
                            default "enable";
                            description "Administrative state of the EHS event trigger entry";
                        }

                        leaf description {
                            type types-sros:description;
                            description "Text description";
                        }

                        leaf filter {
                            type leafref {
                                path "../../../../filter/filter-name";
                            }
                            description "Log filter for EHS event trigger entry";
                        }

                        leaf handler {
                            type leafref {
                                path "../../../../event-handling/handler/name";
                            }
                            description "Event handler for EHS event trigger entry";
                        }

                        leaf-list apply-groups {
                            type leafref {
                                path "../../../../../groups/group/name";
                            }
                            max-elements 8;
                            ordered-by user;
                            description "Apply a configuration group at this level";
                        }

                        leaf-list apply-groups-exclude {
                            type leafref {
                                path "../../../../../groups/group/name";
                            }
                            max-elements 8;
                            ordered-by user;
                            description "Exclude a configuration group at this level";
                        }

                        container debounce {
                            description "Enter the debounce context";

                            leaf value {
                                type uint32 {
                                    range "2..15";
                                }
                                description "Occurrences in time interval to trigger EHS response";
                            }

                            leaf time {
                                type uint32 {
                                    range "1..604800";
                                }
                                units "seconds";
                                description "Time window for events for EHS to trigger a response";
                            }

                        } // container debounce

                    } // list entry

                } // list li

                list lldp {
                    key "event";
                    description "Enter the lldp list instance";

                    leaf event {
                        type types-log:lldp-events;
                        description "Log event as a trigger for one or more EHS handlers";
                    }

                    leaf admin-state {
                        type types-sros:admin-state;
                        default "disable";
                        description "Administrative state of the EHS event trigger";
                    }

                    leaf description {
                        type types-sros:description;
                        description "Text description";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                    list entry {
                        key "id";
                        description "Enter the entry list instance";

                        leaf id {
                            type uint32 {
                                range "1..1500";
                            }
                            description "ID of the EHS event trigger entry";
                        }

                        leaf admin-state {
                            type types-sros:admin-state;
                            default "enable";
                            description "Administrative state of the EHS event trigger entry";
                        }

                        leaf description {
                            type types-sros:description;
                            description "Text description";
                        }

                        leaf filter {
                            type leafref {
                                path "../../../../filter/filter-name";
                            }
                            description "Log filter for EHS event trigger entry";
                        }

                        leaf handler {
                            type leafref {
                                path "../../../../event-handling/handler/name";
                            }
                            description "Event handler for EHS event trigger entry";
                        }

                        leaf-list apply-groups {
                            type leafref {
                                path "../../../../../groups/group/name";
                            }
                            max-elements 8;
                            ordered-by user;
                            description "Apply a configuration group at this level";
                        }

                        leaf-list apply-groups-exclude {
                            type leafref {
                                path "../../../../../groups/group/name";
                            }
                            max-elements 8;
                            ordered-by user;
                            description "Exclude a configuration group at this level";
                        }

                        container debounce {
                            description "Enter the debounce context";

                            leaf value {
                                type uint32 {
                                    range "2..15";
                                }
                                description "Occurrences in time interval to trigger EHS response";
                            }

                            leaf time {
                                type uint32 {
                                    range "1..604800";
                                }
                                units "seconds";
                                description "Time window for events for EHS to trigger a response";
                            }

                        } // container debounce

                    } // list entry

                } // list lldp

                list logger {
                    key "event";
                    description "Enter the logger list instance";

                    leaf event {
                        type types-log:logger-events;
                        description "Log event as a trigger for one or more EHS handlers";
                    }

                    leaf admin-state {
                        type types-sros:admin-state;
                        default "disable";
                        description "Administrative state of the EHS event trigger";
                    }

                    leaf description {
                        type types-sros:description;
                        description "Text description";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                    list entry {
                        key "id";
                        description "Enter the entry list instance";

                        leaf id {
                            type uint32 {
                                range "1..1500";
                            }
                            description "ID of the EHS event trigger entry";
                        }

                        leaf admin-state {
                            type types-sros:admin-state;
                            default "enable";
                            description "Administrative state of the EHS event trigger entry";
                        }

                        leaf description {
                            type types-sros:description;
                            description "Text description";
                        }

                        leaf filter {
                            type leafref {
                                path "../../../../filter/filter-name";
                            }
                            description "Log filter for EHS event trigger entry";
                        }

                        leaf handler {
                            type leafref {
                                path "../../../../event-handling/handler/name";
                            }
                            description "Event handler for EHS event trigger entry";
                        }

                        leaf-list apply-groups {
                            type leafref {
                                path "../../../../../groups/group/name";
                            }
                            max-elements 8;
                            ordered-by user;
                            description "Apply a configuration group at this level";
                        }

                        leaf-list apply-groups-exclude {
                            type leafref {
                                path "../../../../../groups/group/name";
                            }
                            max-elements 8;
                            ordered-by user;
                            description "Exclude a configuration group at this level";
                        }

                        container debounce {
                            description "Enter the debounce context";

                            leaf value {
                                type uint32 {
                                    range "2..15";
                                }
                                description "Occurrences in time interval to trigger EHS response";
                            }

                            leaf time {
                                type uint32 {
                                    range "1..604800";
                                }
                                units "seconds";
                                description "Time window for events for EHS to trigger a response";
                            }

                        } // container debounce

                    } // list entry

                } // list logger

                list macsec {
                    key "event";
                    description "Enter the macsec list instance";

                    leaf event {
                        type types-log:macsec-events;
                        description "Log event as a trigger for one or more EHS handlers";
                    }

                    leaf admin-state {
                        type types-sros:admin-state;
                        default "disable";
                        description "Administrative state of the EHS event trigger";
                    }

                    leaf description {
                        type types-sros:description;
                        description "Text description";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                    list entry {
                        key "id";
                        description "Enter the entry list instance";

                        leaf id {
                            type uint32 {
                                range "1..1500";
                            }
                            description "ID of the EHS event trigger entry";
                        }

                        leaf admin-state {
                            type types-sros:admin-state;
                            default "enable";
                            description "Administrative state of the EHS event trigger entry";
                        }

                        leaf description {
                            type types-sros:description;
                            description "Text description";
                        }

                        leaf filter {
                            type leafref {
                                path "../../../../filter/filter-name";
                            }
                            description "Log filter for EHS event trigger entry";
                        }

                        leaf handler {
                            type leafref {
                                path "../../../../event-handling/handler/name";
                            }
                            description "Event handler for EHS event trigger entry";
                        }

                        leaf-list apply-groups {
                            type leafref {
                                path "../../../../../groups/group/name";
                            }
                            max-elements 8;
                            ordered-by user;
                            description "Apply a configuration group at this level";
                        }

                        leaf-list apply-groups-exclude {
                            type leafref {
                                path "../../../../../groups/group/name";
                            }
                            max-elements 8;
                            ordered-by user;
                            description "Exclude a configuration group at this level";
                        }

                        container debounce {
                            description "Enter the debounce context";

                            leaf value {
                                type uint32 {
                                    range "2..15";
                                }
                                description "Occurrences in time interval to trigger EHS response";
                            }

                            leaf time {
                                type uint32 {
                                    range "1..604800";
                                }
                                units "seconds";
                                description "Time window for events for EHS to trigger a response";
                            }

                        } // container debounce

                    } // list entry

                } // list macsec

                list mcpath {
                    key "event";
                    description "Enter the mcpath list instance";

                    leaf event {
                        type types-log:mcpath-events;
                        description "Log event as a trigger for one or more EHS handlers";
                    }

                    leaf admin-state {
                        type types-sros:admin-state;
                        default "disable";
                        description "Administrative state of the EHS event trigger";
                    }

                    leaf description {
                        type types-sros:description;
                        description "Text description";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                    list entry {
                        key "id";
                        description "Enter the entry list instance";

                        leaf id {
                            type uint32 {
                                range "1..1500";
                            }
                            description "ID of the EHS event trigger entry";
                        }

                        leaf admin-state {
                            type types-sros:admin-state;
                            default "enable";
                            description "Administrative state of the EHS event trigger entry";
                        }

                        leaf description {
                            type types-sros:description;
                            description "Text description";
                        }

                        leaf filter {
                            type leafref {
                                path "../../../../filter/filter-name";
                            }
                            description "Log filter for EHS event trigger entry";
                        }

                        leaf handler {
                            type leafref {
                                path "../../../../event-handling/handler/name";
                            }
                            description "Event handler for EHS event trigger entry";
                        }

                        leaf-list apply-groups {
                            type leafref {
                                path "../../../../../groups/group/name";
                            }
                            max-elements 8;
                            ordered-by user;
                            description "Apply a configuration group at this level";
                        }

                        leaf-list apply-groups-exclude {
                            type leafref {
                                path "../../../../../groups/group/name";
                            }
                            max-elements 8;
                            ordered-by user;
                            description "Exclude a configuration group at this level";
                        }

                        container debounce {
                            description "Enter the debounce context";

                            leaf value {
                                type uint32 {
                                    range "2..15";
                                }
                                description "Occurrences in time interval to trigger EHS response";
                            }

                            leaf time {
                                type uint32 {
                                    range "1..604800";
                                }
                                units "seconds";
                                description "Time window for events for EHS to trigger a response";
                            }

                        } // container debounce

                    } // list entry

                } // list mcpath

                list mc-redundancy {
                    key "event";
                    description "Enter the mc-redundancy list instance";

                    leaf event {
                        type types-log:mc-redundancy-events;
                        description "Log event as a trigger for one or more EHS handlers";
                    }

                    leaf admin-state {
                        type types-sros:admin-state;
                        default "disable";
                        description "Administrative state of the EHS event trigger";
                    }

                    leaf description {
                        type types-sros:description;
                        description "Text description";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                    list entry {
                        key "id";
                        description "Enter the entry list instance";

                        leaf id {
                            type uint32 {
                                range "1..1500";
                            }
                            description "ID of the EHS event trigger entry";
                        }

                        leaf admin-state {
                            type types-sros:admin-state;
                            default "enable";
                            description "Administrative state of the EHS event trigger entry";
                        }

                        leaf description {
                            type types-sros:description;
                            description "Text description";
                        }

                        leaf filter {
                            type leafref {
                                path "../../../../filter/filter-name";
                            }
                            description "Log filter for EHS event trigger entry";
                        }

                        leaf handler {
                            type leafref {
                                path "../../../../event-handling/handler/name";
                            }
                            description "Event handler for EHS event trigger entry";
                        }

                        leaf-list apply-groups {
                            type leafref {
                                path "../../../../../groups/group/name";
                            }
                            max-elements 8;
                            ordered-by user;
                            description "Apply a configuration group at this level";
                        }

                        leaf-list apply-groups-exclude {
                            type leafref {
                                path "../../../../../groups/group/name";
                            }
                            max-elements 8;
                            ordered-by user;
                            description "Exclude a configuration group at this level";
                        }

                        container debounce {
                            description "Enter the debounce context";

                            leaf value {
                                type uint32 {
                                    range "2..15";
                                }
                                description "Occurrences in time interval to trigger EHS response";
                            }

                            leaf time {
                                type uint32 {
                                    range "1..604800";
                                }
                                units "seconds";
                                description "Time window for events for EHS to trigger a response";
                            }

                        } // container debounce

                    } // list entry

                } // list mc-redundancy

                list mgmt-core {
                    key "event";
                    description "Enter the mgmt-core list instance";

                    leaf event {
                        type types-log:mgmt-core-events;
                        description "Log event as a trigger for one or more EHS handlers";
                    }

                    leaf admin-state {
                        type types-sros:admin-state;
                        default "disable";
                        description "Administrative state of the EHS event trigger";
                    }

                    leaf description {
                        type types-sros:description;
                        description "Text description";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                    list entry {
                        key "id";
                        description "Enter the entry list instance";

                        leaf id {
                            type uint32 {
                                range "1..1500";
                            }
                            description "ID of the EHS event trigger entry";
                        }

                        leaf admin-state {
                            type types-sros:admin-state;
                            default "enable";
                            description "Administrative state of the EHS event trigger entry";
                        }

                        leaf description {
                            type types-sros:description;
                            description "Text description";
                        }

                        leaf filter {
                            type leafref {
                                path "../../../../filter/filter-name";
                            }
                            description "Log filter for EHS event trigger entry";
                        }

                        leaf handler {
                            type leafref {
                                path "../../../../event-handling/handler/name";
                            }
                            description "Event handler for EHS event trigger entry";
                        }

                        leaf-list apply-groups {
                            type leafref {
                                path "../../../../../groups/group/name";
                            }
                            max-elements 8;
                            ordered-by user;
                            description "Apply a configuration group at this level";
                        }

                        leaf-list apply-groups-exclude {
                            type leafref {
                                path "../../../../../groups/group/name";
                            }
                            max-elements 8;
                            ordered-by user;
                            description "Exclude a configuration group at this level";
                        }

                        container debounce {
                            description "Enter the debounce context";

                            leaf value {
                                type uint32 {
                                    range "2..15";
                                }
                                description "Occurrences in time interval to trigger EHS response";
                            }

                            leaf time {
                                type uint32 {
                                    range "1..604800";
                                }
                                units "seconds";
                                description "Time window for events for EHS to trigger a response";
                            }

                        } // container debounce

                    } // list entry

                } // list mgmt-core

                list mirror {
                    key "event";
                    description "Enter the mirror list instance";

                    leaf event {
                        type types-log:mirror-events;
                        description "Log event as a trigger for one or more EHS handlers";
                    }

                    leaf admin-state {
                        type types-sros:admin-state;
                        default "disable";
                        description "Administrative state of the EHS event trigger";
                    }

                    leaf description {
                        type types-sros:description;
                        description "Text description";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                    list entry {
                        key "id";
                        description "Enter the entry list instance";

                        leaf id {
                            type uint32 {
                                range "1..1500";
                            }
                            description "ID of the EHS event trigger entry";
                        }

                        leaf admin-state {
                            type types-sros:admin-state;
                            default "enable";
                            description "Administrative state of the EHS event trigger entry";
                        }

                        leaf description {
                            type types-sros:description;
                            description "Text description";
                        }

                        leaf filter {
                            type leafref {
                                path "../../../../filter/filter-name";
                            }
                            description "Log filter for EHS event trigger entry";
                        }

                        leaf handler {
                            type leafref {
                                path "../../../../event-handling/handler/name";
                            }
                            description "Event handler for EHS event trigger entry";
                        }

                        leaf-list apply-groups {
                            type leafref {
                                path "../../../../../groups/group/name";
                            }
                            max-elements 8;
                            ordered-by user;
                            description "Apply a configuration group at this level";
                        }

                        leaf-list apply-groups-exclude {
                            type leafref {
                                path "../../../../../groups/group/name";
                            }
                            max-elements 8;
                            ordered-by user;
                            description "Exclude a configuration group at this level";
                        }

                        container debounce {
                            description "Enter the debounce context";

                            leaf value {
                                type uint32 {
                                    range "2..15";
                                }
                                description "Occurrences in time interval to trigger EHS response";
                            }

                            leaf time {
                                type uint32 {
                                    range "1..604800";
                                }
                                units "seconds";
                                description "Time window for events for EHS to trigger a response";
                            }

                        } // container debounce

                    } // list entry

                } // list mirror

                list mld {
                    key "event";
                    description "Enter the mld list instance";

                    leaf event {
                        type types-log:mld-events;
                        description "Log event as a trigger for one or more EHS handlers";
                    }

                    leaf admin-state {
                        type types-sros:admin-state;
                        default "disable";
                        description "Administrative state of the EHS event trigger";
                    }

                    leaf description {
                        type types-sros:description;
                        description "Text description";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                    list entry {
                        key "id";
                        description "Enter the entry list instance";

                        leaf id {
                            type uint32 {
                                range "1..1500";
                            }
                            description "ID of the EHS event trigger entry";
                        }

                        leaf admin-state {
                            type types-sros:admin-state;
                            default "enable";
                            description "Administrative state of the EHS event trigger entry";
                        }

                        leaf description {
                            type types-sros:description;
                            description "Text description";
                        }

                        leaf filter {
                            type leafref {
                                path "../../../../filter/filter-name";
                            }
                            description "Log filter for EHS event trigger entry";
                        }

                        leaf handler {
                            type leafref {
                                path "../../../../event-handling/handler/name";
                            }
                            description "Event handler for EHS event trigger entry";
                        }

                        leaf-list apply-groups {
                            type leafref {
                                path "../../../../../groups/group/name";
                            }
                            max-elements 8;
                            ordered-by user;
                            description "Apply a configuration group at this level";
                        }

                        leaf-list apply-groups-exclude {
                            type leafref {
                                path "../../../../../groups/group/name";
                            }
                            max-elements 8;
                            ordered-by user;
                            description "Exclude a configuration group at this level";
                        }

                        container debounce {
                            description "Enter the debounce context";

                            leaf value {
                                type uint32 {
                                    range "2..15";
                                }
                                description "Occurrences in time interval to trigger EHS response";
                            }

                            leaf time {
                                type uint32 {
                                    range "1..604800";
                                }
                                units "seconds";
                                description "Time window for events for EHS to trigger a response";
                            }

                        } // container debounce

                    } // list entry

                } // list mld

                list mld-snooping {
                    key "event";
                    description "Enter the mld-snooping list instance";

                    leaf event {
                        type types-log:mld-snooping-events;
                        description "Log event as a trigger for one or more EHS handlers";
                    }

                    leaf admin-state {
                        type types-sros:admin-state;
                        default "disable";
                        description "Administrative state of the EHS event trigger";
                    }

                    leaf description {
                        type types-sros:description;
                        description "Text description";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                    list entry {
                        key "id";
                        description "Enter the entry list instance";

                        leaf id {
                            type uint32 {
                                range "1..1500";
                            }
                            description "ID of the EHS event trigger entry";
                        }

                        leaf admin-state {
                            type types-sros:admin-state;
                            default "enable";
                            description "Administrative state of the EHS event trigger entry";
                        }

                        leaf description {
                            type types-sros:description;
                            description "Text description";
                        }

                        leaf filter {
                            type leafref {
                                path "../../../../filter/filter-name";
                            }
                            description "Log filter for EHS event trigger entry";
                        }

                        leaf handler {
                            type leafref {
                                path "../../../../event-handling/handler/name";
                            }
                            description "Event handler for EHS event trigger entry";
                        }

                        leaf-list apply-groups {
                            type leafref {
                                path "../../../../../groups/group/name";
                            }
                            max-elements 8;
                            ordered-by user;
                            description "Apply a configuration group at this level";
                        }

                        leaf-list apply-groups-exclude {
                            type leafref {
                                path "../../../../../groups/group/name";
                            }
                            max-elements 8;
                            ordered-by user;
                            description "Exclude a configuration group at this level";
                        }

                        container debounce {
                            description "Enter the debounce context";

                            leaf value {
                                type uint32 {
                                    range "2..15";
                                }
                                description "Occurrences in time interval to trigger EHS response";
                            }

                            leaf time {
                                type uint32 {
                                    range "1..604800";
                                }
                                units "seconds";
                                description "Time window for events for EHS to trigger a response";
                            }

                        } // container debounce

                    } // list entry

                } // list mld-snooping

                list mpls {
                    key "event";
                    description "Enter the mpls list instance";

                    leaf event {
                        type types-log:mpls-events;
                        description "Log event as a trigger for one or more EHS handlers";
                    }

                    leaf admin-state {
                        type types-sros:admin-state;
                        default "disable";
                        description "Administrative state of the EHS event trigger";
                    }

                    leaf description {
                        type types-sros:description;
                        description "Text description";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                    list entry {
                        key "id";
                        description "Enter the entry list instance";

                        leaf id {
                            type uint32 {
                                range "1..1500";
                            }
                            description "ID of the EHS event trigger entry";
                        }

                        leaf admin-state {
                            type types-sros:admin-state;
                            default "enable";
                            description "Administrative state of the EHS event trigger entry";
                        }

                        leaf description {
                            type types-sros:description;
                            description "Text description";
                        }

                        leaf filter {
                            type leafref {
                                path "../../../../filter/filter-name";
                            }
                            description "Log filter for EHS event trigger entry";
                        }

                        leaf handler {
                            type leafref {
                                path "../../../../event-handling/handler/name";
                            }
                            description "Event handler for EHS event trigger entry";
                        }

                        leaf-list apply-groups {
                            type leafref {
                                path "../../../../../groups/group/name";
                            }
                            max-elements 8;
                            ordered-by user;
                            description "Apply a configuration group at this level";
                        }

                        leaf-list apply-groups-exclude {
                            type leafref {
                                path "../../../../../groups/group/name";
                            }
                            max-elements 8;
                            ordered-by user;
                            description "Exclude a configuration group at this level";
                        }

                        container debounce {
                            description "Enter the debounce context";

                            leaf value {
                                type uint32 {
                                    range "2..15";
                                }
                                description "Occurrences in time interval to trigger EHS response";
                            }

                            leaf time {
                                type uint32 {
                                    range "1..604800";
                                }
                                units "seconds";
                                description "Time window for events for EHS to trigger a response";
                            }

                        } // container debounce

                    } // list entry

                } // list mpls

                list mpls-tp {
                    key "event";
                    description "Enter the mpls-tp list instance";

                    leaf event {
                        type types-log:mpls-tp-events;
                        description "Log event as a trigger for one or more EHS handlers";
                    }

                    leaf admin-state {
                        type types-sros:admin-state;
                        default "disable";
                        description "Administrative state of the EHS event trigger";
                    }

                    leaf description {
                        type types-sros:description;
                        description "Text description";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                    list entry {
                        key "id";
                        description "Enter the entry list instance";

                        leaf id {
                            type uint32 {
                                range "1..1500";
                            }
                            description "ID of the EHS event trigger entry";
                        }

                        leaf admin-state {
                            type types-sros:admin-state;
                            default "enable";
                            description "Administrative state of the EHS event trigger entry";
                        }

                        leaf description {
                            type types-sros:description;
                            description "Text description";
                        }

                        leaf filter {
                            type leafref {
                                path "../../../../filter/filter-name";
                            }
                            description "Log filter for EHS event trigger entry";
                        }

                        leaf handler {
                            type leafref {
                                path "../../../../event-handling/handler/name";
                            }
                            description "Event handler for EHS event trigger entry";
                        }

                        leaf-list apply-groups {
                            type leafref {
                                path "../../../../../groups/group/name";
                            }
                            max-elements 8;
                            ordered-by user;
                            description "Apply a configuration group at this level";
                        }

                        leaf-list apply-groups-exclude {
                            type leafref {
                                path "../../../../../groups/group/name";
                            }
                            max-elements 8;
                            ordered-by user;
                            description "Exclude a configuration group at this level";
                        }

                        container debounce {
                            description "Enter the debounce context";

                            leaf value {
                                type uint32 {
                                    range "2..15";
                                }
                                description "Occurrences in time interval to trigger EHS response";
                            }

                            leaf time {
                                type uint32 {
                                    range "1..604800";
                                }
                                units "seconds";
                                description "Time window for events for EHS to trigger a response";
                            }

                        } // container debounce

                    } // list entry

                } // list mpls-tp

                list msdp {
                    key "event";
                    description "Enter the msdp list instance";

                    leaf event {
                        type types-log:msdp-events;
                        description "Log event as a trigger for one or more EHS handlers";
                    }

                    leaf admin-state {
                        type types-sros:admin-state;
                        default "disable";
                        description "Administrative state of the EHS event trigger";
                    }

                    leaf description {
                        type types-sros:description;
                        description "Text description";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                    list entry {
                        key "id";
                        description "Enter the entry list instance";

                        leaf id {
                            type uint32 {
                                range "1..1500";
                            }
                            description "ID of the EHS event trigger entry";
                        }

                        leaf admin-state {
                            type types-sros:admin-state;
                            default "enable";
                            description "Administrative state of the EHS event trigger entry";
                        }

                        leaf description {
                            type types-sros:description;
                            description "Text description";
                        }

                        leaf filter {
                            type leafref {
                                path "../../../../filter/filter-name";
                            }
                            description "Log filter for EHS event trigger entry";
                        }

                        leaf handler {
                            type leafref {
                                path "../../../../event-handling/handler/name";
                            }
                            description "Event handler for EHS event trigger entry";
                        }

                        leaf-list apply-groups {
                            type leafref {
                                path "../../../../../groups/group/name";
                            }
                            max-elements 8;
                            ordered-by user;
                            description "Apply a configuration group at this level";
                        }

                        leaf-list apply-groups-exclude {
                            type leafref {
                                path "../../../../../groups/group/name";
                            }
                            max-elements 8;
                            ordered-by user;
                            description "Exclude a configuration group at this level";
                        }

                        container debounce {
                            description "Enter the debounce context";

                            leaf value {
                                type uint32 {
                                    range "2..15";
                                }
                                description "Occurrences in time interval to trigger EHS response";
                            }

                            leaf time {
                                type uint32 {
                                    range "1..604800";
                                }
                                units "seconds";
                                description "Time window for events for EHS to trigger a response";
                            }

                        } // container debounce

                    } // list entry

                } // list msdp

                list nat {
                    key "event";
                    description "Enter the nat list instance";

                    leaf event {
                        type types-log:nat-events;
                        description "Log event as a trigger for one or more EHS handlers";
                    }

                    leaf admin-state {
                        type types-sros:admin-state;
                        default "disable";
                        description "Administrative state of the EHS event trigger";
                    }

                    leaf description {
                        type types-sros:description;
                        description "Text description";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                    list entry {
                        key "id";
                        description "Enter the entry list instance";

                        leaf id {
                            type uint32 {
                                range "1..1500";
                            }
                            description "ID of the EHS event trigger entry";
                        }

                        leaf admin-state {
                            type types-sros:admin-state;
                            default "enable";
                            description "Administrative state of the EHS event trigger entry";
                        }

                        leaf description {
                            type types-sros:description;
                            description "Text description";
                        }

                        leaf filter {
                            type leafref {
                                path "../../../../filter/filter-name";
                            }
                            description "Log filter for EHS event trigger entry";
                        }

                        leaf handler {
                            type leafref {
                                path "../../../../event-handling/handler/name";
                            }
                            description "Event handler for EHS event trigger entry";
                        }

                        leaf-list apply-groups {
                            type leafref {
                                path "../../../../../groups/group/name";
                            }
                            max-elements 8;
                            ordered-by user;
                            description "Apply a configuration group at this level";
                        }

                        leaf-list apply-groups-exclude {
                            type leafref {
                                path "../../../../../groups/group/name";
                            }
                            max-elements 8;
                            ordered-by user;
                            description "Exclude a configuration group at this level";
                        }

                        container debounce {
                            description "Enter the debounce context";

                            leaf value {
                                type uint32 {
                                    range "2..15";
                                }
                                description "Occurrences in time interval to trigger EHS response";
                            }

                            leaf time {
                                type uint32 {
                                    range "1..604800";
                                }
                                units "seconds";
                                description "Time window for events for EHS to trigger a response";
                            }

                        } // container debounce

                    } // list entry

                } // list nat

                list ntp {
                    key "event";
                    description "Enter the ntp list instance";

                    leaf event {
                        type types-log:ntp-events;
                        description "Log event as a trigger for one or more EHS handlers";
                    }

                    leaf admin-state {
                        type types-sros:admin-state;
                        default "disable";
                        description "Administrative state of the EHS event trigger";
                    }

                    leaf description {
                        type types-sros:description;
                        description "Text description";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                    list entry {
                        key "id";
                        description "Enter the entry list instance";

                        leaf id {
                            type uint32 {
                                range "1..1500";
                            }
                            description "ID of the EHS event trigger entry";
                        }

                        leaf admin-state {
                            type types-sros:admin-state;
                            default "enable";
                            description "Administrative state of the EHS event trigger entry";
                        }

                        leaf description {
                            type types-sros:description;
                            description "Text description";
                        }

                        leaf filter {
                            type leafref {
                                path "../../../../filter/filter-name";
                            }
                            description "Log filter for EHS event trigger entry";
                        }

                        leaf handler {
                            type leafref {
                                path "../../../../event-handling/handler/name";
                            }
                            description "Event handler for EHS event trigger entry";
                        }

                        leaf-list apply-groups {
                            type leafref {
                                path "../../../../../groups/group/name";
                            }
                            max-elements 8;
                            ordered-by user;
                            description "Apply a configuration group at this level";
                        }

                        leaf-list apply-groups-exclude {
                            type leafref {
                                path "../../../../../groups/group/name";
                            }
                            max-elements 8;
                            ordered-by user;
                            description "Exclude a configuration group at this level";
                        }

                        container debounce {
                            description "Enter the debounce context";

                            leaf value {
                                type uint32 {
                                    range "2..15";
                                }
                                description "Occurrences in time interval to trigger EHS response";
                            }

                            leaf time {
                                type uint32 {
                                    range "1..604800";
                                }
                                units "seconds";
                                description "Time window for events for EHS to trigger a response";
                            }

                        } // container debounce

                    } // list entry

                } // list ntp

                list oam {
                    key "event";
                    description "Enter the oam list instance";

                    leaf event {
                        type types-log:oam-events;
                        description "Log event as a trigger for one or more EHS handlers";
                    }

                    leaf admin-state {
                        type types-sros:admin-state;
                        default "disable";
                        description "Administrative state of the EHS event trigger";
                    }

                    leaf description {
                        type types-sros:description;
                        description "Text description";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                    list entry {
                        key "id";
                        description "Enter the entry list instance";

                        leaf id {
                            type uint32 {
                                range "1..1500";
                            }
                            description "ID of the EHS event trigger entry";
                        }

                        leaf admin-state {
                            type types-sros:admin-state;
                            default "enable";
                            description "Administrative state of the EHS event trigger entry";
                        }

                        leaf description {
                            type types-sros:description;
                            description "Text description";
                        }

                        leaf filter {
                            type leafref {
                                path "../../../../filter/filter-name";
                            }
                            description "Log filter for EHS event trigger entry";
                        }

                        leaf handler {
                            type leafref {
                                path "../../../../event-handling/handler/name";
                            }
                            description "Event handler for EHS event trigger entry";
                        }

                        leaf-list apply-groups {
                            type leafref {
                                path "../../../../../groups/group/name";
                            }
                            max-elements 8;
                            ordered-by user;
                            description "Apply a configuration group at this level";
                        }

                        leaf-list apply-groups-exclude {
                            type leafref {
                                path "../../../../../groups/group/name";
                            }
                            max-elements 8;
                            ordered-by user;
                            description "Exclude a configuration group at this level";
                        }

                        container debounce {
                            description "Enter the debounce context";

                            leaf value {
                                type uint32 {
                                    range "2..15";
                                }
                                description "Occurrences in time interval to trigger EHS response";
                            }

                            leaf time {
                                type uint32 {
                                    range "1..604800";
                                }
                                units "seconds";
                                description "Time window for events for EHS to trigger a response";
                            }

                        } // container debounce

                    } // list entry

                } // list oam

                list openflow {
                    key "event";
                    description "Enter the openflow list instance";

                    leaf event {
                        type types-log:openflow-events;
                        description "Log event as a trigger for one or more EHS handlers";
                    }

                    leaf admin-state {
                        type types-sros:admin-state;
                        default "disable";
                        description "Administrative state of the EHS event trigger";
                    }

                    leaf description {
                        type types-sros:description;
                        description "Text description";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                    list entry {
                        key "id";
                        description "Enter the entry list instance";

                        leaf id {
                            type uint32 {
                                range "1..1500";
                            }
                            description "ID of the EHS event trigger entry";
                        }

                        leaf admin-state {
                            type types-sros:admin-state;
                            default "enable";
                            description "Administrative state of the EHS event trigger entry";
                        }

                        leaf description {
                            type types-sros:description;
                            description "Text description";
                        }

                        leaf filter {
                            type leafref {
                                path "../../../../filter/filter-name";
                            }
                            description "Log filter for EHS event trigger entry";
                        }

                        leaf handler {
                            type leafref {
                                path "../../../../event-handling/handler/name";
                            }
                            description "Event handler for EHS event trigger entry";
                        }

                        leaf-list apply-groups {
                            type leafref {
                                path "../../../../../groups/group/name";
                            }
                            max-elements 8;
                            ordered-by user;
                            description "Apply a configuration group at this level";
                        }

                        leaf-list apply-groups-exclude {
                            type leafref {
                                path "../../../../../groups/group/name";
                            }
                            max-elements 8;
                            ordered-by user;
                            description "Exclude a configuration group at this level";
                        }

                        container debounce {
                            description "Enter the debounce context";

                            leaf value {
                                type uint32 {
                                    range "2..15";
                                }
                                description "Occurrences in time interval to trigger EHS response";
                            }

                            leaf time {
                                type uint32 {
                                    range "1..604800";
                                }
                                units "seconds";
                                description "Time window for events for EHS to trigger a response";
                            }

                        } // container debounce

                    } // list entry

                } // list openflow

                list ospf {
                    key "event";
                    description "Enter the ospf list instance";

                    leaf event {
                        type types-log:ospf-events;
                        description "Log event as a trigger for one or more EHS handlers";
                    }

                    leaf admin-state {
                        type types-sros:admin-state;
                        default "disable";
                        description "Administrative state of the EHS event trigger";
                    }

                    leaf description {
                        type types-sros:description;
                        description "Text description";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                    list entry {
                        key "id";
                        description "Enter the entry list instance";

                        leaf id {
                            type uint32 {
                                range "1..1500";
                            }
                            description "ID of the EHS event trigger entry";
                        }

                        leaf admin-state {
                            type types-sros:admin-state;
                            default "enable";
                            description "Administrative state of the EHS event trigger entry";
                        }

                        leaf description {
                            type types-sros:description;
                            description "Text description";
                        }

                        leaf filter {
                            type leafref {
                                path "../../../../filter/filter-name";
                            }
                            description "Log filter for EHS event trigger entry";
                        }

                        leaf handler {
                            type leafref {
                                path "../../../../event-handling/handler/name";
                            }
                            description "Event handler for EHS event trigger entry";
                        }

                        leaf-list apply-groups {
                            type leafref {
                                path "../../../../../groups/group/name";
                            }
                            max-elements 8;
                            ordered-by user;
                            description "Apply a configuration group at this level";
                        }

                        leaf-list apply-groups-exclude {
                            type leafref {
                                path "../../../../../groups/group/name";
                            }
                            max-elements 8;
                            ordered-by user;
                            description "Exclude a configuration group at this level";
                        }

                        container debounce {
                            description "Enter the debounce context";

                            leaf value {
                                type uint32 {
                                    range "2..15";
                                }
                                description "Occurrences in time interval to trigger EHS response";
                            }

                            leaf time {
                                type uint32 {
                                    range "1..604800";
                                }
                                units "seconds";
                                description "Time window for events for EHS to trigger a response";
                            }

                        } // container debounce

                    } // list entry

                } // list ospf

                list pcap {
                    key "event";
                    description "Enter the pcap list instance";

                    leaf event {
                        type types-log:pcap-events;
                        description "Log event as a trigger for one or more EHS handlers";
                    }

                    leaf admin-state {
                        type types-sros:admin-state;
                        default "disable";
                        description "Administrative state of the EHS event trigger";
                    }

                    leaf description {
                        type types-sros:description;
                        description "Text description";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                    list entry {
                        key "id";
                        description "Enter the entry list instance";

                        leaf id {
                            type uint32 {
                                range "1..1500";
                            }
                            description "ID of the EHS event trigger entry";
                        }

                        leaf admin-state {
                            type types-sros:admin-state;
                            default "enable";
                            description "Administrative state of the EHS event trigger entry";
                        }

                        leaf description {
                            type types-sros:description;
                            description "Text description";
                        }

                        leaf filter {
                            type leafref {
                                path "../../../../filter/filter-name";
                            }
                            description "Log filter for EHS event trigger entry";
                        }

                        leaf handler {
                            type leafref {
                                path "../../../../event-handling/handler/name";
                            }
                            description "Event handler for EHS event trigger entry";
                        }

                        leaf-list apply-groups {
                            type leafref {
                                path "../../../../../groups/group/name";
                            }
                            max-elements 8;
                            ordered-by user;
                            description "Apply a configuration group at this level";
                        }

                        leaf-list apply-groups-exclude {
                            type leafref {
                                path "../../../../../groups/group/name";
                            }
                            max-elements 8;
                            ordered-by user;
                            description "Exclude a configuration group at this level";
                        }

                        container debounce {
                            description "Enter the debounce context";

                            leaf value {
                                type uint32 {
                                    range "2..15";
                                }
                                description "Occurrences in time interval to trigger EHS response";
                            }

                            leaf time {
                                type uint32 {
                                    range "1..604800";
                                }
                                units "seconds";
                                description "Time window for events for EHS to trigger a response";
                            }

                        } // container debounce

                    } // list entry

                } // list pcap

                list pcep {
                    key "event";
                    description "Enter the pcep list instance";

                    leaf event {
                        type types-log:pcep-events;
                        description "PCEP module events";
                    }

                    leaf admin-state {
                        type types-sros:admin-state;
                        default "disable";
                        description "Administrative state of the EHS event trigger";
                    }

                    leaf description {
                        type types-sros:description;
                        description "Text description";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                    list entry {
                        key "id";
                        description "Enter the entry list instance";

                        leaf id {
                            type uint32 {
                                range "1..1500";
                            }
                            description "ID of the EHS event trigger entry";
                        }

                        leaf admin-state {
                            type types-sros:admin-state;
                            default "enable";
                            description "Administrative state of the EHS event trigger entry";
                        }

                        leaf description {
                            type types-sros:description;
                            description "Text description";
                        }

                        leaf filter {
                            type leafref {
                                path "../../../../filter/filter-name";
                            }
                            description "Log filter for EHS event trigger entry";
                        }

                        leaf handler {
                            type leafref {
                                path "../../../../event-handling/handler/name";
                            }
                            description "Event handler for EHS event trigger entry";
                        }

                        leaf-list apply-groups {
                            type leafref {
                                path "../../../../../groups/group/name";
                            }
                            max-elements 8;
                            ordered-by user;
                            description "Apply a configuration group at this level";
                        }

                        leaf-list apply-groups-exclude {
                            type leafref {
                                path "../../../../../groups/group/name";
                            }
                            max-elements 8;
                            ordered-by user;
                            description "Exclude a configuration group at this level";
                        }

                        container debounce {
                            description "Enter the debounce context";

                            leaf value {
                                type uint32 {
                                    range "2..15";
                                }
                                description "Occurrences in time interval to trigger EHS response";
                            }

                            leaf time {
                                type uint32 {
                                    range "1..604800";
                                }
                                units "seconds";
                                description "Time window for events for EHS to trigger a response";
                            }

                        } // container debounce

                    } // list entry

                } // list pcep

                list pfcp {
                    key "event";
                    description "Enter the pfcp list instance";

                    leaf event {
                        type types-log:pfcp-events;
                        description "PFCP events";
                    }

                    leaf admin-state {
                        type types-sros:admin-state;
                        default "disable";
                        description "Administrative state of the EHS event trigger";
                    }

                    leaf description {
                        type types-sros:description;
                        description "Text description";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                    list entry {
                        key "id";
                        description "Enter the entry list instance";

                        leaf id {
                            type uint32 {
                                range "1..1500";
                            }
                            description "ID of the EHS event trigger entry";
                        }

                        leaf admin-state {
                            type types-sros:admin-state;
                            default "enable";
                            description "Administrative state of the EHS event trigger entry";
                        }

                        leaf description {
                            type types-sros:description;
                            description "Text description";
                        }

                        leaf filter {
                            type leafref {
                                path "../../../../filter/filter-name";
                            }
                            description "Log filter for EHS event trigger entry";
                        }

                        leaf handler {
                            type leafref {
                                path "../../../../event-handling/handler/name";
                            }
                            description "Event handler for EHS event trigger entry";
                        }

                        leaf-list apply-groups {
                            type leafref {
                                path "../../../../../groups/group/name";
                            }
                            max-elements 8;
                            ordered-by user;
                            description "Apply a configuration group at this level";
                        }

                        leaf-list apply-groups-exclude {
                            type leafref {
                                path "../../../../../groups/group/name";
                            }
                            max-elements 8;
                            ordered-by user;
                            description "Exclude a configuration group at this level";
                        }

                        container debounce {
                            description "Enter the debounce context";

                            leaf value {
                                type uint32 {
                                    range "2..15";
                                }
                                description "Occurrences in time interval to trigger EHS response";
                            }

                            leaf time {
                                type uint32 {
                                    range "1..604800";
                                }
                                units "seconds";
                                description "Time window for events for EHS to trigger a response";
                            }

                        } // container debounce

                    } // list entry

                } // list pfcp

                list pim {
                    key "event";
                    description "Enter the pim list instance";

                    leaf event {
                        type types-log:pim-events;
                        description "Log event as a trigger for one or more EHS handlers";
                    }

                    leaf admin-state {
                        type types-sros:admin-state;
                        default "disable";
                        description "Administrative state of the EHS event trigger";
                    }

                    leaf description {
                        type types-sros:description;
                        description "Text description";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                    list entry {
                        key "id";
                        description "Enter the entry list instance";

                        leaf id {
                            type uint32 {
                                range "1..1500";
                            }
                            description "ID of the EHS event trigger entry";
                        }

                        leaf admin-state {
                            type types-sros:admin-state;
                            default "enable";
                            description "Administrative state of the EHS event trigger entry";
                        }

                        leaf description {
                            type types-sros:description;
                            description "Text description";
                        }

                        leaf filter {
                            type leafref {
                                path "../../../../filter/filter-name";
                            }
                            description "Log filter for EHS event trigger entry";
                        }

                        leaf handler {
                            type leafref {
                                path "../../../../event-handling/handler/name";
                            }
                            description "Event handler for EHS event trigger entry";
                        }

                        leaf-list apply-groups {
                            type leafref {
                                path "../../../../../groups/group/name";
                            }
                            max-elements 8;
                            ordered-by user;
                            description "Apply a configuration group at this level";
                        }

                        leaf-list apply-groups-exclude {
                            type leafref {
                                path "../../../../../groups/group/name";
                            }
                            max-elements 8;
                            ordered-by user;
                            description "Exclude a configuration group at this level";
                        }

                        container debounce {
                            description "Enter the debounce context";

                            leaf value {
                                type uint32 {
                                    range "2..15";
                                }
                                description "Occurrences in time interval to trigger EHS response";
                            }

                            leaf time {
                                type uint32 {
                                    range "1..604800";
                                }
                                units "seconds";
                                description "Time window for events for EHS to trigger a response";
                            }

                        } // container debounce

                    } // list entry

                } // list pim

                list pim-snooping {
                    key "event";
                    description "Enter the pim-snooping list instance";

                    leaf event {
                        type types-log:pim-snooping-events;
                        description "Log event as a trigger for one or more EHS handlers";
                    }

                    leaf admin-state {
                        type types-sros:admin-state;
                        default "disable";
                        description "Administrative state of the EHS event trigger";
                    }

                    leaf description {
                        type types-sros:description;
                        description "Text description";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                    list entry {
                        key "id";
                        description "Enter the entry list instance";

                        leaf id {
                            type uint32 {
                                range "1..1500";
                            }
                            description "ID of the EHS event trigger entry";
                        }

                        leaf admin-state {
                            type types-sros:admin-state;
                            default "enable";
                            description "Administrative state of the EHS event trigger entry";
                        }

                        leaf description {
                            type types-sros:description;
                            description "Text description";
                        }

                        leaf filter {
                            type leafref {
                                path "../../../../filter/filter-name";
                            }
                            description "Log filter for EHS event trigger entry";
                        }

                        leaf handler {
                            type leafref {
                                path "../../../../event-handling/handler/name";
                            }
                            description "Event handler for EHS event trigger entry";
                        }

                        leaf-list apply-groups {
                            type leafref {
                                path "../../../../../groups/group/name";
                            }
                            max-elements 8;
                            ordered-by user;
                            description "Apply a configuration group at this level";
                        }

                        leaf-list apply-groups-exclude {
                            type leafref {
                                path "../../../../../groups/group/name";
                            }
                            max-elements 8;
                            ordered-by user;
                            description "Exclude a configuration group at this level";
                        }

                        container debounce {
                            description "Enter the debounce context";

                            leaf value {
                                type uint32 {
                                    range "2..15";
                                }
                                description "Occurrences in time interval to trigger EHS response";
                            }

                            leaf time {
                                type uint32 {
                                    range "1..604800";
                                }
                                units "seconds";
                                description "Time window for events for EHS to trigger a response";
                            }

                        } // container debounce

                    } // list entry

                } // list pim-snooping

                list port {
                    key "event";
                    description "Enter the port list instance";

                    leaf event {
                        type types-log:port-events;
                        description "Log event as a trigger for one or more EHS handlers";
                    }

                    leaf admin-state {
                        type types-sros:admin-state;
                        default "disable";
                        description "Administrative state of the EHS event trigger";
                    }

                    leaf description {
                        type types-sros:description;
                        description "Text description";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                    list entry {
                        key "id";
                        description "Enter the entry list instance";

                        leaf id {
                            type uint32 {
                                range "1..1500";
                            }
                            description "ID of the EHS event trigger entry";
                        }

                        leaf admin-state {
                            type types-sros:admin-state;
                            default "enable";
                            description "Administrative state of the EHS event trigger entry";
                        }

                        leaf description {
                            type types-sros:description;
                            description "Text description";
                        }

                        leaf filter {
                            type leafref {
                                path "../../../../filter/filter-name";
                            }
                            description "Log filter for EHS event trigger entry";
                        }

                        leaf handler {
                            type leafref {
                                path "../../../../event-handling/handler/name";
                            }
                            description "Event handler for EHS event trigger entry";
                        }

                        leaf-list apply-groups {
                            type leafref {
                                path "../../../../../groups/group/name";
                            }
                            max-elements 8;
                            ordered-by user;
                            description "Apply a configuration group at this level";
                        }

                        leaf-list apply-groups-exclude {
                            type leafref {
                                path "../../../../../groups/group/name";
                            }
                            max-elements 8;
                            ordered-by user;
                            description "Exclude a configuration group at this level";
                        }

                        container debounce {
                            description "Enter the debounce context";

                            leaf value {
                                type uint32 {
                                    range "2..15";
                                }
                                description "Occurrences in time interval to trigger EHS response";
                            }

                            leaf time {
                                type uint32 {
                                    range "1..604800";
                                }
                                units "seconds";
                                description "Time window for events for EHS to trigger a response";
                            }

                        } // container debounce

                    } // list entry

                } // list port

                list pppoe {
                    key "event";
                    description "Enter the pppoe list instance";

                    leaf event {
                        type types-log:pppoe-events;
                        description "Log event as a trigger for one or more EHS handlers";
                    }

                    leaf admin-state {
                        type types-sros:admin-state;
                        default "disable";
                        description "Administrative state of the EHS event trigger";
                    }

                    leaf description {
                        type types-sros:description;
                        description "Text description";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                    list entry {
                        key "id";
                        description "Enter the entry list instance";

                        leaf id {
                            type uint32 {
                                range "1..1500";
                            }
                            description "ID of the EHS event trigger entry";
                        }

                        leaf admin-state {
                            type types-sros:admin-state;
                            default "enable";
                            description "Administrative state of the EHS event trigger entry";
                        }

                        leaf description {
                            type types-sros:description;
                            description "Text description";
                        }

                        leaf filter {
                            type leafref {
                                path "../../../../filter/filter-name";
                            }
                            description "Log filter for EHS event trigger entry";
                        }

                        leaf handler {
                            type leafref {
                                path "../../../../event-handling/handler/name";
                            }
                            description "Event handler for EHS event trigger entry";
                        }

                        leaf-list apply-groups {
                            type leafref {
                                path "../../../../../groups/group/name";
                            }
                            max-elements 8;
                            ordered-by user;
                            description "Apply a configuration group at this level";
                        }

                        leaf-list apply-groups-exclude {
                            type leafref {
                                path "../../../../../groups/group/name";
                            }
                            max-elements 8;
                            ordered-by user;
                            description "Exclude a configuration group at this level";
                        }

                        container debounce {
                            description "Enter the debounce context";

                            leaf value {
                                type uint32 {
                                    range "2..15";
                                }
                                description "Occurrences in time interval to trigger EHS response";
                            }

                            leaf time {
                                type uint32 {
                                    range "1..604800";
                                }
                                units "seconds";
                                description "Time window for events for EHS to trigger a response";
                            }

                        } // container debounce

                    } // list entry

                } // list pppoe

                list pppoe-clnt {
                    key "event";
                    description "Enter the pppoe-clnt list instance";

                    leaf event {
                        type types-log:pppoe-clnt-events;
                        description "Log event as a trigger for one or more EHS handlers";
                    }

                    leaf admin-state {
                        type types-sros:admin-state;
                        default "disable";
                        description "Administrative state of the EHS event trigger";
                    }

                    leaf description {
                        type types-sros:description;
                        description "Text description";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                    list entry {
                        key "id";
                        description "Enter the entry list instance";

                        leaf id {
                            type uint32 {
                                range "1..1500";
                            }
                            description "ID of the EHS event trigger entry";
                        }

                        leaf admin-state {
                            type types-sros:admin-state;
                            default "enable";
                            description "Administrative state of the EHS event trigger entry";
                        }

                        leaf description {
                            type types-sros:description;
                            description "Text description";
                        }

                        leaf filter {
                            type leafref {
                                path "../../../../filter/filter-name";
                            }
                            description "Log filter for EHS event trigger entry";
                        }

                        leaf handler {
                            type leafref {
                                path "../../../../event-handling/handler/name";
                            }
                            description "Event handler for EHS event trigger entry";
                        }

                        leaf-list apply-groups {
                            type leafref {
                                path "../../../../../groups/group/name";
                            }
                            max-elements 8;
                            ordered-by user;
                            description "Apply a configuration group at this level";
                        }

                        leaf-list apply-groups-exclude {
                            type leafref {
                                path "../../../../../groups/group/name";
                            }
                            max-elements 8;
                            ordered-by user;
                            description "Exclude a configuration group at this level";
                        }

                        container debounce {
                            description "Enter the debounce context";

                            leaf value {
                                type uint32 {
                                    range "2..15";
                                }
                                description "Occurrences in time interval to trigger EHS response";
                            }

                            leaf time {
                                type uint32 {
                                    range "1..604800";
                                }
                                units "seconds";
                                description "Time window for events for EHS to trigger a response";
                            }

                        } // container debounce

                    } // list entry

                } // list pppoe-clnt

                list ptp {
                    key "event";
                    description "Enter the ptp list instance";

                    leaf event {
                        type types-log:ptp-events;
                        description "Log event as a trigger for one or more EHS handlers";
                    }

                    leaf admin-state {
                        type types-sros:admin-state;
                        default "disable";
                        description "Administrative state of the EHS event trigger";
                    }

                    leaf description {
                        type types-sros:description;
                        description "Text description";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                    list entry {
                        key "id";
                        description "Enter the entry list instance";

                        leaf id {
                            type uint32 {
                                range "1..1500";
                            }
                            description "ID of the EHS event trigger entry";
                        }

                        leaf admin-state {
                            type types-sros:admin-state;
                            default "enable";
                            description "Administrative state of the EHS event trigger entry";
                        }

                        leaf description {
                            type types-sros:description;
                            description "Text description";
                        }

                        leaf filter {
                            type leafref {
                                path "../../../../filter/filter-name";
                            }
                            description "Log filter for EHS event trigger entry";
                        }

                        leaf handler {
                            type leafref {
                                path "../../../../event-handling/handler/name";
                            }
                            description "Event handler for EHS event trigger entry";
                        }

                        leaf-list apply-groups {
                            type leafref {
                                path "../../../../../groups/group/name";
                            }
                            max-elements 8;
                            ordered-by user;
                            description "Apply a configuration group at this level";
                        }

                        leaf-list apply-groups-exclude {
                            type leafref {
                                path "../../../../../groups/group/name";
                            }
                            max-elements 8;
                            ordered-by user;
                            description "Exclude a configuration group at this level";
                        }

                        container debounce {
                            description "Enter the debounce context";

                            leaf value {
                                type uint32 {
                                    range "2..15";
                                }
                                description "Occurrences in time interval to trigger EHS response";
                            }

                            leaf time {
                                type uint32 {
                                    range "1..604800";
                                }
                                units "seconds";
                                description "Time window for events for EHS to trigger a response";
                            }

                        } // container debounce

                    } // list entry

                } // list ptp

                list python {
                    key "event";
                    description "Enter the python list instance";

                    leaf event {
                        type types-log:python-events;
                        description "Python module events";
                    }

                    leaf admin-state {
                        type types-sros:admin-state;
                        default "disable";
                        description "Administrative state of the EHS event trigger";
                    }

                    leaf description {
                        type types-sros:description;
                        description "Text description";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                    list entry {
                        key "id";
                        description "Enter the entry list instance";

                        leaf id {
                            type uint32 {
                                range "1..1500";
                            }
                            description "ID of the EHS event trigger entry";
                        }

                        leaf admin-state {
                            type types-sros:admin-state;
                            default "enable";
                            description "Administrative state of the EHS event trigger entry";
                        }

                        leaf description {
                            type types-sros:description;
                            description "Text description";
                        }

                        leaf filter {
                            type leafref {
                                path "../../../../filter/filter-name";
                            }
                            description "Log filter for EHS event trigger entry";
                        }

                        leaf handler {
                            type leafref {
                                path "../../../../event-handling/handler/name";
                            }
                            description "Event handler for EHS event trigger entry";
                        }

                        leaf-list apply-groups {
                            type leafref {
                                path "../../../../../groups/group/name";
                            }
                            max-elements 8;
                            ordered-by user;
                            description "Apply a configuration group at this level";
                        }

                        leaf-list apply-groups-exclude {
                            type leafref {
                                path "../../../../../groups/group/name";
                            }
                            max-elements 8;
                            ordered-by user;
                            description "Exclude a configuration group at this level";
                        }

                        container debounce {
                            description "Enter the debounce context";

                            leaf value {
                                type uint32 {
                                    range "2..15";
                                }
                                description "Occurrences in time interval to trigger EHS response";
                            }

                            leaf time {
                                type uint32 {
                                    range "1..604800";
                                }
                                units "seconds";
                                description "Time window for events for EHS to trigger a response";
                            }

                        } // container debounce

                    } // list entry

                } // list python

                list radius {
                    key "event";
                    description "Enter the radius list instance";

                    leaf event {
                        type types-log:radius-events;
                        description "Log event as a trigger for one or more EHS handlers";
                    }

                    leaf admin-state {
                        type types-sros:admin-state;
                        default "disable";
                        description "Administrative state of the EHS event trigger";
                    }

                    leaf description {
                        type types-sros:description;
                        description "Text description";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                    list entry {
                        key "id";
                        description "Enter the entry list instance";

                        leaf id {
                            type uint32 {
                                range "1..1500";
                            }
                            description "ID of the EHS event trigger entry";
                        }

                        leaf admin-state {
                            type types-sros:admin-state;
                            default "enable";
                            description "Administrative state of the EHS event trigger entry";
                        }

                        leaf description {
                            type types-sros:description;
                            description "Text description";
                        }

                        leaf filter {
                            type leafref {
                                path "../../../../filter/filter-name";
                            }
                            description "Log filter for EHS event trigger entry";
                        }

                        leaf handler {
                            type leafref {
                                path "../../../../event-handling/handler/name";
                            }
                            description "Event handler for EHS event trigger entry";
                        }

                        leaf-list apply-groups {
                            type leafref {
                                path "../../../../../groups/group/name";
                            }
                            max-elements 8;
                            ordered-by user;
                            description "Apply a configuration group at this level";
                        }

                        leaf-list apply-groups-exclude {
                            type leafref {
                                path "../../../../../groups/group/name";
                            }
                            max-elements 8;
                            ordered-by user;
                            description "Exclude a configuration group at this level";
                        }

                        container debounce {
                            description "Enter the debounce context";

                            leaf value {
                                type uint32 {
                                    range "2..15";
                                }
                                description "Occurrences in time interval to trigger EHS response";
                            }

                            leaf time {
                                type uint32 {
                                    range "1..604800";
                                }
                                units "seconds";
                                description "Time window for events for EHS to trigger a response";
                            }

                        } // container debounce

                    } // list entry

                } // list radius

                list rip {
                    key "event";
                    description "Enter the rip list instance";

                    leaf event {
                        type types-log:rip-events;
                        description "Log event as a trigger for one or more EHS handlers";
                    }

                    leaf admin-state {
                        type types-sros:admin-state;
                        default "disable";
                        description "Administrative state of the EHS event trigger";
                    }

                    leaf description {
                        type types-sros:description;
                        description "Text description";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                    list entry {
                        key "id";
                        description "Enter the entry list instance";

                        leaf id {
                            type uint32 {
                                range "1..1500";
                            }
                            description "ID of the EHS event trigger entry";
                        }

                        leaf admin-state {
                            type types-sros:admin-state;
                            default "enable";
                            description "Administrative state of the EHS event trigger entry";
                        }

                        leaf description {
                            type types-sros:description;
                            description "Text description";
                        }

                        leaf filter {
                            type leafref {
                                path "../../../../filter/filter-name";
                            }
                            description "Log filter for EHS event trigger entry";
                        }

                        leaf handler {
                            type leafref {
                                path "../../../../event-handling/handler/name";
                            }
                            description "Event handler for EHS event trigger entry";
                        }

                        leaf-list apply-groups {
                            type leafref {
                                path "../../../../../groups/group/name";
                            }
                            max-elements 8;
                            ordered-by user;
                            description "Apply a configuration group at this level";
                        }

                        leaf-list apply-groups-exclude {
                            type leafref {
                                path "../../../../../groups/group/name";
                            }
                            max-elements 8;
                            ordered-by user;
                            description "Exclude a configuration group at this level";
                        }

                        container debounce {
                            description "Enter the debounce context";

                            leaf value {
                                type uint32 {
                                    range "2..15";
                                }
                                description "Occurrences in time interval to trigger EHS response";
                            }

                            leaf time {
                                type uint32 {
                                    range "1..604800";
                                }
                                units "seconds";
                                description "Time window for events for EHS to trigger a response";
                            }

                        } // container debounce

                    } // list entry

                } // list rip

                list ripng {
                    key "event";
                    description "Enter the ripng list instance";

                    leaf event {
                        type types-log:ripng-events;
                        description "Log event as a trigger for one or more EHS handlers";
                    }

                    leaf admin-state {
                        type types-sros:admin-state;
                        default "disable";
                        description "Administrative state of the EHS event trigger";
                    }

                    leaf description {
                        type types-sros:description;
                        description "Text description";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                    list entry {
                        key "id";
                        description "Enter the entry list instance";

                        leaf id {
                            type uint32 {
                                range "1..1500";
                            }
                            description "ID of the EHS event trigger entry";
                        }

                        leaf admin-state {
                            type types-sros:admin-state;
                            default "enable";
                            description "Administrative state of the EHS event trigger entry";
                        }

                        leaf description {
                            type types-sros:description;
                            description "Text description";
                        }

                        leaf filter {
                            type leafref {
                                path "../../../../filter/filter-name";
                            }
                            description "Log filter for EHS event trigger entry";
                        }

                        leaf handler {
                            type leafref {
                                path "../../../../event-handling/handler/name";
                            }
                            description "Event handler for EHS event trigger entry";
                        }

                        leaf-list apply-groups {
                            type leafref {
                                path "../../../../../groups/group/name";
                            }
                            max-elements 8;
                            ordered-by user;
                            description "Apply a configuration group at this level";
                        }

                        leaf-list apply-groups-exclude {
                            type leafref {
                                path "../../../../../groups/group/name";
                            }
                            max-elements 8;
                            ordered-by user;
                            description "Exclude a configuration group at this level";
                        }

                        container debounce {
                            description "Enter the debounce context";

                            leaf value {
                                type uint32 {
                                    range "2..15";
                                }
                                description "Occurrences in time interval to trigger EHS response";
                            }

                            leaf time {
                                type uint32 {
                                    range "1..604800";
                                }
                                units "seconds";
                                description "Time window for events for EHS to trigger a response";
                            }

                        } // container debounce

                    } // list entry

                } // list ripng

                list route-policy {
                    key "event";
                    description "Enter the route-policy list instance";

                    leaf event {
                        type types-log:route-policy-events;
                        description "Log event as a trigger for one or more EHS handlers";
                    }

                    leaf admin-state {
                        type types-sros:admin-state;
                        default "disable";
                        description "Administrative state of the EHS event trigger";
                    }

                    leaf description {
                        type types-sros:description;
                        description "Text description";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                    list entry {
                        key "id";
                        description "Enter the entry list instance";

                        leaf id {
                            type uint32 {
                                range "1..1500";
                            }
                            description "ID of the EHS event trigger entry";
                        }

                        leaf admin-state {
                            type types-sros:admin-state;
                            default "enable";
                            description "Administrative state of the EHS event trigger entry";
                        }

                        leaf description {
                            type types-sros:description;
                            description "Text description";
                        }

                        leaf filter {
                            type leafref {
                                path "../../../../filter/filter-name";
                            }
                            description "Log filter for EHS event trigger entry";
                        }

                        leaf handler {
                            type leafref {
                                path "../../../../event-handling/handler/name";
                            }
                            description "Event handler for EHS event trigger entry";
                        }

                        leaf-list apply-groups {
                            type leafref {
                                path "../../../../../groups/group/name";
                            }
                            max-elements 8;
                            ordered-by user;
                            description "Apply a configuration group at this level";
                        }

                        leaf-list apply-groups-exclude {
                            type leafref {
                                path "../../../../../groups/group/name";
                            }
                            max-elements 8;
                            ordered-by user;
                            description "Exclude a configuration group at this level";
                        }

                        container debounce {
                            description "Enter the debounce context";

                            leaf value {
                                type uint32 {
                                    range "2..15";
                                }
                                description "Occurrences in time interval to trigger EHS response";
                            }

                            leaf time {
                                type uint32 {
                                    range "1..604800";
                                }
                                units "seconds";
                                description "Time window for events for EHS to trigger a response";
                            }

                        } // container debounce

                    } // list entry

                } // list route-policy

                list rpki {
                    key "event";
                    description "Enter the rpki list instance";

                    leaf event {
                        type types-log:rpki-events;
                        description "Log event as a trigger for one or more EHS handlers";
                    }

                    leaf admin-state {
                        type types-sros:admin-state;
                        default "disable";
                        description "Administrative state of the EHS event trigger";
                    }

                    leaf description {
                        type types-sros:description;
                        description "Text description";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                    list entry {
                        key "id";
                        description "Enter the entry list instance";

                        leaf id {
                            type uint32 {
                                range "1..1500";
                            }
                            description "ID of the EHS event trigger entry";
                        }

                        leaf admin-state {
                            type types-sros:admin-state;
                            default "enable";
                            description "Administrative state of the EHS event trigger entry";
                        }

                        leaf description {
                            type types-sros:description;
                            description "Text description";
                        }

                        leaf filter {
                            type leafref {
                                path "../../../../filter/filter-name";
                            }
                            description "Log filter for EHS event trigger entry";
                        }

                        leaf handler {
                            type leafref {
                                path "../../../../event-handling/handler/name";
                            }
                            description "Event handler for EHS event trigger entry";
                        }

                        leaf-list apply-groups {
                            type leafref {
                                path "../../../../../groups/group/name";
                            }
                            max-elements 8;
                            ordered-by user;
                            description "Apply a configuration group at this level";
                        }

                        leaf-list apply-groups-exclude {
                            type leafref {
                                path "../../../../../groups/group/name";
                            }
                            max-elements 8;
                            ordered-by user;
                            description "Exclude a configuration group at this level";
                        }

                        container debounce {
                            description "Enter the debounce context";

                            leaf value {
                                type uint32 {
                                    range "2..15";
                                }
                                description "Occurrences in time interval to trigger EHS response";
                            }

                            leaf time {
                                type uint32 {
                                    range "1..604800";
                                }
                                units "seconds";
                                description "Time window for events for EHS to trigger a response";
                            }

                        } // container debounce

                    } // list entry

                } // list rpki

                list rsvp {
                    key "event";
                    description "Enter the rsvp list instance";

                    leaf event {
                        type types-log:rsvp-events;
                        description "Log event as a trigger for one or more EHS handlers";
                    }

                    leaf admin-state {
                        type types-sros:admin-state;
                        default "disable";
                        description "Administrative state of the EHS event trigger";
                    }

                    leaf description {
                        type types-sros:description;
                        description "Text description";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                    list entry {
                        key "id";
                        description "Enter the entry list instance";

                        leaf id {
                            type uint32 {
                                range "1..1500";
                            }
                            description "ID of the EHS event trigger entry";
                        }

                        leaf admin-state {
                            type types-sros:admin-state;
                            default "enable";
                            description "Administrative state of the EHS event trigger entry";
                        }

                        leaf description {
                            type types-sros:description;
                            description "Text description";
                        }

                        leaf filter {
                            type leafref {
                                path "../../../../filter/filter-name";
                            }
                            description "Log filter for EHS event trigger entry";
                        }

                        leaf handler {
                            type leafref {
                                path "../../../../event-handling/handler/name";
                            }
                            description "Event handler for EHS event trigger entry";
                        }

                        leaf-list apply-groups {
                            type leafref {
                                path "../../../../../groups/group/name";
                            }
                            max-elements 8;
                            ordered-by user;
                            description "Apply a configuration group at this level";
                        }

                        leaf-list apply-groups-exclude {
                            type leafref {
                                path "../../../../../groups/group/name";
                            }
                            max-elements 8;
                            ordered-by user;
                            description "Exclude a configuration group at this level";
                        }

                        container debounce {
                            description "Enter the debounce context";

                            leaf value {
                                type uint32 {
                                    range "2..15";
                                }
                                description "Occurrences in time interval to trigger EHS response";
                            }

                            leaf time {
                                type uint32 {
                                    range "1..604800";
                                }
                                units "seconds";
                                description "Time window for events for EHS to trigger a response";
                            }

                        } // container debounce

                    } // list entry

                } // list rsvp

                list satellite {
                    key "event";
                    description "Enter the satellite list instance";

                    leaf event {
                        type types-log:satellite-events;
                        description "Log event as a trigger for one or more EHS handlers";
                    }

                    leaf admin-state {
                        type types-sros:admin-state;
                        default "disable";
                        description "Administrative state of the EHS event trigger";
                    }

                    leaf description {
                        type types-sros:description;
                        description "Text description";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                    list entry {
                        key "id";
                        description "Enter the entry list instance";

                        leaf id {
                            type uint32 {
                                range "1..1500";
                            }
                            description "ID of the EHS event trigger entry";
                        }

                        leaf admin-state {
                            type types-sros:admin-state;
                            default "enable";
                            description "Administrative state of the EHS event trigger entry";
                        }

                        leaf description {
                            type types-sros:description;
                            description "Text description";
                        }

                        leaf filter {
                            type leafref {
                                path "../../../../filter/filter-name";
                            }
                            description "Log filter for EHS event trigger entry";
                        }

                        leaf handler {
                            type leafref {
                                path "../../../../event-handling/handler/name";
                            }
                            description "Event handler for EHS event trigger entry";
                        }

                        leaf-list apply-groups {
                            type leafref {
                                path "../../../../../groups/group/name";
                            }
                            max-elements 8;
                            ordered-by user;
                            description "Apply a configuration group at this level";
                        }

                        leaf-list apply-groups-exclude {
                            type leafref {
                                path "../../../../../groups/group/name";
                            }
                            max-elements 8;
                            ordered-by user;
                            description "Exclude a configuration group at this level";
                        }

                        container debounce {
                            description "Enter the debounce context";

                            leaf value {
                                type uint32 {
                                    range "2..15";
                                }
                                description "Occurrences in time interval to trigger EHS response";
                            }

                            leaf time {
                                type uint32 {
                                    range "1..604800";
                                }
                                units "seconds";
                                description "Time window for events for EHS to trigger a response";
                            }

                        } // container debounce

                    } // list entry

                } // list satellite

                list security {
                    key "event";
                    description "Enter the security list instance";

                    leaf event {
                        type types-log:security-events;
                        description "Log event as a trigger for one or more EHS handlers";
                    }

                    leaf admin-state {
                        type types-sros:admin-state;
                        default "disable";
                        description "Administrative state of the EHS event trigger";
                    }

                    leaf description {
                        type types-sros:description;
                        description "Text description";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                    list entry {
                        key "id";
                        description "Enter the entry list instance";

                        leaf id {
                            type uint32 {
                                range "1..1500";
                            }
                            description "ID of the EHS event trigger entry";
                        }

                        leaf admin-state {
                            type types-sros:admin-state;
                            default "enable";
                            description "Administrative state of the EHS event trigger entry";
                        }

                        leaf description {
                            type types-sros:description;
                            description "Text description";
                        }

                        leaf filter {
                            type leafref {
                                path "../../../../filter/filter-name";
                            }
                            description "Log filter for EHS event trigger entry";
                        }

                        leaf handler {
                            type leafref {
                                path "../../../../event-handling/handler/name";
                            }
                            description "Event handler for EHS event trigger entry";
                        }

                        leaf-list apply-groups {
                            type leafref {
                                path "../../../../../groups/group/name";
                            }
                            max-elements 8;
                            ordered-by user;
                            description "Apply a configuration group at this level";
                        }

                        leaf-list apply-groups-exclude {
                            type leafref {
                                path "../../../../../groups/group/name";
                            }
                            max-elements 8;
                            ordered-by user;
                            description "Exclude a configuration group at this level";
                        }

                        container debounce {
                            description "Enter the debounce context";

                            leaf value {
                                type uint32 {
                                    range "2..15";
                                }
                                description "Occurrences in time interval to trigger EHS response";
                            }

                            leaf time {
                                type uint32 {
                                    range "1..604800";
                                }
                                units "seconds";
                                description "Time window for events for EHS to trigger a response";
                            }

                        } // container debounce

                    } // list entry

                } // list security

                list sflow {
                    key "event";
                    description "Enter the sflow list instance";

                    leaf event {
                        type types-log:sflow-events;
                        description "Log event as a trigger for one or more EHS handlers";
                    }

                    leaf admin-state {
                        type types-sros:admin-state;
                        default "disable";
                        description "Administrative state of the EHS event trigger";
                    }

                    leaf description {
                        type types-sros:description;
                        description "Text description";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                    list entry {
                        key "id";
                        description "Enter the entry list instance";

                        leaf id {
                            type uint32 {
                                range "1..1500";
                            }
                            description "ID of the EHS event trigger entry";
                        }

                        leaf admin-state {
                            type types-sros:admin-state;
                            default "enable";
                            description "Administrative state of the EHS event trigger entry";
                        }

                        leaf description {
                            type types-sros:description;
                            description "Text description";
                        }

                        leaf filter {
                            type leafref {
                                path "../../../../filter/filter-name";
                            }
                            description "Log filter for EHS event trigger entry";
                        }

                        leaf handler {
                            type leafref {
                                path "../../../../event-handling/handler/name";
                            }
                            description "Event handler for EHS event trigger entry";
                        }

                        leaf-list apply-groups {
                            type leafref {
                                path "../../../../../groups/group/name";
                            }
                            max-elements 8;
                            ordered-by user;
                            description "Apply a configuration group at this level";
                        }

                        leaf-list apply-groups-exclude {
                            type leafref {
                                path "../../../../../groups/group/name";
                            }
                            max-elements 8;
                            ordered-by user;
                            description "Exclude a configuration group at this level";
                        }

                        container debounce {
                            description "Enter the debounce context";

                            leaf value {
                                type uint32 {
                                    range "2..15";
                                }
                                description "Occurrences in time interval to trigger EHS response";
                            }

                            leaf time {
                                type uint32 {
                                    range "1..604800";
                                }
                                units "seconds";
                                description "Time window for events for EHS to trigger a response";
                            }

                        } // container debounce

                    } // list entry

                } // list sflow

                list snmp {
                    key "event";
                    description "Enter the snmp list instance";

                    leaf event {
                        type types-log:snmp-events;
                        description "Log event as a trigger for one or more EHS handlers";
                    }

                    leaf admin-state {
                        type types-sros:admin-state;
                        default "disable";
                        description "Administrative state of the EHS event trigger";
                    }

                    leaf description {
                        type types-sros:description;
                        description "Text description";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                    list entry {
                        key "id";
                        description "Enter the entry list instance";

                        leaf id {
                            type uint32 {
                                range "1..1500";
                            }
                            description "ID of the EHS event trigger entry";
                        }

                        leaf admin-state {
                            type types-sros:admin-state;
                            default "enable";
                            description "Administrative state of the EHS event trigger entry";
                        }

                        leaf description {
                            type types-sros:description;
                            description "Text description";
                        }

                        leaf filter {
                            type leafref {
                                path "../../../../filter/filter-name";
                            }
                            description "Log filter for EHS event trigger entry";
                        }

                        leaf handler {
                            type leafref {
                                path "../../../../event-handling/handler/name";
                            }
                            description "Event handler for EHS event trigger entry";
                        }

                        leaf-list apply-groups {
                            type leafref {
                                path "../../../../../groups/group/name";
                            }
                            max-elements 8;
                            ordered-by user;
                            description "Apply a configuration group at this level";
                        }

                        leaf-list apply-groups-exclude {
                            type leafref {
                                path "../../../../../groups/group/name";
                            }
                            max-elements 8;
                            ordered-by user;
                            description "Exclude a configuration group at this level";
                        }

                        container debounce {
                            description "Enter the debounce context";

                            leaf value {
                                type uint32 {
                                    range "2..15";
                                }
                                description "Occurrences in time interval to trigger EHS response";
                            }

                            leaf time {
                                type uint32 {
                                    range "1..604800";
                                }
                                units "seconds";
                                description "Time window for events for EHS to trigger a response";
                            }

                        } // container debounce

                    } // list entry

                } // list snmp

                list sr-mpls {
                    key "event";
                    description "Enter the sr-mpls list instance";

                    leaf event {
                        type types-log:sr-mpls-events;
                        description "SR MPLS event";
                    }

                    leaf admin-state {
                        type types-sros:admin-state;
                        default "disable";
                        description "Administrative state of the EHS event trigger";
                    }

                    leaf description {
                        type types-sros:description;
                        description "Text description";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                    list entry {
                        key "id";
                        description "Enter the entry list instance";

                        leaf id {
                            type uint32 {
                                range "1..1500";
                            }
                            description "ID of the EHS event trigger entry";
                        }

                        leaf admin-state {
                            type types-sros:admin-state;
                            default "enable";
                            description "Administrative state of the EHS event trigger entry";
                        }

                        leaf description {
                            type types-sros:description;
                            description "Text description";
                        }

                        leaf filter {
                            type leafref {
                                path "../../../../filter/filter-name";
                            }
                            description "Log filter for EHS event trigger entry";
                        }

                        leaf handler {
                            type leafref {
                                path "../../../../event-handling/handler/name";
                            }
                            description "Event handler for EHS event trigger entry";
                        }

                        leaf-list apply-groups {
                            type leafref {
                                path "../../../../../groups/group/name";
                            }
                            max-elements 8;
                            ordered-by user;
                            description "Apply a configuration group at this level";
                        }

                        leaf-list apply-groups-exclude {
                            type leafref {
                                path "../../../../../groups/group/name";
                            }
                            max-elements 8;
                            ordered-by user;
                            description "Exclude a configuration group at this level";
                        }

                        container debounce {
                            description "Enter the debounce context";

                            leaf value {
                                type uint32 {
                                    range "2..15";
                                }
                                description "Occurrences in time interval to trigger EHS response";
                            }

                            leaf time {
                                type uint32 {
                                    range "1..604800";
                                }
                                units "seconds";
                                description "Time window for events for EHS to trigger a response";
                            }

                        } // container debounce

                    } // list entry

                } // list sr-mpls

                list sr-policy {
                    key "event";
                    description "Enter the sr-policy list instance";

                    leaf event {
                        type types-log:sr-policy-events;
                        description "Events for SR policy module";
                    }

                    leaf admin-state {
                        type types-sros:admin-state;
                        default "disable";
                        description "Administrative state of the EHS event trigger";
                    }

                    leaf description {
                        type types-sros:description;
                        description "Text description";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                    list entry {
                        key "id";
                        description "Enter the entry list instance";

                        leaf id {
                            type uint32 {
                                range "1..1500";
                            }
                            description "ID of the EHS event trigger entry";
                        }

                        leaf admin-state {
                            type types-sros:admin-state;
                            default "enable";
                            description "Administrative state of the EHS event trigger entry";
                        }

                        leaf description {
                            type types-sros:description;
                            description "Text description";
                        }

                        leaf filter {
                            type leafref {
                                path "../../../../filter/filter-name";
                            }
                            description "Log filter for EHS event trigger entry";
                        }

                        leaf handler {
                            type leafref {
                                path "../../../../event-handling/handler/name";
                            }
                            description "Event handler for EHS event trigger entry";
                        }

                        leaf-list apply-groups {
                            type leafref {
                                path "../../../../../groups/group/name";
                            }
                            max-elements 8;
                            ordered-by user;
                            description "Apply a configuration group at this level";
                        }

                        leaf-list apply-groups-exclude {
                            type leafref {
                                path "../../../../../groups/group/name";
                            }
                            max-elements 8;
                            ordered-by user;
                            description "Exclude a configuration group at this level";
                        }

                        container debounce {
                            description "Enter the debounce context";

                            leaf value {
                                type uint32 {
                                    range "2..15";
                                }
                                description "Occurrences in time interval to trigger EHS response";
                            }

                            leaf time {
                                type uint32 {
                                    range "1..604800";
                                }
                                units "seconds";
                                description "Time window for events for EHS to trigger a response";
                            }

                        } // container debounce

                    } // list entry

                } // list sr-policy

                list srv6 {
                    key "event";
                    description "Enter the srv6 list instance";

                    leaf event {
                        type types-log:srv6-events;
                        description "Log event as a trigger for one or more EHS handlers";
                    }

                    leaf admin-state {
                        type types-sros:admin-state;
                        default "disable";
                        description "Administrative state of the EHS event trigger";
                    }

                    leaf description {
                        type types-sros:description;
                        description "Text description";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                    list entry {
                        key "id";
                        description "Enter the entry list instance";

                        leaf id {
                            type uint32 {
                                range "1..1500";
                            }
                            description "ID of the EHS event trigger entry";
                        }

                        leaf admin-state {
                            type types-sros:admin-state;
                            default "enable";
                            description "Administrative state of the EHS event trigger entry";
                        }

                        leaf description {
                            type types-sros:description;
                            description "Text description";
                        }

                        leaf filter {
                            type leafref {
                                path "../../../../filter/filter-name";
                            }
                            description "Log filter for EHS event trigger entry";
                        }

                        leaf handler {
                            type leafref {
                                path "../../../../event-handling/handler/name";
                            }
                            description "Event handler for EHS event trigger entry";
                        }

                        leaf-list apply-groups {
                            type leafref {
                                path "../../../../../groups/group/name";
                            }
                            max-elements 8;
                            ordered-by user;
                            description "Apply a configuration group at this level";
                        }

                        leaf-list apply-groups-exclude {
                            type leafref {
                                path "../../../../../groups/group/name";
                            }
                            max-elements 8;
                            ordered-by user;
                            description "Exclude a configuration group at this level";
                        }

                        container debounce {
                            description "Enter the debounce context";

                            leaf value {
                                type uint32 {
                                    range "2..15";
                                }
                                description "Occurrences in time interval to trigger EHS response";
                            }

                            leaf time {
                                type uint32 {
                                    range "1..604800";
                                }
                                units "seconds";
                                description "Time window for events for EHS to trigger a response";
                            }

                        } // container debounce

                    } // list entry

                } // list srv6

                list stp {
                    key "event";
                    description "Enter the stp list instance";

                    leaf event {
                        type types-log:stp-events;
                        description "Log event as a trigger for one or more EHS handlers";
                    }

                    leaf admin-state {
                        type types-sros:admin-state;
                        default "disable";
                        description "Administrative state of the EHS event trigger";
                    }

                    leaf description {
                        type types-sros:description;
                        description "Text description";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                    list entry {
                        key "id";
                        description "Enter the entry list instance";

                        leaf id {
                            type uint32 {
                                range "1..1500";
                            }
                            description "ID of the EHS event trigger entry";
                        }

                        leaf admin-state {
                            type types-sros:admin-state;
                            default "enable";
                            description "Administrative state of the EHS event trigger entry";
                        }

                        leaf description {
                            type types-sros:description;
                            description "Text description";
                        }

                        leaf filter {
                            type leafref {
                                path "../../../../filter/filter-name";
                            }
                            description "Log filter for EHS event trigger entry";
                        }

                        leaf handler {
                            type leafref {
                                path "../../../../event-handling/handler/name";
                            }
                            description "Event handler for EHS event trigger entry";
                        }

                        leaf-list apply-groups {
                            type leafref {
                                path "../../../../../groups/group/name";
                            }
                            max-elements 8;
                            ordered-by user;
                            description "Apply a configuration group at this level";
                        }

                        leaf-list apply-groups-exclude {
                            type leafref {
                                path "../../../../../groups/group/name";
                            }
                            max-elements 8;
                            ordered-by user;
                            description "Exclude a configuration group at this level";
                        }

                        container debounce {
                            description "Enter the debounce context";

                            leaf value {
                                type uint32 {
                                    range "2..15";
                                }
                                description "Occurrences in time interval to trigger EHS response";
                            }

                            leaf time {
                                type uint32 {
                                    range "1..604800";
                                }
                                units "seconds";
                                description "Time window for events for EHS to trigger a response";
                            }

                        } // container debounce

                    } // list entry

                } // list stp

                list svcmgr {
                    key "event";
                    description "Enter the svcmgr list instance";

                    leaf event {
                        type types-log:svcmgr-events;
                        description "Log event as a trigger for one or more EHS handlers";
                    }

                    leaf admin-state {
                        type types-sros:admin-state;
                        default "disable";
                        description "Administrative state of the EHS event trigger";
                    }

                    leaf description {
                        type types-sros:description;
                        description "Text description";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                    list entry {
                        key "id";
                        description "Enter the entry list instance";

                        leaf id {
                            type uint32 {
                                range "1..1500";
                            }
                            description "ID of the EHS event trigger entry";
                        }

                        leaf admin-state {
                            type types-sros:admin-state;
                            default "enable";
                            description "Administrative state of the EHS event trigger entry";
                        }

                        leaf description {
                            type types-sros:description;
                            description "Text description";
                        }

                        leaf filter {
                            type leafref {
                                path "../../../../filter/filter-name";
                            }
                            description "Log filter for EHS event trigger entry";
                        }

                        leaf handler {
                            type leafref {
                                path "../../../../event-handling/handler/name";
                            }
                            description "Event handler for EHS event trigger entry";
                        }

                        leaf-list apply-groups {
                            type leafref {
                                path "../../../../../groups/group/name";
                            }
                            max-elements 8;
                            ordered-by user;
                            description "Apply a configuration group at this level";
                        }

                        leaf-list apply-groups-exclude {
                            type leafref {
                                path "../../../../../groups/group/name";
                            }
                            max-elements 8;
                            ordered-by user;
                            description "Exclude a configuration group at this level";
                        }

                        container debounce {
                            description "Enter the debounce context";

                            leaf value {
                                type uint32 {
                                    range "2..15";
                                }
                                description "Occurrences in time interval to trigger EHS response";
                            }

                            leaf time {
                                type uint32 {
                                    range "1..604800";
                                }
                                units "seconds";
                                description "Time window for events for EHS to trigger a response";
                            }

                        } // container debounce

                    } // list entry

                } // list svcmgr

                list system {
                    key "event";
                    description "Enter the system list instance";

                    leaf event {
                        type types-log:system-events;
                        description "Log event as a trigger for one or more EHS handlers";
                    }

                    leaf admin-state {
                        type types-sros:admin-state;
                        default "disable";
                        description "Administrative state of the EHS event trigger";
                    }

                    leaf description {
                        type types-sros:description;
                        description "Text description";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                    list entry {
                        key "id";
                        description "Enter the entry list instance";

                        leaf id {
                            type uint32 {
                                range "1..1500";
                            }
                            description "ID of the EHS event trigger entry";
                        }

                        leaf admin-state {
                            type types-sros:admin-state;
                            default "enable";
                            description "Administrative state of the EHS event trigger entry";
                        }

                        leaf description {
                            type types-sros:description;
                            description "Text description";
                        }

                        leaf filter {
                            type leafref {
                                path "../../../../filter/filter-name";
                            }
                            description "Log filter for EHS event trigger entry";
                        }

                        leaf handler {
                            type leafref {
                                path "../../../../event-handling/handler/name";
                            }
                            description "Event handler for EHS event trigger entry";
                        }

                        leaf-list apply-groups {
                            type leafref {
                                path "../../../../../groups/group/name";
                            }
                            max-elements 8;
                            ordered-by user;
                            description "Apply a configuration group at this level";
                        }

                        leaf-list apply-groups-exclude {
                            type leafref {
                                path "../../../../../groups/group/name";
                            }
                            max-elements 8;
                            ordered-by user;
                            description "Exclude a configuration group at this level";
                        }

                        container debounce {
                            description "Enter the debounce context";

                            leaf value {
                                type uint32 {
                                    range "2..15";
                                }
                                description "Occurrences in time interval to trigger EHS response";
                            }

                            leaf time {
                                type uint32 {
                                    range "1..604800";
                                }
                                units "seconds";
                                description "Time window for events for EHS to trigger a response";
                            }

                        } // container debounce

                    } // list entry

                } // list system

                list tls {
                    key "event";
                    description "Enter the tls list instance";

                    leaf event {
                        type types-log:tls-events;
                        description "Log event as a trigger for one or more EHS handlers";
                    }

                    leaf admin-state {
                        type types-sros:admin-state;
                        default "disable";
                        description "Administrative state of the EHS event trigger";
                    }

                    leaf description {
                        type types-sros:description;
                        description "Text description";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                    list entry {
                        key "id";
                        description "Enter the entry list instance";

                        leaf id {
                            type uint32 {
                                range "1..1500";
                            }
                            description "ID of the EHS event trigger entry";
                        }

                        leaf admin-state {
                            type types-sros:admin-state;
                            default "enable";
                            description "Administrative state of the EHS event trigger entry";
                        }

                        leaf description {
                            type types-sros:description;
                            description "Text description";
                        }

                        leaf filter {
                            type leafref {
                                path "../../../../filter/filter-name";
                            }
                            description "Log filter for EHS event trigger entry";
                        }

                        leaf handler {
                            type leafref {
                                path "../../../../event-handling/handler/name";
                            }
                            description "Event handler for EHS event trigger entry";
                        }

                        leaf-list apply-groups {
                            type leafref {
                                path "../../../../../groups/group/name";
                            }
                            max-elements 8;
                            ordered-by user;
                            description "Apply a configuration group at this level";
                        }

                        leaf-list apply-groups-exclude {
                            type leafref {
                                path "../../../../../groups/group/name";
                            }
                            max-elements 8;
                            ordered-by user;
                            description "Exclude a configuration group at this level";
                        }

                        container debounce {
                            description "Enter the debounce context";

                            leaf value {
                                type uint32 {
                                    range "2..15";
                                }
                                description "Occurrences in time interval to trigger EHS response";
                            }

                            leaf time {
                                type uint32 {
                                    range "1..604800";
                                }
                                units "seconds";
                                description "Time window for events for EHS to trigger a response";
                            }

                        } // container debounce

                    } // list entry

                } // list tls

                list tree-sid {
                    key "event";
                    description "Enter the tree-sid list instance";

                    leaf event {
                        type types-log:treesid-events;
                        description "Log event as a trigger for one or more EHS handlers";
                    }

                    leaf admin-state {
                        type types-sros:admin-state;
                        default "disable";
                        description "Administrative state of the EHS event trigger";
                    }

                    leaf description {
                        type types-sros:description;
                        description "Text description";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                    list entry {
                        key "id";
                        description "Enter the entry list instance";

                        leaf id {
                            type uint32 {
                                range "1..1500";
                            }
                            description "ID of the EHS event trigger entry";
                        }

                        leaf admin-state {
                            type types-sros:admin-state;
                            default "enable";
                            description "Administrative state of the EHS event trigger entry";
                        }

                        leaf description {
                            type types-sros:description;
                            description "Text description";
                        }

                        leaf filter {
                            type leafref {
                                path "../../../../filter/filter-name";
                            }
                            description "Log filter for EHS event trigger entry";
                        }

                        leaf handler {
                            type leafref {
                                path "../../../../event-handling/handler/name";
                            }
                            description "Event handler for EHS event trigger entry";
                        }

                        leaf-list apply-groups {
                            type leafref {
                                path "../../../../../groups/group/name";
                            }
                            max-elements 8;
                            ordered-by user;
                            description "Apply a configuration group at this level";
                        }

                        leaf-list apply-groups-exclude {
                            type leafref {
                                path "../../../../../groups/group/name";
                            }
                            max-elements 8;
                            ordered-by user;
                            description "Exclude a configuration group at this level";
                        }

                        container debounce {
                            description "Enter the debounce context";

                            leaf value {
                                type uint32 {
                                    range "2..15";
                                }
                                description "Occurrences in time interval to trigger EHS response";
                            }

                            leaf time {
                                type uint32 {
                                    range "1..604800";
                                }
                                units "seconds";
                                description "Time window for events for EHS to trigger a response";
                            }

                        } // container debounce

                    } // list entry

                } // list tree-sid

                list user {
                    key "event";
                    description "Enter the user list instance";

                    leaf event {
                        type types-log:user-events;
                        description "Log event as a trigger for one or more EHS handlers";
                    }

                    leaf admin-state {
                        type types-sros:admin-state;
                        default "disable";
                        description "Administrative state of the EHS event trigger";
                    }

                    leaf description {
                        type types-sros:description;
                        description "Text description";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                    list entry {
                        key "id";
                        description "Enter the entry list instance";

                        leaf id {
                            type uint32 {
                                range "1..1500";
                            }
                            description "ID of the EHS event trigger entry";
                        }

                        leaf admin-state {
                            type types-sros:admin-state;
                            default "enable";
                            description "Administrative state of the EHS event trigger entry";
                        }

                        leaf description {
                            type types-sros:description;
                            description "Text description";
                        }

                        leaf filter {
                            type leafref {
                                path "../../../../filter/filter-name";
                            }
                            description "Log filter for EHS event trigger entry";
                        }

                        leaf handler {
                            type leafref {
                                path "../../../../event-handling/handler/name";
                            }
                            description "Event handler for EHS event trigger entry";
                        }

                        leaf-list apply-groups {
                            type leafref {
                                path "../../../../../groups/group/name";
                            }
                            max-elements 8;
                            ordered-by user;
                            description "Apply a configuration group at this level";
                        }

                        leaf-list apply-groups-exclude {
                            type leafref {
                                path "../../../../../groups/group/name";
                            }
                            max-elements 8;
                            ordered-by user;
                            description "Exclude a configuration group at this level";
                        }

                        container debounce {
                            description "Enter the debounce context";

                            leaf value {
                                type uint32 {
                                    range "2..15";
                                }
                                description "Occurrences in time interval to trigger EHS response";
                            }

                            leaf time {
                                type uint32 {
                                    range "1..604800";
                                }
                                units "seconds";
                                description "Time window for events for EHS to trigger a response";
                            }

                        } // container debounce

                    } // list entry

                } // list user

                list video {
                    key "event";
                    description "Enter the video list instance";

                    leaf event {
                        type types-log:video-events;
                        description "Log event as a trigger for one or more EHS handlers";
                    }

                    leaf admin-state {
                        type types-sros:admin-state;
                        default "disable";
                        description "Administrative state of the EHS event trigger";
                    }

                    leaf description {
                        type types-sros:description;
                        description "Text description";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                    list entry {
                        key "id";
                        description "Enter the entry list instance";

                        leaf id {
                            type uint32 {
                                range "1..1500";
                            }
                            description "ID of the EHS event trigger entry";
                        }

                        leaf admin-state {
                            type types-sros:admin-state;
                            default "enable";
                            description "Administrative state of the EHS event trigger entry";
                        }

                        leaf description {
                            type types-sros:description;
                            description "Text description";
                        }

                        leaf filter {
                            type leafref {
                                path "../../../../filter/filter-name";
                            }
                            description "Log filter for EHS event trigger entry";
                        }

                        leaf handler {
                            type leafref {
                                path "../../../../event-handling/handler/name";
                            }
                            description "Event handler for EHS event trigger entry";
                        }

                        leaf-list apply-groups {
                            type leafref {
                                path "../../../../../groups/group/name";
                            }
                            max-elements 8;
                            ordered-by user;
                            description "Apply a configuration group at this level";
                        }

                        leaf-list apply-groups-exclude {
                            type leafref {
                                path "../../../../../groups/group/name";
                            }
                            max-elements 8;
                            ordered-by user;
                            description "Exclude a configuration group at this level";
                        }

                        container debounce {
                            description "Enter the debounce context";

                            leaf value {
                                type uint32 {
                                    range "2..15";
                                }
                                description "Occurrences in time interval to trigger EHS response";
                            }

                            leaf time {
                                type uint32 {
                                    range "1..604800";
                                }
                                units "seconds";
                                description "Time window for events for EHS to trigger a response";
                            }

                        } // container debounce

                    } // list entry

                } // list video

                list vrrp {
                    key "event";
                    description "Enter the vrrp list instance";

                    leaf event {
                        type types-log:vrrp-events;
                        description "Log event as a trigger for one or more EHS handlers";
                    }

                    leaf admin-state {
                        type types-sros:admin-state;
                        default "disable";
                        description "Administrative state of the EHS event trigger";
                    }

                    leaf description {
                        type types-sros:description;
                        description "Text description";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                    list entry {
                        key "id";
                        description "Enter the entry list instance";

                        leaf id {
                            type uint32 {
                                range "1..1500";
                            }
                            description "ID of the EHS event trigger entry";
                        }

                        leaf admin-state {
                            type types-sros:admin-state;
                            default "enable";
                            description "Administrative state of the EHS event trigger entry";
                        }

                        leaf description {
                            type types-sros:description;
                            description "Text description";
                        }

                        leaf filter {
                            type leafref {
                                path "../../../../filter/filter-name";
                            }
                            description "Log filter for EHS event trigger entry";
                        }

                        leaf handler {
                            type leafref {
                                path "../../../../event-handling/handler/name";
                            }
                            description "Event handler for EHS event trigger entry";
                        }

                        leaf-list apply-groups {
                            type leafref {
                                path "../../../../../groups/group/name";
                            }
                            max-elements 8;
                            ordered-by user;
                            description "Apply a configuration group at this level";
                        }

                        leaf-list apply-groups-exclude {
                            type leafref {
                                path "../../../../../groups/group/name";
                            }
                            max-elements 8;
                            ordered-by user;
                            description "Exclude a configuration group at this level";
                        }

                        container debounce {
                            description "Enter the debounce context";

                            leaf value {
                                type uint32 {
                                    range "2..15";
                                }
                                description "Occurrences in time interval to trigger EHS response";
                            }

                            leaf time {
                                type uint32 {
                                    range "1..604800";
                                }
                                units "seconds";
                                description "Time window for events for EHS to trigger a response";
                            }

                        } // container debounce

                    } // list entry

                } // list vrrp

                list vrtr {
                    key "event";
                    description "Enter the vrtr list instance";

                    leaf event {
                        type types-log:vrtr-events;
                        description "Log event as a trigger for one or more EHS handlers";
                    }

                    leaf admin-state {
                        type types-sros:admin-state;
                        default "disable";
                        description "Administrative state of the EHS event trigger";
                    }

                    leaf description {
                        type types-sros:description;
                        description "Text description";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                    list entry {
                        key "id";
                        description "Enter the entry list instance";

                        leaf id {
                            type uint32 {
                                range "1..1500";
                            }
                            description "ID of the EHS event trigger entry";
                        }

                        leaf admin-state {
                            type types-sros:admin-state;
                            default "enable";
                            description "Administrative state of the EHS event trigger entry";
                        }

                        leaf description {
                            type types-sros:description;
                            description "Text description";
                        }

                        leaf filter {
                            type leafref {
                                path "../../../../filter/filter-name";
                            }
                            description "Log filter for EHS event trigger entry";
                        }

                        leaf handler {
                            type leafref {
                                path "../../../../event-handling/handler/name";
                            }
                            description "Event handler for EHS event trigger entry";
                        }

                        leaf-list apply-groups {
                            type leafref {
                                path "../../../../../groups/group/name";
                            }
                            max-elements 8;
                            ordered-by user;
                            description "Apply a configuration group at this level";
                        }

                        leaf-list apply-groups-exclude {
                            type leafref {
                                path "../../../../../groups/group/name";
                            }
                            max-elements 8;
                            ordered-by user;
                            description "Exclude a configuration group at this level";
                        }

                        container debounce {
                            description "Enter the debounce context";

                            leaf value {
                                type uint32 {
                                    range "2..15";
                                }
                                description "Occurrences in time interval to trigger EHS response";
                            }

                            leaf time {
                                type uint32 {
                                    range "1..604800";
                                }
                                units "seconds";
                                description "Time window for events for EHS to trigger a response";
                            }

                        } // container debounce

                    } // list entry

                } // list vrtr

                list wlan-gw {
                    key "event";
                    description "Enter the wlan-gw list instance";

                    leaf event {
                        type types-log:wlan-gw-events;
                        description "Log event as a trigger for one or more EHS handlers";
                    }

                    leaf admin-state {
                        type types-sros:admin-state;
                        default "disable";
                        description "Administrative state of the EHS event trigger";
                    }

                    leaf description {
                        type types-sros:description;
                        description "Text description";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                    list entry {
                        key "id";
                        description "Enter the entry list instance";

                        leaf id {
                            type uint32 {
                                range "1..1500";
                            }
                            description "ID of the EHS event trigger entry";
                        }

                        leaf admin-state {
                            type types-sros:admin-state;
                            default "enable";
                            description "Administrative state of the EHS event trigger entry";
                        }

                        leaf description {
                            type types-sros:description;
                            description "Text description";
                        }

                        leaf filter {
                            type leafref {
                                path "../../../../filter/filter-name";
                            }
                            description "Log filter for EHS event trigger entry";
                        }

                        leaf handler {
                            type leafref {
                                path "../../../../event-handling/handler/name";
                            }
                            description "Event handler for EHS event trigger entry";
                        }

                        leaf-list apply-groups {
                            type leafref {
                                path "../../../../../groups/group/name";
                            }
                            max-elements 8;
                            ordered-by user;
                            description "Apply a configuration group at this level";
                        }

                        leaf-list apply-groups-exclude {
                            type leafref {
                                path "../../../../../groups/group/name";
                            }
                            max-elements 8;
                            ordered-by user;
                            description "Exclude a configuration group at this level";
                        }

                        container debounce {
                            description "Enter the debounce context";

                            leaf value {
                                type uint32 {
                                    range "2..15";
                                }
                                description "Occurrences in time interval to trigger EHS response";
                            }

                            leaf time {
                                type uint32 {
                                    range "1..604800";
                                }
                                units "seconds";
                                description "Time window for events for EHS to trigger a response";
                            }

                        } // container debounce

                    } // list entry

                } // list wlan-gw

                list wpp {
                    key "event";
                    description "Enter the wpp list instance";

                    leaf event {
                        type types-log:wpp-events;
                        description "Log event as a trigger for one or more EHS handlers";
                    }

                    leaf admin-state {
                        type types-sros:admin-state;
                        default "disable";
                        description "Administrative state of the EHS event trigger";
                    }

                    leaf description {
                        type types-sros:description;
                        description "Text description";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                    list entry {
                        key "id";
                        description "Enter the entry list instance";

                        leaf id {
                            type uint32 {
                                range "1..1500";
                            }
                            description "ID of the EHS event trigger entry";
                        }

                        leaf admin-state {
                            type types-sros:admin-state;
                            default "enable";
                            description "Administrative state of the EHS event trigger entry";
                        }

                        leaf description {
                            type types-sros:description;
                            description "Text description";
                        }

                        leaf filter {
                            type leafref {
                                path "../../../../filter/filter-name";
                            }
                            description "Log filter for EHS event trigger entry";
                        }

                        leaf handler {
                            type leafref {
                                path "../../../../event-handling/handler/name";
                            }
                            description "Event handler for EHS event trigger entry";
                        }

                        leaf-list apply-groups {
                            type leafref {
                                path "../../../../../groups/group/name";
                            }
                            max-elements 8;
                            ordered-by user;
                            description "Apply a configuration group at this level";
                        }

                        leaf-list apply-groups-exclude {
                            type leafref {
                                path "../../../../../groups/group/name";
                            }
                            max-elements 8;
                            ordered-by user;
                            description "Exclude a configuration group at this level";
                        }

                        container debounce {
                            description "Enter the debounce context";

                            leaf value {
                                type uint32 {
                                    range "2..15";
                                }
                                description "Occurrences in time interval to trigger EHS response";
                            }

                            leaf time {
                                type uint32 {
                                    range "1..604800";
                                }
                                units "seconds";
                                description "Time window for events for EHS to trigger a response";
                            }

                        } // container debounce

                    } // list entry

                } // list wpp

            } // container event-trigger

            list file {
                key "file-policy-name";
                max-elements 99;
                description "Enter the file list instance";

                leaf file-policy-name {
                    type types-log:file-policy-name;
                    description "File ID for a log or accounting file";
                }

                leaf description {
                    type types-sros:description;
                    description "Text description";
                }

                leaf rollover {
                    type int32 {
                        range "5..10080";
                    }
                    units "minutes";
                    default "1440";
                    description "Frequency at which a new log or accounting file is created";
                }

                leaf retention {
                    type int32 {
                        range "1..500";
                    }
                    units "hours";
                    default "12";
                    description "Minimum time that a file is retained on the media";
                }

                leaf-list apply-groups {
                    type leafref {
                        path "../../../groups/group/name";
                    }
                    max-elements 8;
                    ordered-by user;
                    description "Apply a configuration group at this level";
                }

                leaf-list apply-groups-exclude {
                    type leafref {
                        path "../../../groups/group/name";
                    }
                    max-elements 8;
                    ordered-by user;
                    description "Exclude a configuration group at this level";
                }

                container compact-flash-location {
                    description "Enter the compact-flash-location context";

                    leaf primary {
                        type types-log:compact-flash-drive;
                        sros-ext:immutable;
                        default "cf-unspecified";
                        description "Log file location";
                    }

                    leaf backup {
                        type types-log:compact-flash-drive;
                        sros-ext:immutable;
                        default "cf-unspecified";
                        description "Log file location";
                    }

                } // container compact-flash-location

            } // list file

            list filter {
                key "filter-name";
                max-elements 1500;
                description "Enter the filter list instance";

                leaf filter-name {
                    type types-log:log-filter-name;
                    description "Filter name";
                }

                leaf description {
                    type types-sros:description;
                    description "Text description";
                }

                leaf default-action {
                    type types-log:filter-action;
                    description "Default action for the event filter";
                }

                leaf-list apply-groups {
                    type leafref {
                        path "../../../groups/group/name";
                    }
                    max-elements 8;
                    ordered-by user;
                    description "Apply a configuration group at this level";
                }

                leaf-list apply-groups-exclude {
                    type leafref {
                        path "../../../groups/group/name";
                    }
                    max-elements 8;
                    ordered-by user;
                    description "Exclude a configuration group at this level";
                }

                list entry {
                    status obsolete;
                    key "entry-id";
                    description "Enter the entry list instance";

                    leaf entry-id {
                        status obsolete;
                        type uint32 {
                            range "1..999";
                        }
                        description "Identification number for an event log filter parameter";
                    }

                    leaf description {
                        status obsolete;
                        type types-sros:description;
                        description "Text description";
                    }

                    leaf action {
                        status obsolete;
                        type types-log:filter-action;
                        description "Action for this event filter entry";
                    }

                    leaf-list apply-groups {
                        status obsolete;
                        type leafref {
                            path "../../../../groups/group/name";
                        }
                        max-elements 8;
                        ordered-by user;
                        description "Apply a configuration group at this level";
                    }

                    leaf-list apply-groups-exclude {
                        status obsolete;
                        type leafref {
                            path "../../../../groups/group/name";
                        }
                        max-elements 8;
                        ordered-by user;
                        description "Exclude a configuration group at this level";
                    }

                    container match {
                        status obsolete;
                        description "Enter the match context";

                        container application {
                            status obsolete;
                            description "Enter the application context";

                            choice application-match {
                                status obsolete;
                                case eq {
                                    status obsolete;

                                    leaf eq {
                                        status obsolete;
                                        type types-log:application-obsolete;
                                        description "Application to match";
                                    }

                                }
                                case neq {
                                    status obsolete;

                                    leaf neq {
                                        status obsolete;
                                        type types-log:application-obsolete;
                                        description "Application to be filtered out";
                                    }

                                }
                            }
                        } // container application

                        container event {
                            status obsolete;
                            description "Enter the event context";

                            choice event-match {
                                status obsolete;
                                case eq {
                                    status obsolete;

                                    leaf eq {
                                        status obsolete;
                                        type uint32 {
                                            range "1..max";
                                        }
                                        description "Log event message to match";
                                    }

                                }
                                case neq {
                                    status obsolete;

                                    leaf neq {
                                        status obsolete;
                                        type uint32 {
                                            range "1..max";
                                        }
                                        description "Log event message to filter out";
                                    }

                                }
                                case lt {
                                    status obsolete;

                                    leaf lt {
                                        status obsolete;
                                        type uint32 {
                                            range "1..max";
                                        }
                                        description "Number of the log event to match";
                                    }

                                }
                                case lte {
                                    status obsolete;

                                    leaf lte {
                                        status obsolete;
                                        type uint32 {
                                            range "1..max";
                                        }
                                        description "Number of the log event to match";
                                    }

                                }
                                case gt {
                                    status obsolete;

                                    leaf gt {
                                        status obsolete;
                                        type uint32 {
                                            range "1..max";
                                        }
                                        description "Number of the log event to match";
                                    }

                                }
                                case gte {
                                    status obsolete;

                                    leaf gte {
                                        status obsolete;
                                        type uint32 {
                                            range "1..max";
                                        }
                                        description "Number of the log event to match";
                                    }

                                }
                            }
                        } // container event

                        container message {
                            status obsolete;
                            description "Enter the message context";

                            leaf regexp {
                                status obsolete;
                                type boolean;
                                default "false";
                                description "String comparison to determine if the log event matches the value of pattern";
                            }

                            choice message-match {
                                status obsolete;
                                case eq {
                                    status obsolete;

                                    leaf eq {
                                        status obsolete;
                                        type string {
                                            length "1..400";
                                        }
                                        description "Log event message to match";
                                    }

                                }
                                case neq {
                                    status obsolete;

                                    leaf neq {
                                        status obsolete;
                                        type string {
                                            length "1..400";
                                        }
                                        description "Log event message to be filtered out";
                                    }

                                }
                            }
                        } // container message

                        container vrtr-name {
                            status obsolete;
                            description "Enter the vrtr-name context";

                            leaf regexp {
                                status obsolete;
                                type boolean;
                                default "false";
                                description "Match the router instance string";
                            }

                            choice vrtr-name-match {
                                status obsolete;
                                case eq {
                                    status obsolete;

                                    leaf eq {
                                        status obsolete;
                                        type types-sros:named-item;
                                        description "Log event router instance to match";
                                    }

                                }
                                case neq {
                                    status obsolete;

                                    leaf neq {
                                        status obsolete;
                                        type types-sros:named-item;
                                        description "Log event router instance to filter out";
                                    }

                                }
                            }
                        } // container vrtr-name

                        container severity {
                            status obsolete;
                            description "Enter the severity context";

                            choice severity-match {
                                status obsolete;
                                case eq {
                                    status obsolete;

                                    leaf eq {
                                        status obsolete;
                                        type types-log:severity-level;
                                        description "Log event severity level to match";
                                    }

                                }
                                case neq {
                                    status obsolete;

                                    leaf neq {
                                        status obsolete;
                                        type types-log:severity-level;
                                        description "Log event severity level to filter out";
                                    }

                                }
                                case lt {
                                    status obsolete;

                                    leaf lt {
                                        status obsolete;
                                        type types-log:severity-level;
                                        description "Log event severity level";
                                    }

                                }
                                case lte {
                                    status obsolete;

                                    leaf lte {
                                        status obsolete;
                                        type types-log:severity-level;
                                        description "Log event severity level";
                                    }

                                }
                                case gt {
                                    status obsolete;

                                    leaf gt {
                                        status obsolete;
                                        type types-log:severity-level;
                                        description "Log event severity level";
                                    }

                                }
                                case gte {
                                    status obsolete;

                                    leaf gte {
                                        status obsolete;
                                        type types-log:severity-level;
                                        description "Log event severity level";
                                    }

                                }
                            }
                        } // container severity

                        container subject {
                            status obsolete;
                            description "Enter the subject context";

                            leaf regexp {
                                status obsolete;
                                type boolean;
                                default "false";
                                description "String comparison to determine if the log event matches the value of subject";
                            }

                            choice subject-match {
                                status obsolete;
                                case eq {
                                    status obsolete;

                                    leaf eq {
                                        status obsolete;
                                        type types-sros:named-item;
                                        description "Log event subject string to match";
                                    }

                                }
                                case neq {
                                    status obsolete;

                                    leaf neq {
                                        status obsolete;
                                        type types-sros:named-item;
                                        description "Log event subject string to filter out";
                                    }

                                }
                            }
                        } // container subject

                    } // container match

                } // list entry

                list named-entry {
                    key "entry-name";
                    max-elements 999;
                    ordered-by user;
                    description "Enter the named-entry list instance";

                    leaf entry-name {
                        type types-log:log-filter-entry-name;
                        description "Entry name";
                    }

                    leaf description {
                        type types-sros:description;
                        description "Text description";
                    }

                    leaf action {
                        type types-log:filter-action;
                        description "Action for this event filter entry";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                    container match {
                        description "Enter the match context";

                        container application {
                            description "Enter the application context";

                            choice application-match {
                                case eq {

                                    leaf eq {
                                        type types-log:application;
                                        description "Application to match";
                                    }

                                }
                                case neq {

                                    leaf neq {
                                        type types-log:application;
                                        description "Application to be filtered out";
                                    }

                                }
                            }
                        } // container application

                        container event {
                            description "Enter the event context";

                            choice event-match {
                                case eq {

                                    leaf eq {
                                        type uint32 {
                                            range "1..max";
                                        }
                                        description "Log event message to match";
                                    }

                                }
                                case neq {

                                    leaf neq {
                                        type uint32 {
                                            range "1..max";
                                        }
                                        description "Log event message to filter out";
                                    }

                                }
                                case lt {

                                    leaf lt {
                                        type uint32 {
                                            range "1..max";
                                        }
                                        description "Number of the log event to match";
                                    }

                                }
                                case lte {

                                    leaf lte {
                                        type uint32 {
                                            range "1..max";
                                        }
                                        description "Number of the log event to match";
                                    }

                                }
                                case gt {

                                    leaf gt {
                                        type uint32 {
                                            range "1..max";
                                        }
                                        description "Number of the log event to match";
                                    }

                                }
                                case gte {

                                    leaf gte {
                                        type uint32 {
                                            range "1..max";
                                        }
                                        description "Number of the log event to match";
                                    }

                                }
                            }
                        } // container event

                        container message {
                            description "Enter the message context";

                            leaf regexp {
                                type boolean;
                                default "false";
                                description "String comparison to determine if the log event matches the value of pattern";
                            }

                            choice message-match {
                                case eq {

                                    leaf eq {
                                        type string {
                                            length "1..400";
                                        }
                                        description "Log event message to match";
                                    }

                                }
                                case neq {

                                    leaf neq {
                                        type string {
                                            length "1..400";
                                        }
                                        description "Log event message to be filtered out";
                                    }

                                }
                            }
                        } // container message

                        container vrtr-name {
                            description "Enter the vrtr-name context";

                            leaf regexp {
                                type boolean;
                                default "false";
                                description "Match the router instance string";
                            }

                            choice vrtr-name-match {
                                case eq {

                                    leaf eq {
                                        type types-sros:named-item;
                                        description "Log event router instance to match";
                                    }

                                }
                                case neq {

                                    leaf neq {
                                        type types-sros:named-item;
                                        description "Log event router instance to filter out";
                                    }

                                }
                            }
                        } // container vrtr-name

                        container severity {
                            description "Enter the severity context";

                            choice severity-match {
                                case eq {

                                    leaf eq {
                                        type types-log:severity-level;
                                        description "Log event severity level to match";
                                    }

                                }
                                case neq {

                                    leaf neq {
                                        type types-log:severity-level;
                                        description "Log event severity level to filter out";
                                    }

                                }
                                case lt {

                                    leaf lt {
                                        type types-log:severity-level;
                                        description "Log event severity level";
                                    }

                                }
                                case lte {

                                    leaf lte {
                                        type types-log:severity-level;
                                        description "Log event severity level";
                                    }

                                }
                                case gt {

                                    leaf gt {
                                        type types-log:severity-level;
                                        description "Log event severity level";
                                    }

                                }
                                case gte {

                                    leaf gte {
                                        type types-log:severity-level;
                                        description "Log event severity level";
                                    }

                                }
                            }
                        } // container severity

                        container subject {
                            description "Enter the subject context";

                            leaf regexp {
                                type boolean;
                                default "false";
                                description "String comparison to determine if the log event matches the value of subject";
                            }

                            choice subject-match {
                                case eq {

                                    leaf eq {
                                        type types-sros:named-item;
                                        description "Log event subject string to match";
                                    }

                                }
                                case neq {

                                    leaf neq {
                                        type types-sros:named-item;
                                        description "Log event subject string to filter out";
                                    }

                                }
                            }
                        } // container subject

                    } // container match

                } // list named-entry

            } // list filter

            list log-id {
                key "name";
                max-elements 30;
                description "Enter the log-id list instance";

                leaf name {
                    type types-log:log-name;
                    description "Log ID";
                }

                leaf admin-state {
                    type types-sros:admin-state;
                    default "enable";
                    description "Administrative state of the log";
                }

                leaf description {
                    type types-sros:description;
                    description "Text description";
                }

                leaf netconf-stream {
                    type types-sros:named-item;
                    description "Destination NETCONF stream name";
                }

                leaf time-format {
                    type enumeration {
                        enum utc                            { value 1; }
                        enum local                          { value 2; }
                    }
                    default "utc";
                    description "Time zone output for file log contents and syslog";
                }

                leaf python-policy {
                    type leafref {
                        path "../../../python/python-policy/name";
                    }
                    description "Python policy name";
                }

                leaf filter {
                    type leafref {
                        path "../../filter/filter-name";
                    }
                    description "Event filter policy with the log destination";
                }

                leaf-list apply-groups {
                    type leafref {
                        path "../../../groups/group/name";
                    }
                    max-elements 8;
                    ordered-by user;
                    description "Apply a configuration group at this level";
                }

                leaf-list apply-groups-exclude {
                    type leafref {
                        path "../../../groups/group/name";
                    }
                    max-elements 8;
                    ordered-by user;
                    description "Exclude a configuration group at this level";
                }

                container source {
                    description "Enter the source context";

                    leaf main {
                        type boolean;
                        description "Collect log events from the main event stream";
                    }

                    leaf security {
                        type boolean;
                        description "Collect log events from the security event stream";
                    }

                    leaf change {
                        type boolean;
                        description "Collect log events from change event stream";
                    }

                    leaf debug {
                        type boolean;
                        default "false";
                        description "Collect log events from the debug event stream";
                    }

                } // container source

                container destination {
                    description "Enter the destination context";

                    choice log-id-destination {
                        case file {

                            leaf file {
                                type leafref {
                                    path "../../../file/file-policy-name";
                                }
                                sros-ext:immutable;
                                description "File to send log events";
                            }

                        }
                        case syslog {

                            leaf syslog {
                                type leafref {
                                    path "../../../syslog/syslog-name";
                                }
                                sros-ext:immutable;
                                description "Syslog collector to send log events";
                            }

                        }
                        case memory {

                            container memory {
                                presence "Enable the memory context";
                                description "Enable the memory context";

                                leaf max-entries {
                                    type uint32 {
                                        range "50..3000";
                                    }
                                    sros-ext:immutable;
                                    default "100";
                                    description "Number of events stored in this memory log";
                                }

                            } // container memory

                        }
                        case snmp {

                            container snmp {
                                presence "Enable the snmp context";
                                description "Enable the snmp context";

                                leaf max-entries {
                                    type uint32 {
                                        range "50..3000";
                                    }
                                    sros-ext:immutable;
                                    default "100";
                                    description "Number of events stored in this SNMP log";
                                }

                            } // container snmp

                        }
                        case console {

                            leaf console {
                                type empty;
                                sros-ext:immutable;
                                description "Send log events to the system console port";
                            }

                        }
                        case netconf {

                            container netconf {
                                presence "Enable the netconf context";
                                description "Enable the netconf context";

                                leaf max-entries {
                                    type uint32 {
                                        range "50..3000";
                                    }
                                    sros-ext:immutable;
                                    description "Number of events stored in this NETCONF log";
                                }

                            } // container netconf

                        }
                        case cli {

                            container cli {
                                presence "Enable the cli context";
                                description "Enable the cli context";

                                leaf max-entries {
                                    type uint32 {
                                        range "50..3000";
                                    }
                                    sros-ext:immutable;
                                    default "100";
                                    description "Number of events stored in this CLI log";
                                }

                            } // container cli

                        }
                    }
                } // container destination

            } // list log-id

            container route-preference {
                description "Enter the route-preference context";

                leaf primary {
                    type enumeration {
                        enum inband                         { value 1; }
                        enum outband                        { value 2; }
                    }
                    default "outband";
                    description "Primary routing preference for traffic that is generated for SNMP notifications and syslog messages";
                }

                leaf secondary {
                    type enumeration {
                        enum inband                         { value 1; }
                        enum outband                        { value 2; }
                        enum none                           { value 3; }
                    }
                    default "inband";
                    description "Secondary route preference for SNMP and syslog traffic";
                }

            } // container route-preference

            container services-all-events {
                description "Enter the services-all-events context";

                list service {
                    key "service-name";
                    description "Add a list entry for service";

                    leaf service-name {
                        type leafref {
                            path "../../../../service/vprn/service-name";
                        }
                        description "Administrative service name";
                    }

                } // list service

            } // container services-all-events

            list snmp-trap-group {
                key "log-name";
                max-elements 15;
                description "Enter the snmp-trap-group list instance";

                leaf log-name {
                    type types-log:snmp-trap-group-name;
                    description "Log ID";
                }

                leaf description {
                    type types-sros:description;
                    description "Text description";
                }

                leaf log-id {
                    status obsolete;
                    type int32 {
                        range "1..100";
                    }
                    sros-ext:immutable;
                    description "SNMP notification group associated with the event log";
                }

                leaf-list apply-groups {
                    type leafref {
                        path "../../../groups/group/name";
                    }
                    max-elements 8;
                    ordered-by user;
                    description "Apply a configuration group at this level";
                }

                leaf-list apply-groups-exclude {
                    type leafref {
                        path "../../../groups/group/name";
                    }
                    max-elements 8;
                    ordered-by user;
                    description "Exclude a configuration group at this level";
                }

                list trap-target {
                    key "name";
                    max-elements 25;
                    description "Enter the trap-target list instance";

                    leaf name {
                        type string {
                            length "1..28";
                        }
                        description "Trap target name";
                    }

                    leaf description {
                        type types-sros:description;
                        description "Text description";
                    }

                    leaf address {
                        type types-sros:ip-unicast-address;
                        mandatory true;
                        description "IP address of the trap receiver";
                    }

                    leaf port {
                        type types-qos:tcp-udp-match-port;
                        default "162";
                        description "UDP port number to send messages to this remote SNMP notification collector";
                    }

                    leaf version {
                        type enumeration {
                            enum snmpv1                         { value 0; }
                            enum snmpv2c                        { value 1; }
                            enum snmpv3                         { value 3; }
                        }
                        default "snmpv3";
                        description "SNMP version to format notification messages sent to this SNMP notification collector";
                    }

                    leaf notify-community {
                        type string {
                            length "1..31";
                        }
                        mandatory true;
                        description "SNMPv1 or SNMPv2c community name string, or SNMPv3 security name, for sending a notification";
                    }

                    leaf security-level {
                        type enumeration {
                            enum no-auth-no-privacy             { value 1; }
                            enum auth-no-privacy                { value 2; }
                            enum privacy                        { value 3; }
                        }
                        default "no-auth-no-privacy";
                        description "Security level at which SNMP notification messages are sent to SNMP notification collector";
                    }

                    leaf replay {
                        type boolean;
                        default "false";
                        description "Retransmit missed notifications";
                    }

                    leaf dying-gasp {
                        type boolean;
                        default "false";
                        description "Enable transmission of dying gasp notifications";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                } // list trap-target

            } // list snmp-trap-group

            list syslog {
                key "syslog-name";
                max-elements 10;
                description "Enter the syslog list instance";

                leaf syslog-name {
                    type types-log:log-syslog-name;
                    description "Syslog name";
                }

                leaf description {
                    type types-sros:description;
                    description "Text description";
                }

                leaf address {
                    type types-sros:ip-unicast-address;
                    description "IP address of the Syslog target host";
                }

                leaf facility {
                    type enumeration {
                        enum kernel                         { value 0; }
                        enum user                           { value 1; }
                        enum mail                           { value 2; }
                        enum systemd                        { value 3; }
                        enum auth                           { value 4; }
                        enum syslogd                        { value 5; }
                        enum printer                        { value 6; }
                        enum netnews                        { value 7; }
                        enum uucp                           { value 8; }
                        enum cron                           { value 9; }
                        enum authpriv                       { value 10; }
                        enum ftp                            { value 11; }
                        enum ntp                            { value 12; }
                        enum logaudit                       { value 13; }
                        enum logalert                       { value 14; }
                        enum cron2                          { value 15; }
                        enum local0                         { value 16; }
                        enum local1                         { value 17; }
                        enum local2                         { value 18; }
                        enum local3                         { value 19; }
                        enum local4                         { value 20; }
                        enum local5                         { value 21; }
                        enum local6                         { value 22; }
                        enum local7                         { value 23; }
                    }
                    default "local7";
                    description "Facility code for messages";
                }

                leaf severity {
                    type enumeration {
                        enum emergency                      { value 0; }
                        enum alert                          { value 1; }
                        enum critical                       { value 2; }
                        enum error                          { value 3; }
                        enum warning                        { value 4; }
                        enum notice                         { value 5; }
                        enum info                           { value 6; }
                        enum debug                          { value 7; }
                    }
                    default "info";
                    description "Severity level threshold for the syslog message";
                }

                leaf log-prefix {
                    type union {
                        type enumeration {
                            enum no-prefix                      { value -1; }
                        }
                        type string {
                            length "1..32";
                            pattern "([!-9;<>-~])+" {
                                error-message "String must contain only printable characters between 33 - 126 ASCII except ':' and '='";
                            }
                        }
                    }
                    default "TMNX";
                    description "String that is prepended to every log message sent to this target syslog host";
                }

                leaf tls-client-profile {
                    type leafref {
                        path "../../../system/security/tls/client-tls-profile/client-profile-name";
                    }
                    sros-ext:immutable;
                    description "TLS client profile used to encrypt syslog communication";
                }

                leaf port {
                    when "not(../tls-client-profile)" {
                        description "Log syslog TLS profile can not be defined together with port. TLS is using default port 6514";
                    }
                    type types-qos:tcp-udp-match-port;
                    default "514";
                    description "Destination port when sending syslog over UDP";
                }

                leaf timestamp-format {
                    type enumeration {
                        enum millisecond {
                            value 1;
                            description "Set timestamp format to milliseconds";
                        }
                    }
                    description "Syslog timestamp format";
                }

                leaf-list apply-groups {
                    type leafref {
                        path "../../../groups/group/name";
                    }
                    max-elements 8;
                    ordered-by user;
                    description "Apply a configuration group at this level";
                }

                leaf-list apply-groups-exclude {
                    type leafref {
                        path "../../../groups/group/name";
                    }
                    max-elements 8;
                    ordered-by user;
                    description "Exclude a configuration group at this level";
                }

                container hostname {
                    description "Enter the hostname context";

                    choice hostname {
                        case value {

                            leaf value {
                                type types-sros:named-item-255;
                                description "Syslog HOSTNAME field value";
                            }

                        }
                        case use-system-name {

                            container use-system-name {
                                presence "Enable the use-system-name context";
                                description "Enable the use-system-name context";

                            } // container use-system-name

                        }
                    }
                } // container hostname

            } // list syslog

            container throttle-rate {
                description "Enter the throttle-rate context";

                leaf limit {
                    type uint32 {
                        range "1..20000";
                    }
                    default "2000";
                    description "Number of log events within the throttle interval";
                }

                leaf interval {
                    type uint32 {
                        range "1..1200";
                    }
                    default "1";
                    description "Duration of an event throttling interval";
                }

            } // container throttle-rate

        } // container log

    } // grouping conf-log

}
