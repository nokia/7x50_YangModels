submodule nokia-state-router-msdp {

    yang-version "1.1";

    belongs-to nokia-state { prefix "state"; }

    import ietf-yang-types                { prefix "yang"; }
    import nokia-sros-yang-extensions     { prefix "sros-ext"; }
    import nokia-types-sros               { prefix "types-sros"; }

    sros-ext:sros-major-release "rel25";
    organization "Nokia";
    contact
        "Nokia SR OS Support
         Web: <http://www.nokia.com>";
    description
        "Nokia YANG Data model with operational state for  The Multicast Source Discovery Protocol (MSDP) is used to connect multicast routing domains. on SR OS based routers.

         Copyright 2016 Nokia. All rights reserved. Reproduction of this document
         is authorized on the condition that the foregoing copyright notice is included.

         This nokia-state-router-msdp YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";
    revision "2025-03-12";

    grouping state-router-msdp {
        container msdp {
            description "Enter the msdp context";

            leaf source-active-reject-export-policy {
                type yang:counter32;
                description "The number of SA messages that were not sent due to export policy";
            }

            leaf source-active-reject-import-policy {
                type yang:counter32;
                description "The number of SA messages that rejected due to import policy";
            }

            list group {
                key "name";
                description "Enter the group list instance";

                leaf name {
                    type types-sros:named-item;
                    description "The peer group name";
                }

                leaf source-active-reject-export-policy {
                    type yang:counter32;
                    description "The number of SA messages that were not sent due to export policy";
                }

                leaf source-active-reject-import-policy {
                    type yang:counter32;
                    description "The number of SA messages that rejected due to import policy";
                }

                leaf active-source-limit-exceeded {
                    type yang:counter32;
                    description
                        "The number of source active messages received from this
                         group that exceeded the established maximum number";
                }

                list peer {
                    key "ip-address";
                    description "Enter the peer list instance";

                    leaf ip-address {
                        type types-sros:ipv4-unicast-address;
                        description "The local end of an MSDP session";
                    }

                    leaf peer-state {
                        type enumeration {
                            enum listen                         { value 0; }
                            enum established                    { value 1; }
                            enum inactive                       { value 2; }
                            enum disabled                       { value 3; }
                            enum connecting                     { value 4; }
                        }
                        description "The status of connection";
                    }

                    leaf last-peer-state-change {
                        type types-sros:date-time;
                        description "The time at which the most recent peer-state change occurred";
                    }

                    leaf connection-retry {
                        type yang:counter32;
                        description "The number of peer connection retry attempts";
                    }

                    leaf state-timer {
                        type uint32;
                        units "seconds";
                        description "The number of seconds to wait before another message is sent to a peer";
                    }

                    leaf timeout {
                        type uint32;
                        units "seconds";
                        description
                            "The number of seconds to wait for a response from the peer before declaring
                             the peer unavailable";
                    }

                    leaf active-source-accepted {
                        type yang:counter32;
                        description "The number of source-active cache accepted from the peer";
                    }

                    leaf active-source-received {
                        type yang:counter32;
                        description "The number of source-active cache received by the peer";
                    }

                    leaf last-active-source-limit {
                        type types-sros:date-time;
                        description "The time that the last active source limit was triggered";
                    }

                    leaf operational-local-address {
                        type types-sros:ipv4-unicast-address;
                        description "The operational value of the local address";
                    }

                    container statistics {
                        description "Enter the statistics context";

                        leaf active-source-limit-exceeded {
                            type yang:counter32;
                            description
                                "The number of source active messages received from this
                                 group that exceeded the established maximum number";
                        }

                        leaf last-state-change {
                            type types-sros:time-interval;
                            description "This indicates how long ago the peer state changed";
                        }

                        leaf rpf-failures {
                            type yang:counter32;
                            description "The number of reverse path forwarding (RPF) failures";
                        }

                        leaf remote-closes {
                            type yang:counter32;
                            description "The number of times the remote peer closed";
                        }

                        leaf peer-timeouts {
                            type yang:counter32;
                            description "The number of peer timeouts";
                        }

                        leaf source-active-messages-tx {
                            type yang:counter32;
                            description "The number of source-active messages sent";
                        }

                        leaf source-active-messages-rx {
                            type yang:counter32;
                            description "The number of source-active messages received";
                        }

                        leaf source-active-requests-messages-tx {
                            type yang:counter32;
                            description "The number of source-active request messages sent";
                        }

                        leaf source-active-requests-messages-rx {
                            type yang:counter32;
                            description "The number of source-active request messages received";
                        }

                        leaf source-active-response-messages-tx {
                            type yang:counter32;
                            description "The number of source-active response messages sent";
                        }

                        leaf source-active-response-messages-rx {
                            type yang:counter32;
                            description "The number of source-active response messages received";
                        }

                        leaf keepalive-messages-tx {
                            type yang:counter32;
                            description "The number of keep-alive messages sent";
                        }

                        leaf keepalive-messages-rx {
                            type yang:counter32;
                            description "The number of keep-alive messages received";
                        }

                        leaf unknown-messages-rx {
                            type yang:counter32;
                            description "The number of unknown messages received";
                        }

                        leaf error-messages-rx {
                            type yang:counter32;
                            description "The number of error messages received";
                        }

                        leaf source-active-learnt {
                            type yang:gauge32;
                            description
                                "The number of unique source active entries in the cache
                                 learned from the peer";
                        }

                        leaf source-active-reject-export-policy {
                            type yang:counter32;
                            description
                                "The number of source active messages from the peer that
                                 were not sent due to export policy";
                        }

                        leaf source-active-reject-import-policy {
                            type yang:counter32;
                            description
                                "The number of source active messages from the peer that
                                 were not sent due to import policy";
                        }

                        leaf reserved-messages-rx {
                            type yang:counter32;
                            description "The number of MSDP messages received with type 'Reserved'";
                        }

                    } // container statistics

                } // list peer

            } // list group

            list peer {
                key "ip-address";
                description "Enter the peer list instance";

                leaf ip-address {
                    type types-sros:ipv4-unicast-address;
                    description "The local end of an MSDP session";
                }

                leaf peer-state {
                    type enumeration {
                        enum listen                         { value 0; }
                        enum established                    { value 1; }
                        enum inactive                       { value 2; }
                        enum disabled                       { value 3; }
                        enum connecting                     { value 4; }
                    }
                    description "The status of connection";
                }

                leaf last-peer-state-change {
                    type types-sros:date-time;
                    description "The time at which the most recent peer-state change occurred";
                }

                leaf connection-retry {
                    type yang:counter32;
                    description "The number of peer connection retry attempts";
                }

                leaf state-timer {
                    type uint32;
                    units "seconds";
                    description "The number of seconds to wait before another message is sent to a peer";
                }

                leaf timeout {
                    type uint32;
                    units "seconds";
                    description
                        "The number of seconds to wait for a response from the peer before declaring
                         the peer unavailable";
                }

                leaf active-source-accepted {
                    type yang:counter32;
                    description "The number of source-active cache accepted from the peer";
                }

                leaf active-source-received {
                    type yang:counter32;
                    description "The number of source-active cache received by the peer";
                }

                leaf last-active-source-limit {
                    type types-sros:date-time;
                    description "The time that the last active source limit was triggered";
                }

                leaf operational-local-address {
                    type types-sros:ipv4-unicast-address;
                    description "The operational value of the local address";
                }

                container statistics {
                    description "Enter the statistics context";

                    leaf active-source-limit-exceeded {
                        type yang:counter32;
                        description
                            "The number of source active messages received from this
                             group that exceeded the established maximum number";
                    }

                    leaf last-state-change {
                        type types-sros:time-interval;
                        description "This indicates how long ago the peer state changed";
                    }

                    leaf rpf-failures {
                        type yang:counter32;
                        description "The number of reverse path forwarding (RPF) failures";
                    }

                    leaf remote-closes {
                        type yang:counter32;
                        description "The number of times the remote peer closed";
                    }

                    leaf peer-timeouts {
                        type yang:counter32;
                        description "The number of peer timeouts";
                    }

                    leaf source-active-messages-tx {
                        type yang:counter32;
                        description "The number of source-active messages sent";
                    }

                    leaf source-active-messages-rx {
                        type yang:counter32;
                        description "The number of source-active messages received";
                    }

                    leaf source-active-requests-messages-tx {
                        type yang:counter32;
                        description "The number of source-active request messages sent";
                    }

                    leaf source-active-requests-messages-rx {
                        type yang:counter32;
                        description "The number of source-active request messages received";
                    }

                    leaf source-active-response-messages-tx {
                        type yang:counter32;
                        description "The number of source-active response messages sent";
                    }

                    leaf source-active-response-messages-rx {
                        type yang:counter32;
                        description "The number of source-active response messages received";
                    }

                    leaf keepalive-messages-tx {
                        type yang:counter32;
                        description "The number of keep-alive messages sent";
                    }

                    leaf keepalive-messages-rx {
                        type yang:counter32;
                        description "The number of keep-alive messages received";
                    }

                    leaf unknown-messages-rx {
                        type yang:counter32;
                        description "The number of unknown messages received";
                    }

                    leaf error-messages-rx {
                        type yang:counter32;
                        description "The number of error messages received";
                    }

                    leaf source-active-learnt {
                        type yang:gauge32;
                        description
                            "The number of unique source active entries in the cache
                             learned from the peer";
                    }

                    leaf source-active-reject-export-policy {
                        type yang:counter32;
                        description
                            "The number of source active messages from the peer that
                             were not sent due to export policy";
                    }

                    leaf source-active-reject-import-policy {
                        type yang:counter32;
                        description
                            "The number of source active messages from the peer that
                             were not sent due to import policy";
                    }

                    leaf reserved-messages-rx {
                        type yang:counter32;
                        description "The number of MSDP messages received with type 'Reserved'";
                    }

                } // container statistics

            } // list peer

            list source {
                key "ip-prefix";
                description "Enter the source list instance";

                leaf ip-prefix {
                    type types-sros:ipv4-unicast-prefix;
                    description
                        "The IP address of the sources from which the
                         source active messages would be accepted";
                }

                leaf discovery-method {
                    type enumeration {
                        enum dynamic                        { value 0; }
                        enum configured                     { value 1; }
                    }
                    description "The discovery method for this multicast source";
                }

                leaf active-messages-exceed-max {
                    type yang:counter32;
                    description
                        "The number of source active messages received from
                         the source that exceeded the established maximum number";
                }

                leaf last-exceeded-event-time {
                    type types-sros:date-time;
                    description "The time the last exceed event was triggered";
                }

            } // list source

            container status {
                description "Enter the status context";

                leaf peer-count {
                    type yang:gauge32;
                    description "The number of configured peers";
                }

                leaf peers-established {
                    type yang:gauge32;
                    description "The number of peers in established state";
                }

                leaf source-active-messages-count {
                    type yang:gauge32;
                    description "The number of source active configured in cache";
                }

                leaf last-time-up {
                    type types-sros:date-time;
                    description "The last time the protocol was enabled";
                }

                leaf active-source-limit-exceeded {
                    type yang:counter32;
                    description
                        "The number of time the global active source
                         limit has been exceeded";
                }

            } // container status

            list source-active {
                key "group source origin-rendez-vous-point";
                description "Enter the source-active list instance";

                leaf group {
                    type types-sros:ipv4-multicast-address;
                    description "The group address of the source active";
                }

                leaf source {
                    type types-sros:ipv4-unicast-address;
                    description "The source address of the source active";
                }

                leaf origin-rendez-vous-point {
                    type types-sros:ipv4-address;
                    description "The origin rendez vous point address of the source active";
                }

                leaf peer-learnt-from {
                    type types-sros:ipv4-address;
                    description "The peer from which the source active was last accepted";
                }

                leaf reverse-path-forwarding-peer {
                    type types-sros:ipv4-address;
                    description
                        "The peer from which an source active message corresponding
                         to this cache would be accepted";
                }

                leaf up-time {
                    type types-sros:time-duration;
                    description "The time since this was first placed in the source active cache";
                }

                leaf expiry-time {
                    type types-sros:time-interval;
                    description
                        "The time remaining before this will expire from the
                         source active cache";
                }

            } // list source-active

            list source-active-rejected {
                key "group-name group source origin-rendez-vous-point peer";
                description "Enter the source-active-rejected list instance";

                leaf group-name {
                    type types-sros:named-item-or-empty;
                    description "The peer group name of the source active that is rejected";
                }

                leaf group {
                    type types-sros:ipv4-address;
                    description "The group address of the source active that is rejected";
                }

                leaf source {
                    type types-sros:ipv4-address;
                    description "The source address of the source active that is rejected";
                }

                leaf origin-rendez-vous-point {
                    type types-sros:ipv4-address;
                    description "The origin rendez vous point address of the source active that is rejected";
                }

                leaf peer {
                    type types-sros:ipv4-address;
                    description "The peer from which this rejected source active was last received";
                }

                leaf failure-reason {
                    type enumeration {
                        enum import-policy-failure          { value 1; }
                        enum export-policy-failure          { value 2; }
                        enum reverse-path-forwarding-failure { value 3; }
                        enum active-source-limit-exceeded   { value 4; }
                        enum source-active-source-limit-exceeded { value 5; }
                        enum peer-active-source-limit-exceeded { value 6; }
                        enum group-active-source-limit-exceeded { value 7; }
                        enum group-peer-active-source-limit-exceeded { value 8; }
                    }
                    description "The reason why this source active is rejected";
                }

            } // list source-active-rejected

        } // container msdp

    } // grouping state-router-msdp

}
