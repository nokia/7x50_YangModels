submodule nokia-state-port-access {

    yang-version "1.1";

    belongs-to nokia-state { prefix "state"; }

    import ietf-yang-types                { prefix "yang"; }
    import nokia-sros-yang-extensions     { prefix "sros-ext"; }
    import nokia-types-sros               { prefix "types-sros"; }

    sros-ext:sros-major-release "rel25";
    organization "Nokia";
    contact
        "Nokia SR OS Support
         Web: <http://www.nokia.com>";
    description
        "Nokia YANG Data model with operational state for access port parameters on SR OS based routers.

         Copyright 2016 Nokia. All rights reserved. Reproduction of this document
         is authorized on the condition that the foregoing copyright notice is included.

         This nokia-state-port-access YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";
    revision "2025-03-12";

    grouping state-port-access {
        container access {
            description "Enter the access context";

            container egress {
                description "Enter the egress context";

                list pool {
                    key "name";
                    description "Enter the pool list instance";

                    leaf name {
                        type types-sros:named-item;
                        description "Specifies the unique name of the pool for the access port.";
                    }

                    container pool-depth {
                        description "Enter the pool-depth context";

                        leaf elapsed-time {
                            type types-sros:time-interval;
                            description "Indicated the elapsed time.";
                        }

                        leaf pool-polling-interval {
                            type types-sros:time-interval;
                            description "Indicates the pool polling interval.";
                        }

                        leaf reserved-pool-last-violation {
                            type yang:date-and-time;
                            description "Indicates the last violation time for reserved pool buffers in use.";
                        }

                        leaf reserved-pool-total-threshold-violations {
                            type yang:counter32;
                            description "Indicates the total threshold violations for reserved pool buffers in use.";
                        }

                        leaf shared-pool-last-violation {
                            type yang:date-and-time;
                            description "Indicates the last violation time for shared pool buffers in use.";
                        }

                        leaf shared-pool-total-threshold-violations {
                            type yang:counter32;
                            description "Indicates the total threshold violations for shared pool buffers in use.";
                        }

                        leaf total-pool-last-violation {
                            type yang:date-and-time;
                            description "Indicates the last violation time for total pool buffers in use.";
                        }

                        leaf total-pool-total-threshold-violations {
                            type yang:counter32;
                            description "Indicates the total threshold violations for total pool buffers in use.";
                        }

                        container total-pool {
                            description "Enter the total-pool context";

                            leaf depth-0-to-10-percent {
                                type decimal64 {
                                    fraction-digits 2;
                                }
                                description "Indicated the depth 0 to 10 percent.";
                            }

                            leaf depth-11-to-20-percent {
                                type decimal64 {
                                    fraction-digits 2;
                                }
                                description "Indicated the depth 0 to 20 percent.";
                            }

                            leaf depth-21-to-30-percent {
                                type decimal64 {
                                    fraction-digits 2;
                                }
                                description "Indicated the depth 0 to 30 percent.";
                            }

                            leaf depth-31-to-40-percent {
                                type decimal64 {
                                    fraction-digits 2;
                                }
                                description "Indicated the depth 0 to 40 percent.";
                            }

                            leaf depth-41-to-50-percent {
                                type decimal64 {
                                    fraction-digits 2;
                                }
                                description "Indicated the depth 0 to 50 percent.";
                            }

                            leaf depth-51-to-60-percent {
                                type decimal64 {
                                    fraction-digits 2;
                                }
                                description "Indicated the depth 0 to 60 percent.";
                            }

                            leaf depth-61-to-70-percent {
                                type decimal64 {
                                    fraction-digits 2;
                                }
                                description "Indicated the depth 0 to 70 percent.";
                            }

                            leaf depth-71-to-80-percent {
                                type decimal64 {
                                    fraction-digits 2;
                                }
                                description "Indicated the depth 0 to 80 percent.";
                            }

                            leaf depth-81-to-90-percent {
                                type decimal64 {
                                    fraction-digits 2;
                                }
                                description "Indicated the depth 0 to 90 percent.";
                            }

                            leaf depth-91-to-100-percent {
                                type decimal64 {
                                    fraction-digits 2;
                                }
                                description "Indicated the depth 0 to 100 percent.";
                            }

                        } // container total-pool

                        container shared-pool {
                            description "Enter the shared-pool context";

                            leaf depth-0-to-10-percent {
                                type decimal64 {
                                    fraction-digits 2;
                                }
                                description "Indicated the depth 0 to 10 percent.";
                            }

                            leaf depth-11-to-20-percent {
                                type decimal64 {
                                    fraction-digits 2;
                                }
                                description "Indicated the depth 0 to 20 percent.";
                            }

                            leaf depth-21-to-30-percent {
                                type decimal64 {
                                    fraction-digits 2;
                                }
                                description "Indicated the depth 0 to 30 percent.";
                            }

                            leaf depth-31-to-40-percent {
                                type decimal64 {
                                    fraction-digits 2;
                                }
                                description "Indicated the depth 0 to 40 percent.";
                            }

                            leaf depth-41-to-50-percent {
                                type decimal64 {
                                    fraction-digits 2;
                                }
                                description "Indicated the depth 0 to 50 percent.";
                            }

                            leaf depth-51-to-60-percent {
                                type decimal64 {
                                    fraction-digits 2;
                                }
                                description "Indicated the depth 0 to 60 percent.";
                            }

                            leaf depth-61-to-70-percent {
                                type decimal64 {
                                    fraction-digits 2;
                                }
                                description "Indicated the depth 0 to 70 percent.";
                            }

                            leaf depth-71-to-80-percent {
                                type decimal64 {
                                    fraction-digits 2;
                                }
                                description "Indicated the depth 0 to 80 percent.";
                            }

                            leaf depth-81-to-90-percent {
                                type decimal64 {
                                    fraction-digits 2;
                                }
                                description "Indicated the depth 0 to 90 percent.";
                            }

                            leaf depth-91-to-100-percent {
                                type decimal64 {
                                    fraction-digits 2;
                                }
                                description "Indicated the depth 0 to 100 percent.";
                            }

                        } // container shared-pool

                        container reserved-pool {
                            description "Enter the reserved-pool context";

                            leaf depth-0-to-10-percent {
                                type decimal64 {
                                    fraction-digits 2;
                                }
                                description "Indicated the depth 0 to 10 percent.";
                            }

                            leaf depth-11-to-20-percent {
                                type decimal64 {
                                    fraction-digits 2;
                                }
                                description "Indicated the depth 0 to 20 percent.";
                            }

                            leaf depth-21-to-30-percent {
                                type decimal64 {
                                    fraction-digits 2;
                                }
                                description "Indicated the depth 0 to 30 percent.";
                            }

                            leaf depth-31-to-40-percent {
                                type decimal64 {
                                    fraction-digits 2;
                                }
                                description "Indicated the depth 0 to 40 percent.";
                            }

                            leaf depth-41-to-50-percent {
                                type decimal64 {
                                    fraction-digits 2;
                                }
                                description "Indicated the depth 0 to 50 percent.";
                            }

                            leaf depth-51-to-60-percent {
                                type decimal64 {
                                    fraction-digits 2;
                                }
                                description "Indicated the depth 0 to 60 percent.";
                            }

                            leaf depth-61-to-70-percent {
                                type decimal64 {
                                    fraction-digits 2;
                                }
                                description "Indicated the depth 0 to 70 percent.";
                            }

                            leaf depth-71-to-80-percent {
                                type decimal64 {
                                    fraction-digits 2;
                                }
                                description "Indicated the depth 0 to 80 percent.";
                            }

                            leaf depth-81-to-90-percent {
                                type decimal64 {
                                    fraction-digits 2;
                                }
                                description "Indicated the depth 0 to 90 percent.";
                            }

                            leaf depth-91-to-100-percent {
                                type decimal64 {
                                    fraction-digits 2;
                                }
                                description "Indicated the depth 0 to 100 percent.";
                            }

                        } // container reserved-pool

                        container usage-alarm-thresholds {
                            description "Enter the usage-alarm-thresholds context";

                            leaf total-pool-usage-threshold-exceeded {
                                type boolean;
                                description
                                    "Specifies if total pool buffer usage is in violation state and is
                                     above the configured threshold percentage. When true it is above the
                                     thresholds. When false it is below the thresholds.";
                            }

                            leaf shared-pool-usage-threshold-exceeded {
                                type boolean;
                                description
                                    "Specifies if shared pool buffer usage is in violation state and is
                                     above the configured threshold percentage. When true it is above the
                                     thresholds. When false it is below the thresholds.";
                            }

                            leaf reserved-pool-usage-threshold-exceeded {
                                type boolean;
                                description
                                    "Specifies if reserved pool buffer usage is in violation state and is
                                     above the configured threshold percentage. When true it is above the
                                     thresholds. When false it is below the thresholds.";
                            }

                        } // container usage-alarm-thresholds

                    } // container pool-depth

                    container pool-usage {
                        description "Enter the pool-usage context";

                        leaf total-pool-size {
                            type uint32;
                            units "kilobytes";
                            description "Total buffer pools size.";
                        }

                        leaf total-pool-in-use {
                            type uint32;
                            units "kilobytes";
                            description "Total buffer pools size in use.";
                        }

                        leaf shared-pool-size {
                            type uint32;
                            units "kilobytes";
                            description "Total shared pools size.";
                        }

                        leaf shared-pool-in-use {
                            type uint32;
                            units "kilobytes";
                            description "Total shared pools size in use.";
                        }

                        leaf reserved-pool-size {
                            type uint32;
                            units "kilobytes";
                            description "Total reserved pools size.";
                        }

                        leaf reserved-pool-in-use {
                            type uint32;
                            units "kilobytes";
                            description "Total reserved pools size in use.";
                        }

                        leaf total-queues-added {
                            type uint32;
                            description "Total queues added.";
                        }

                        leaf total-queues-deleted {
                            type uint32;
                            description "Total queues deleted.";
                        }

                        leaf current-queues {
                            type uint32;
                            description "Current queues.";
                        }

                    } // container pool-usage

                    container statistics {
                        description "Enter the statistics context";

                        leaf forward-packets {
                            type yang:counter64;
                            description "The number of packets forwarded.";
                        }

                        leaf forward-octets {
                            type yang:counter64;
                            description "The number of octets forwarded.";
                        }

                        leaf discard-other-packets {
                            type yang:counter64;
                            description "The number of packets dropped due to queue tail drop or lack of buffer from pool.";
                        }

                        leaf discard-other-octets {
                            type yang:counter64;
                            description "The number of octets dropped due to queue tail drop or lack of buffer from pool.";
                        }

                        leaf discard-pool-exceed-slope-packets {
                            type yang:counter64;
                            description "The number of dropped pool exceed slope packets.";
                        }

                        leaf discard-pool-exceed-slope-octets {
                            type yang:counter64;
                            description "The number of dropped pool exceed slope octets.";
                        }

                        leaf discard-pool-low-slope-packets {
                            type yang:counter64;
                            description "The number of dropped pool low slope packets.";
                        }

                        leaf discard-pool-low-slope-octets {
                            type yang:counter64;
                            description "The number of dropped pool low slope octets.";
                        }

                        leaf discard-pool-high-slope-packets {
                            type yang:counter64;
                            description "The number of dropped pool high slope packets.";
                        }

                        leaf discard-pool-high-slope-octets {
                            type yang:counter64;
                            description "The number of dropped pool high slope octets.";
                        }

                        leaf discard-pool-highplus-slope-packets {
                            type yang:counter64;
                            description "The number of dropped pool highplus slope packets.";
                        }

                        leaf discard-pool-highplus-slope-octets {
                            type yang:counter64;
                            description "The number of dropped pool highplus slope octets.";
                        }

                        leaf discard-pool-shared-packets {
                            type yang:counter64;
                            description "The number of dropped pool fairness packets.";
                        }

                        leaf discard-pool-shared-octets {
                            type yang:counter64;
                            description "The number of dropped pool fairness octets.";
                        }

                        leaf discard-pool-total-packets {
                            type yang:counter64;
                            description "The number of dropped pool exhaust packets.";
                        }

                        leaf discard-pool-total-octets {
                            type yang:counter64;
                            description "The number of dropped pool exhaust octets.";
                        }

                        leaf discard-queue-tail-drop-packets {
                            type yang:counter64;
                            description "The number of dropped queue tail packets.";
                        }

                        leaf discard-queue-tail-drop-octets {
                            type yang:counter64;
                            description "The number of dropped queue tail octets.";
                        }

                        leaf total-packets {
                            type yang:counter64;
                            description "The number of total packets.";
                        }

                        leaf total-octets {
                            type yang:counter64;
                            description "The number of total octets.";
                        }

                    } // container statistics

                } // list pool

            } // container egress

            container ingress {
                description "Enter the ingress context";

                list pool {
                    key "name";
                    description "Enter the pool list instance";

                    leaf name {
                        type types-sros:named-item;
                        description "Specifies the unique name of the pool for the access port.";
                    }

                    container pool-depth {
                        description "Enter the pool-depth context";

                        leaf elapsed-time {
                            type types-sros:time-interval;
                            description "Indicated the elapsed time.";
                        }

                        leaf pool-polling-interval {
                            type types-sros:time-interval;
                            description "Indicates the pool polling interval.";
                        }

                        leaf reserved-pool-last-violation {
                            type yang:date-and-time;
                            description "Indicates the last violation time for reserved pool buffers in use.";
                        }

                        leaf reserved-pool-total-threshold-violations {
                            type yang:counter32;
                            description "Indicates the total threshold violations for reserved pool buffers in use.";
                        }

                        leaf shared-pool-last-violation {
                            type yang:date-and-time;
                            description "Indicates the last violation time for shared pool buffers in use.";
                        }

                        leaf shared-pool-total-threshold-violations {
                            type yang:counter32;
                            description "Indicates the total threshold violations for shared pool buffers in use.";
                        }

                        leaf total-pool-last-violation {
                            type yang:date-and-time;
                            description "Indicates the last violation time for total pool buffers in use.";
                        }

                        leaf total-pool-total-threshold-violations {
                            type yang:counter32;
                            description "Indicates the total threshold violations for total pool buffers in use.";
                        }

                        container total-pool {
                            description "Enter the total-pool context";

                            leaf depth-0-to-10-percent {
                                type decimal64 {
                                    fraction-digits 2;
                                }
                                description "Indicated the depth 0 to 10 percent.";
                            }

                            leaf depth-11-to-20-percent {
                                type decimal64 {
                                    fraction-digits 2;
                                }
                                description "Indicated the depth 0 to 20 percent.";
                            }

                            leaf depth-21-to-30-percent {
                                type decimal64 {
                                    fraction-digits 2;
                                }
                                description "Indicated the depth 0 to 30 percent.";
                            }

                            leaf depth-31-to-40-percent {
                                type decimal64 {
                                    fraction-digits 2;
                                }
                                description "Indicated the depth 0 to 40 percent.";
                            }

                            leaf depth-41-to-50-percent {
                                type decimal64 {
                                    fraction-digits 2;
                                }
                                description "Indicated the depth 0 to 50 percent.";
                            }

                            leaf depth-51-to-60-percent {
                                type decimal64 {
                                    fraction-digits 2;
                                }
                                description "Indicated the depth 0 to 60 percent.";
                            }

                            leaf depth-61-to-70-percent {
                                type decimal64 {
                                    fraction-digits 2;
                                }
                                description "Indicated the depth 0 to 70 percent.";
                            }

                            leaf depth-71-to-80-percent {
                                type decimal64 {
                                    fraction-digits 2;
                                }
                                description "Indicated the depth 0 to 80 percent.";
                            }

                            leaf depth-81-to-90-percent {
                                type decimal64 {
                                    fraction-digits 2;
                                }
                                description "Indicated the depth 0 to 90 percent.";
                            }

                            leaf depth-91-to-100-percent {
                                type decimal64 {
                                    fraction-digits 2;
                                }
                                description "Indicated the depth 0 to 100 percent.";
                            }

                        } // container total-pool

                        container shared-pool {
                            description "Enter the shared-pool context";

                            leaf depth-0-to-10-percent {
                                type decimal64 {
                                    fraction-digits 2;
                                }
                                description "Indicated the depth 0 to 10 percent.";
                            }

                            leaf depth-11-to-20-percent {
                                type decimal64 {
                                    fraction-digits 2;
                                }
                                description "Indicated the depth 0 to 20 percent.";
                            }

                            leaf depth-21-to-30-percent {
                                type decimal64 {
                                    fraction-digits 2;
                                }
                                description "Indicated the depth 0 to 30 percent.";
                            }

                            leaf depth-31-to-40-percent {
                                type decimal64 {
                                    fraction-digits 2;
                                }
                                description "Indicated the depth 0 to 40 percent.";
                            }

                            leaf depth-41-to-50-percent {
                                type decimal64 {
                                    fraction-digits 2;
                                }
                                description "Indicated the depth 0 to 50 percent.";
                            }

                            leaf depth-51-to-60-percent {
                                type decimal64 {
                                    fraction-digits 2;
                                }
                                description "Indicated the depth 0 to 60 percent.";
                            }

                            leaf depth-61-to-70-percent {
                                type decimal64 {
                                    fraction-digits 2;
                                }
                                description "Indicated the depth 0 to 70 percent.";
                            }

                            leaf depth-71-to-80-percent {
                                type decimal64 {
                                    fraction-digits 2;
                                }
                                description "Indicated the depth 0 to 80 percent.";
                            }

                            leaf depth-81-to-90-percent {
                                type decimal64 {
                                    fraction-digits 2;
                                }
                                description "Indicated the depth 0 to 90 percent.";
                            }

                            leaf depth-91-to-100-percent {
                                type decimal64 {
                                    fraction-digits 2;
                                }
                                description "Indicated the depth 0 to 100 percent.";
                            }

                        } // container shared-pool

                        container reserved-pool {
                            description "Enter the reserved-pool context";

                            leaf depth-0-to-10-percent {
                                type decimal64 {
                                    fraction-digits 2;
                                }
                                description "Indicated the depth 0 to 10 percent.";
                            }

                            leaf depth-11-to-20-percent {
                                type decimal64 {
                                    fraction-digits 2;
                                }
                                description "Indicated the depth 0 to 20 percent.";
                            }

                            leaf depth-21-to-30-percent {
                                type decimal64 {
                                    fraction-digits 2;
                                }
                                description "Indicated the depth 0 to 30 percent.";
                            }

                            leaf depth-31-to-40-percent {
                                type decimal64 {
                                    fraction-digits 2;
                                }
                                description "Indicated the depth 0 to 40 percent.";
                            }

                            leaf depth-41-to-50-percent {
                                type decimal64 {
                                    fraction-digits 2;
                                }
                                description "Indicated the depth 0 to 50 percent.";
                            }

                            leaf depth-51-to-60-percent {
                                type decimal64 {
                                    fraction-digits 2;
                                }
                                description "Indicated the depth 0 to 60 percent.";
                            }

                            leaf depth-61-to-70-percent {
                                type decimal64 {
                                    fraction-digits 2;
                                }
                                description "Indicated the depth 0 to 70 percent.";
                            }

                            leaf depth-71-to-80-percent {
                                type decimal64 {
                                    fraction-digits 2;
                                }
                                description "Indicated the depth 0 to 80 percent.";
                            }

                            leaf depth-81-to-90-percent {
                                type decimal64 {
                                    fraction-digits 2;
                                }
                                description "Indicated the depth 0 to 90 percent.";
                            }

                            leaf depth-91-to-100-percent {
                                type decimal64 {
                                    fraction-digits 2;
                                }
                                description "Indicated the depth 0 to 100 percent.";
                            }

                        } // container reserved-pool

                        container usage-alarm-thresholds {
                            description "Enter the usage-alarm-thresholds context";

                            leaf total-pool-usage-threshold-exceeded {
                                type boolean;
                                description
                                    "Specifies if total pool buffer usage is in violation state and is
                                     above the configured threshold percentage. When true it is above the
                                     thresholds. When false it is below the thresholds.";
                            }

                            leaf shared-pool-usage-threshold-exceeded {
                                type boolean;
                                description
                                    "Specifies if shared pool buffer usage is in violation state and is
                                     above the configured threshold percentage. When true it is above the
                                     thresholds. When false it is below the thresholds.";
                            }

                            leaf reserved-pool-usage-threshold-exceeded {
                                type boolean;
                                description
                                    "Specifies if reserved pool buffer usage is in violation state and is
                                     above the configured threshold percentage. When true it is above the
                                     thresholds. When false it is below the thresholds.";
                            }

                        } // container usage-alarm-thresholds

                    } // container pool-depth

                    container pool-usage {
                        description "Enter the pool-usage context";

                        leaf total-pool-size {
                            type uint32;
                            units "kilobytes";
                            description "Total buffer pools size.";
                        }

                        leaf total-pool-in-use {
                            type uint32;
                            units "kilobytes";
                            description "Total buffer pools size in use.";
                        }

                        leaf shared-pool-size {
                            type uint32;
                            units "kilobytes";
                            description "Total shared pools size.";
                        }

                        leaf shared-pool-in-use {
                            type uint32;
                            units "kilobytes";
                            description "Total shared pools size in use.";
                        }

                        leaf reserved-pool-size {
                            type uint32;
                            units "kilobytes";
                            description "Total reserved pools size.";
                        }

                        leaf reserved-pool-in-use {
                            type uint32;
                            units "kilobytes";
                            description "Total reserved pools size in use.";
                        }

                        leaf total-queues-added {
                            type uint32;
                            description "Total queues added.";
                        }

                        leaf total-queues-deleted {
                            type uint32;
                            description "Total queues deleted.";
                        }

                        leaf current-queues {
                            type uint32;
                            description "Current queues.";
                        }

                    } // container pool-usage

                    container statistics {
                        description "Enter the statistics context";

                        leaf forward-packets {
                            type yang:counter64;
                            description "The number of packets forwarded.";
                        }

                        leaf forward-octets {
                            type yang:counter64;
                            description "The number of octets forwarded.";
                        }

                        leaf discard-other-packets {
                            type yang:counter64;
                            description "The number of packets dropped due to queue tail drop or lack of buffer from pool.";
                        }

                        leaf discard-other-octets {
                            type yang:counter64;
                            description "The number of octets dropped due to queue tail drop or lack of buffer from pool.";
                        }

                        leaf discard-pool-exceed-slope-packets {
                            type yang:counter64;
                            description "The number of dropped pool exceed slope packets.";
                        }

                        leaf discard-pool-exceed-slope-octets {
                            type yang:counter64;
                            description "The number of dropped pool exceed slope octets.";
                        }

                        leaf discard-pool-low-slope-packets {
                            type yang:counter64;
                            description "The number of dropped pool low slope packets.";
                        }

                        leaf discard-pool-low-slope-octets {
                            type yang:counter64;
                            description "The number of dropped pool low slope octets.";
                        }

                        leaf discard-pool-high-slope-packets {
                            type yang:counter64;
                            description "The number of dropped pool high slope packets.";
                        }

                        leaf discard-pool-high-slope-octets {
                            type yang:counter64;
                            description "The number of dropped pool high slope octets.";
                        }

                        leaf discard-pool-highplus-slope-packets {
                            type yang:counter64;
                            description "The number of dropped pool highplus slope packets.";
                        }

                        leaf discard-pool-highplus-slope-octets {
                            type yang:counter64;
                            description "The number of dropped pool highplus slope octets.";
                        }

                        leaf discard-pool-shared-packets {
                            type yang:counter64;
                            description "The number of dropped pool fairness packets.";
                        }

                        leaf discard-pool-shared-octets {
                            type yang:counter64;
                            description "The number of dropped pool fairness octets.";
                        }

                        leaf discard-pool-total-packets {
                            type yang:counter64;
                            description "The number of dropped pool exhaust packets.";
                        }

                        leaf discard-pool-total-octets {
                            type yang:counter64;
                            description "The number of dropped pool exhaust octets.";
                        }

                        leaf discard-queue-tail-drop-packets {
                            type yang:counter64;
                            description "The number of dropped queue tail packets.";
                        }

                        leaf discard-queue-tail-drop-octets {
                            type yang:counter64;
                            description "The number of dropped queue tail octets.";
                        }

                        leaf total-packets {
                            type yang:counter64;
                            description "The number of total packets.";
                        }

                        leaf total-octets {
                            type yang:counter64;
                            description "The number of total octets.";
                        }

                    } // container statistics

                } // list pool

            } // container ingress

        } // container access

    } // grouping state-port-access

}
