submodule nokia-conf-ipsec {

    yang-version "1.1";

    belongs-to nokia-conf { prefix "conf"; }

    import nokia-sros-yang-extensions     { prefix "sros-ext"; }
    import nokia-types-ipsec              { prefix "types-ipsec"; }
    import nokia-types-security           { prefix "types-security"; }
    import nokia-types-services           { prefix "types-services"; }
    import nokia-types-sros               { prefix "types-sros"; }

    include nokia-conf-aaa;
    include nokia-conf-groups;
    include nokia-conf-system;
    include nokia-conf-system-security;
    include nokia-conf-system-security-pki;

    sros-ext:sros-major-release "rel25";
    organization "Nokia";
    contact
        "Nokia SR OS Support
         Web: <http://www.nokia.com>";
    description
        "Nokia YANG Data model to configure IPsec configuration on SR OS based routers.

         Copyright 2016 Nokia. All rights reserved. Reproduction of this document
         is authorized on the condition that the foregoing copyright notice is included.

         This nokia-conf-ipsec YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";
    revision "2025-04-23";

    grouping conf-ipsec {
        container ipsec {
            description "Enter the ipsec context";

            leaf show-ipsec-keys {
                type boolean;
                default "false";
                description "Show IPsec IKE and ESP keys in the output";
            }

            leaf-list apply-groups {
                type leafref {
                    path "../../groups/group/name";
                }
                max-elements 8;
                ordered-by user;
                description "Apply a configuration group at this level";
            }

            leaf-list apply-groups-exclude {
                type leafref {
                    path "../../groups/group/name";
                }
                max-elements 8;
                ordered-by user;
                description "Exclude a configuration group at this level";
            }

            list cert-profile {
                key "name";
                max-elements 10200;
                description "Enter the cert-profile list instance";

                leaf name {
                    type types-sros:named-item;
                    description "Certificate profile name";
                }

                leaf admin-state {
                    type types-sros:admin-state;
                    default "disable";
                    description "Administrative state of the certificate profile";
                }

                leaf-list apply-groups {
                    type leafref {
                        path "../../../groups/group/name";
                    }
                    max-elements 8;
                    ordered-by user;
                    description "Apply a configuration group at this level";
                }

                leaf-list apply-groups-exclude {
                    type leafref {
                        path "../../../groups/group/name";
                    }
                    max-elements 8;
                    ordered-by user;
                    description "Exclude a configuration group at this level";
                }

                list entry {
                    key "id";
                    max-elements 8;
                    description "Enter the entry list instance";

                    leaf id {
                        type uint32 {
                            range "1..8";
                        }
                        description "Certificate profile entry ID";
                    }

                    leaf cert {
                        type types-security:pki-file-name;
                        description "File name of the imported certificate for the entry";
                    }

                    leaf key {
                        type types-security:pki-file-name;
                        description "File name of the imported key used for authentication";
                    }

                    leaf rsa-signature {
                        type enumeration {
                            enum pkcs1                          { value 1; }
                            enum pss                            { value 2; }
                        }
                        default "pkcs1";
                        description "Signature scheme for the RSA key";
                    }

                    leaf compare-chain-include {
                        type leafref {
                            path "../../../../system/security/pki/ca-profile/ca-profile-name";
                        }
                        description "CA profile to include in the compare-chain";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                    container send-chain {
                        description "Enter the send-chain context";

                        leaf-list ca-profile {
                            type leafref {
                                path "../../../../../system/security/pki/ca-profile/ca-profile-name";
                            }
                            max-elements 7;
                            description "CA certificate to send to the peer";
                        }

                    } // container send-chain

                } // list entry

            } // list cert-profile

            list client-db {
                key "name";
                max-elements 1000;
                description "Enter the client-db list instance";

                leaf name {
                    type types-sros:named-item;
                    description "IPsec client database name";
                }

                leaf admin-state {
                    type types-sros:admin-state;
                    default "disable";
                    description "Administrative state of the client database";
                }

                leaf description {
                    type types-sros:description;
                    description "Text description";
                }

                leaf-list apply-groups {
                    type leafref {
                        path "../../../groups/group/name";
                    }
                    max-elements 8;
                    ordered-by user;
                    sros-ext:auto-restart-to-modify;
                    description "Apply a configuration group at this level";
                }

                leaf-list apply-groups-exclude {
                    type leafref {
                        path "../../../groups/group/name";
                    }
                    max-elements 8;
                    ordered-by user;
                    sros-ext:auto-restart-to-modify;
                    description "Exclude a configuration group at this level";
                }

                container match-list {
                    sros-ext:auto-restart-to-modify;
                    description "Enter the match-list context";

                    leaf idi {
                        type boolean;
                        sros-ext:auto-restart-to-modify;
                        default "false";
                        description "Use IDi type in the IPsec client matching process";
                    }

                    leaf peer-ip-prefix {
                        type boolean;
                        sros-ext:auto-restart-to-modify;
                        default "false";
                        description "Use the peer tunnel IP address in the matching process";
                    }

                } // container match-list

                list client {
                    key "id";
                    description "Enter the client list instance";

                    leaf id {
                        type uint32 {
                            range "1..8000";
                        }
                        description "Client ID";
                    }

                    leaf admin-state {
                        type types-sros:admin-state;
                        default "disable";
                        description "Administrative state of the database client";
                    }

                    leaf client-name {
                        type types-sros:named-item;
                        sros-ext:auto-restart-to-modify;
                        description "Client name";
                    }

                    leaf private-interface {
                        type types-sros:named-item;
                        sros-ext:auto-restart-to-modify;
                        description "Private interface name used for tunnel setup";
                    }

                    leaf private-service-name {
                        type types-services:service-name;
                        sros-ext:auto-restart-to-modify;
                        description "Name of the private service used for tunnel setup";
                    }

                    leaf ts-list {
                        type types-sros:named-item;
                        sros-ext:auto-restart-to-modify;
                        description "Traffic selector list used by the tunnel";
                    }

                    leaf tunnel-template {
                        type uint32 {
                            range "1..2048";
                        }
                        sros-ext:auto-restart-to-modify;
                        description "Tunnel template ID";
                    }

                    leaf-list apply-groups {
                        type leafref {
                            path "../../../../groups/group/name";
                        }
                        max-elements 8;
                        ordered-by user;
                        sros-ext:auto-restart-to-modify;
                        description "Apply a configuration group at this level";
                    }

                    leaf-list apply-groups-exclude {
                        type leafref {
                            path "../../../../groups/group/name";
                        }
                        max-elements 8;
                        ordered-by user;
                        sros-ext:auto-restart-to-modify;
                        description "Exclude a configuration group at this level";
                    }

                    container credential {
                        sros-ext:auto-restart-to-modify;
                        description "Enter the credential context";

                        leaf pre-shared-key {
                            type types-sros:encrypted-leaf-hex-without-prefix {
                                length "1..115";
                            }
                            sros-ext:auto-restart-to-modify;
                            description "Pre-shared key used to authenticate peers";
                        }

                    } // container credential

                    container identification {
                        sros-ext:auto-restart-to-modify;
                        description "Enter the identification context";

                        container idi {
                            presence "Enable the idi context";
                            sros-ext:auto-restart-to-modify;
                            description "Enable the idi context";

                            choice idi {
                                mandatory true;
                                case any {

                                    leaf any {
                                        type boolean;
                                        sros-ext:auto-restart-to-modify;
                                        description "Accept any IDi value as a match";
                                    }

                                }
                                case ipv4-prefix {

                                    leaf ipv4-prefix {
                                        type types-sros:ipv4-prefix;
                                        sros-ext:auto-restart-to-modify;
                                        description "IPv4 prefix used as the match criteria for the IDi";
                                    }

                                }
                                case ipv4-prefix-any {

                                    leaf ipv4-prefix-any {
                                        type boolean;
                                        sros-ext:auto-restart-to-modify;
                                        description "Accept any valid IPv4 prefix as a match for the IDi";
                                    }

                                }
                                case ipv6-prefix {

                                    leaf ipv6-prefix {
                                        type types-sros:ipv6-prefix;
                                        sros-ext:auto-restart-to-modify;
                                        description "IPv6 prefix used as the match criteria for the IDi";
                                    }

                                }
                                case ipv6-prefix-any {

                                    leaf ipv6-prefix-any {
                                        type boolean;
                                        sros-ext:auto-restart-to-modify;
                                        description "Accept any valid IPv6 prefix as a match for the IDi";
                                    }

                                }
                                case fqdn {

                                    leaf fqdn {
                                        type types-sros:display-string-or-empty;
                                        sros-ext:auto-restart-to-modify;
                                        description "FQDN used as the match criteria for the IDi";
                                    }

                                }
                                case fqdn-suffix {

                                    leaf fqdn-suffix {
                                        type types-sros:display-string-or-empty;
                                        sros-ext:auto-restart-to-modify;
                                        description "FQDN suffix used as the match criteria for the IDi";
                                    }

                                }
                                case rfc822 {

                                    leaf rfc822 {
                                        type types-sros:display-string-or-empty;
                                        sros-ext:auto-restart-to-modify;
                                        description "Email address (RFC 822) used as match criteria for IDi";
                                    }

                                }
                                case rfc822-suffix {

                                    leaf rfc822-suffix {
                                        type types-sros:display-string-or-empty;
                                        sros-ext:auto-restart-to-modify;
                                        description "Email address domain (RFC 822) as IDi match criteria";
                                    }

                                }
                            }
                        } // container idi

                        container peer-ip-prefix {
                            presence "Enable the peer-ip-prefix context";
                            sros-ext:auto-restart-to-modify;
                            description "Enable the peer-ip-prefix context";

                            choice prefix {
                                mandatory true;
                                case ipv4-only {

                                    leaf ipv4-only {
                                        type boolean;
                                        sros-ext:auto-restart-to-modify;
                                        description "Accept any valid IPv4 address as a match";
                                    }

                                }
                                case ipv6-only {

                                    leaf ipv6-only {
                                        type boolean;
                                        sros-ext:auto-restart-to-modify;
                                        description "Accept any valid IPv6 address as a match";
                                    }

                                }
                                case ip-prefix {

                                    leaf ip-prefix {
                                        type types-sros:ip-prefix;
                                        sros-ext:auto-restart-to-modify;
                                        description "IP prefix used as the match criteria";
                                    }

                                }
                            }
                        } // container peer-ip-prefix

                    } // container identification

                } // list client

            } // list client-db

            list ike-policy {
                key "id";
                max-elements 2048;
                description "Enter the ike-policy list instance";

                leaf id {
                    type types-ipsec:ike-policy-id;
                    description "IKE policy ID";
                }

                leaf description {
                    type types-sros:description;
                    description "Text description";
                }

                leaf ipsec-lifetime {
                    type types-ipsec:lifetime;
                    default "3600";
                    description "Lifetime of the Phase 2 IKE key";
                }

                leaf match-peer-id-to-cert {
                    type boolean;
                    default "false";
                    description "Check IKE peer ID during certificate authentication";
                }

                leaf-list ike-transform {
                    type leafref {
                        path "../../ike-transform/id";
                    }
                    max-elements 4;
                    description "IKE transform instance associated with the IKE policy";
                }

                leaf-list apply-groups {
                    type leafref {
                        path "../../../groups/group/name";
                    }
                    max-elements 8;
                    ordered-by user;
                    description "Apply a configuration group at this level";
                }

                leaf-list apply-groups-exclude {
                    type leafref {
                        path "../../../groups/group/name";
                    }
                    max-elements 8;
                    ordered-by user;
                    description "Exclude a configuration group at this level";
                }

                choice ike-version {
                    default "version-1";
                    case version-1 {

                        container ike-version-1 {
                            description "Enter the ike-version-1 context";

                            leaf auth-method {
                                type enumeration {
                                    enum psk                            { value 1; }
                                    enum plain-psk-xauth                { value 4; }
                                }
                                default "psk";
                                description "Authentication method used with the IKE policy";
                            }

                            leaf own-auth-method {
                                type enumeration {
                                    enum symmetric                      { value 0; }
                                }
                                default "symmetric";
                                description "Authentication method used with policy on its own side";
                            }

                            leaf ike-mode {
                                type enumeration {
                                    enum main                           { value 1; }
                                    enum aggressive                     { value 2; }
                                }
                                default "main";
                                description "Mode of operation";
                            }

                            leaf ph1-responder-delete-notify {
                                type boolean;
                                default "true";
                                description "Send delete notification for IKEv1 phase 1 removal";
                            }

                        } // container ike-version-1

                    }
                    case version-2 {

                        container ike-version-2 {
                            presence "Enable the ike-version-2 context";
                            description "Enable the ike-version-2 context";

                            leaf auth-method {
                                type enumeration {
                                    enum psk                            { value 1; }
                                    enum cert                           { value 5; }
                                    enum psk-radius                     { value 6; }
                                    enum cert-radius                    { value 7; }
                                    enum eap                            { value 8; }
                                    enum auto-eap-radius                { value 9; }
                                    enum auto-eap                       { value 10; }
                                }
                                default "psk";
                                description "Authentication method used with the IKE policy";
                            }

                            leaf own-auth-method {
                                type enumeration {
                                    enum symmetric                      { value 0; }
                                    enum psk                            { value 1; }
                                    enum cert                           { value 5; }
                                    enum eap-only                       { value 8; }
                                }
                                default "symmetric";
                                description "Authentication method used with IKE policy on own side";
                            }

                            leaf auto-eap-method {
                                type enumeration {
                                    enum psk                            { value 1; }
                                    enum cert                           { value 2; }
                                    enum psk-or-cert                    { value 3; }
                                }
                                default "cert";
                                description "Authentication method used for the remote peer";
                            }

                            leaf own-auto-eap-method {
                                type enumeration {
                                    enum psk                            { value 1; }
                                    enum cert                           { value 2; }
                                }
                                default "cert";
                                description "Authentication method used on its own side";
                            }

                            leaf send-idr-after-eap-success {
                                type boolean;
                                default "true";
                                description "Send IDr payload in last IKE authentication response";
                            }

                            leaf ppk-required {
                                type boolean;
                                default "false";
                                description "Force the use of PPK";
                            }

                            container ikev2-fragment {
                                presence "Enable the ikev2-fragment context";
                                description "Enable the ikev2-fragment context";

                                leaf mtu {
                                    type uint32 {
                                        range "512..9000";
                                    }
                                    units "octets";
                                    default "1500";
                                    description "Maximum size of the IKEv2 packet";
                                }

                                leaf reassembly-timeout {
                                    type uint32 {
                                        range "1..5";
                                    }
                                    units "seconds";
                                    default "2";
                                    description "Timeout for reassembly of IKEv2 message fragments";
                                }

                            } // container ikev2-fragment

                        } // container ike-version-2

                    }
                }
                container limit-init-exchange {
                    when "../ike-version-2" {
                        description "Feature not supported in IKEv1";
                    }
                    description "Enter the limit-init-exchange context";

                    leaf admin-state {
                        type types-sros:admin-state;
                        default "enable";
                        description "Administrative state of limiting initial IKE exchanges";
                    }

                    leaf reduced-max-exchange-timeout {
                        type union {
                            type uint32 {
                                range "2..60";
                            }
                            type enumeration {
                                enum none                           { value 0; }
                            }
                        }
                        units "seconds";
                        default "2";
                        description "Maximum timeout for in-progress initial IKE exchange";
                    }

                } // container limit-init-exchange

                container dpd {
                    presence "Enable the dpd context";
                    description "Enable the dpd context";

                    leaf reply-only {
                        type boolean;
                        default "false";
                        description "Initiate DPD request for incoming ESP or IKE packets";
                    }

                    leaf interval {
                        type uint32 {
                            range "10..300";
                        }
                        units "seconds";
                        default "30";
                        description "DPD interval";
                    }

                    leaf max-retries {
                        type uint32 {
                            range "2..5";
                        }
                        default "3";
                        description "Maximum number of retries before the tunnel is removed";
                    }

                } // container dpd

                container nat-traversal {
                    presence "Enable the nat-traversal context";
                    description "Enable the nat-traversal context";

                    leaf force {
                        type boolean;
                        default "false";
                        description "Enable NAT-T in forced mode";
                    }

                    leaf keep-alive-interval {
                        type uint32 {
                            range "120..600";
                        }
                        units "seconds";
                        description "Keepalive interval for NAT-T";
                    }

                    leaf force-keep-alive {
                        type boolean;
                        default "true";
                        description "Continue sending keepalive packets (no expiry)";
                    }

                } // container nat-traversal

                container lockout {
                    presence "Enable the lockout context";
                    description "Enable the lockout context";

                    leaf failed-attempts {
                        type uint32 {
                            range "1..64";
                        }
                        default "3";
                        description "Maximum failed authentications allowed in the duration";
                    }

                    leaf duration {
                        type uint32 {
                            range "1..60";
                        }
                        units "minutes";
                        default "5";
                        description "Time interval for failed attempts threshold";
                    }

                    leaf block {
                        type union {
                            type uint32 {
                                range "1..1440";
                            }
                            type enumeration {
                                enum infinite                       { value 0; }
                            }
                        }
                        units "minutes";
                        default "10";
                        description "Time a client is blocked for failed authentications";
                    }

                    leaf max-port-per-ip {
                        type uint32 {
                            range "1..32000";
                        }
                        default "16";
                        description "Maximum number of ports allowed under same IP address";
                    }

                } // container lockout

                container pfs {
                    presence "Enable the pfs context";
                    description "Enable the pfs context";

                    leaf dh-group {
                        type types-ipsec:dh-group;
                        default "group-2";
                        description "Diffie-Helman group used to calculate session keys";
                    }

                } // container pfs

                container relay-unsolicited-cfg-attribute {
                    description "Enter the relay-unsolicited-cfg-attribute context";

                    leaf internal-ip4-address {
                        type boolean;
                        default "false";
                        description "Return the IPv4 address from the source to the client";
                    }

                    leaf internal-ip4-netmask {
                        type boolean;
                        default "false";
                        description "Return the IPv4 netmask from the source to the client";
                    }

                    leaf internal-ip4-dns {
                        type boolean;
                        default "false";
                        description "Return IPv4 DNS server address from source to client";
                    }

                    leaf internal-ip6-address {
                        type boolean;
                        default "false";
                        description "Return the IPv6 address from the source to the client";
                    }

                    leaf internal-ip6-dns {
                        type boolean;
                        default "false";
                        description "Return IPv6 DNS server address from source to client";
                    }

                } // container relay-unsolicited-cfg-attribute

            } // list ike-policy

            list ike-transform {
                key "id";
                max-elements 4096;
                description "Enter the ike-transform list instance";

                leaf id {
                    type types-ipsec:ike-transform-id;
                    description "IKE transform instance ID";
                }

                leaf dh-group {
                    type types-ipsec:dh-group;
                    default "group-2";
                    description "Diffie-Helman group used to calculate session keys";
                }

                leaf ike-auth-algorithm {
                    type types-ipsec:ike-auth-algorithms;
                    default "sha-1";
                    description "IKE authentication algorithm for IKE transform instance";
                }

                leaf ike-encryption-algorithm {
                    type types-ipsec:ike-encryption-algorithms;
                    default "aes-128";
                    description "IKE encryption algorith for the IKE transform instance";
                }

                leaf ike-prf-algorithm {
                    type types-ipsec:prf-algorithms;
                    default "same-as-auth";
                    description "PRF algorithm for the IKE transform instance";
                }

                leaf isakmp-lifetime {
                    type types-ipsec:lifetime;
                    default "86400";
                    description "Phase 1 lifetime for the IKE transform instance";
                }

                leaf-list apply-groups {
                    type leafref {
                        path "../../../groups/group/name";
                    }
                    max-elements 8;
                    ordered-by user;
                    description "Apply a configuration group at this level";
                }

                leaf-list apply-groups-exclude {
                    type leafref {
                        path "../../../groups/group/name";
                    }
                    max-elements 8;
                    ordered-by user;
                    description "Exclude a configuration group at this level";
                }

            } // list ike-transform

            list ipsec-transform {
                key "id";
                max-elements 2048;
                description "Enter the ipsec-transform list instance";

                leaf id {
                    type uint32 {
                        range "1..2048";
                    }
                    description "IPsec transform policy ID";
                }

                leaf esp-auth-algorithm {
                    type types-ipsec:auth-algorithms;
                    default "sha-1";
                    description "Encapsulating Security Payload (ESP) authentication";
                }

                leaf esp-encryption-algorithm {
                    type types-ipsec:encryption-algorithms;
                    default "aes-128";
                    description "Encryption algorithm for the IPsec transform session";
                }

                leaf ipsec-lifetime {
                    type types-ipsec:lifetime;
                    description "Phase 2 lifetime for the IPsec transform session";
                }

                leaf pfs-dh-group {
                    type enumeration {
                        enum none                           { value 0; }
                        enum group-1                        { value 1; }
                        enum group-2                        { value 2; }
                        enum group-5                        { value 5; }
                        enum group-14                       { value 14; }
                        enum group-15                       { value 15; }
                        enum group-19                       { value 19; }
                        enum group-20                       { value 20; }
                        enum group-21                       { value 21; }
                    }
                    description "Diffie-Hellman group used for PFS compilation";
                }

                leaf extended-sequence-number {
                    type boolean;
                    default "false";
                    description "Enable extended sequence numbering support";
                }

                leaf-list apply-groups {
                    type leafref {
                        path "../../../groups/group/name";
                    }
                    max-elements 8;
                    ordered-by user;
                    description "Apply a configuration group at this level";
                }

                leaf-list apply-groups-exclude {
                    type leafref {
                        path "../../../groups/group/name";
                    }
                    max-elements 8;
                    ordered-by user;
                    description "Exclude a configuration group at this level";
                }

            } // list ipsec-transform

            list ppk-list {
                key "name";
                max-elements 128;
                description "Enter the ppk-list list instance";

                leaf name {
                    type types-sros:named-item;
                    description "PPK list instance name";
                }

                leaf-list apply-groups {
                    type leafref {
                        path "../../../groups/group/name";
                    }
                    max-elements 8;
                    ordered-by user;
                    description "Apply a configuration group at this level";
                }

                leaf-list apply-groups-exclude {
                    type leafref {
                        path "../../../groups/group/name";
                    }
                    max-elements 8;
                    ordered-by user;
                    description "Exclude a configuration group at this level";
                }

                list ppk {
                    key "ppk-id";
                    max-elements 128;
                    description "Enter the ppk list instance";

                    leaf ppk-id {
                        type types-sros:named-item-64;
                        description "PPK ID";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                    container value {
                        presence "Enable the value context";
                        description "Enable the value context";

                        choice value {
                            mandatory true;
                            case ascii {

                                leaf ascii {
                                    type types-sros:encrypted-leaf {
                                        length "1..115";
                                    }
                                    description "PPK value as an ASCII string";
                                }

                            }
                            case hex {

                                leaf hex {
                                    type types-sros:encrypted-leaf-hex {
                                        length "1..115";
                                    }
                                    description "PPK value as a hexadecimal string with prefix 0x";
                                }

                            }
                        }
                    } // container value

                } // list ppk

            } // list ppk-list

            list static-sa {
                key "name";
                max-elements 1000;
                description "Enter the static-sa list instance";

                leaf name {
                    type types-sros:named-item;
                    description "Static SA name";
                }

                leaf description {
                    type types-sros:named-item;
                    description "Text description";
                }

                leaf direction {
                    type enumeration {
                        enum inbound                        { value 1; }
                        enum outbound                       { value 2; }
                        enum bidirectional                  { value 3; }
                    }
                    default "bidirectional";
                    description "Direction to which the static SA entry can be applied";
                }

                leaf protocol {
                    type enumeration {
                        enum ah                             { value 1; }
                        enum esp                            { value 2; }
                    }
                    default "esp";
                    description "IPsec protocol used with the static SA";
                }

                leaf spi {
                    type uint32 {
                        range "256..16383";
                    }
                    description "Security Parameter Index (SPI) for the static SA";
                }

                leaf-list apply-groups {
                    type leafref {
                        path "../../../groups/group/name";
                    }
                    max-elements 8;
                    ordered-by user;
                    description "Apply a configuration group at this level";
                }

                leaf-list apply-groups-exclude {
                    type leafref {
                        path "../../../groups/group/name";
                    }
                    max-elements 8;
                    ordered-by user;
                    description "Exclude a configuration group at this level";
                }

                container authentication {
                    presence "Enable the authentication context";
                    description "Enable the authentication context";

                    leaf algorithm {
                        type enumeration {
                            enum md5                            { value 2; }
                            enum sha1                           { value 3; }
                        }
                        mandatory true;
                        description "Authentication algorithm used for an IPsec manual SA";
                    }

                    leaf key {
                        type types-sros:encrypted-leaf {
                            length "1..54";
                        }
                        mandatory true;
                        description "Key used for the authentication algorithm";
                    }

                } // container authentication

            } // list static-sa

            list ts-list {
                key "name";
                max-elements 32768;
                description "Enter the ts-list list instance";

                leaf name {
                    type types-sros:named-item;
                    description "Traffic Selector (TS) list name";
                }

                leaf-list apply-groups {
                    type leafref {
                        path "../../../groups/group/name";
                    }
                    max-elements 8;
                    ordered-by user;
                    description "Apply a configuration group at this level";
                }

                leaf-list apply-groups-exclude {
                    type leafref {
                        path "../../../groups/group/name";
                    }
                    max-elements 8;
                    ordered-by user;
                    description "Exclude a configuration group at this level";
                }

                container local {
                    description "Enter the local context";

                    list entry {
                        key "id";
                        description "Enter the entry list instance";

                        leaf id {
                            type uint32 {
                                range "1..32";
                            }
                            description "TS list entry ID";
                        }

                        leaf-list apply-groups {
                            type leafref {
                                path "../../../../../groups/group/name";
                            }
                            max-elements 8;
                            ordered-by user;
                            description "Apply a configuration group at this level";
                        }

                        leaf-list apply-groups-exclude {
                            type leafref {
                                path "../../../../../groups/group/name";
                            }
                            max-elements 8;
                            ordered-by user;
                            description "Exclude a configuration group at this level";
                        }

                        container address {
                            presence "Enable the address context";
                            description "Enable the address context";

                            choice address-range {
                                mandatory true;
                                case prefix {

                                    leaf prefix {
                                        type types-sros:ip-prefix;
                                        description "IP prefix for address range in IKEv2 traffic selector";
                                    }

                                }
                                case range {

                                    container range {
                                        presence "Enable the range context";
                                        description "Enable the range context";

                                        leaf begin {
                                            type types-sros:ip-address;
                                            mandatory true;
                                            description "Lower bound of the IP address range for the entry";
                                        }

                                        leaf end {
                                            type types-sros:ip-address;
                                            mandatory true;
                                            description "Upper bound of the IP address range";
                                        }

                                    } // container range

                                }
                            }
                        } // container address

                        container protocol {
                            presence "Enable the protocol context";
                            description "Enable the protocol context";

                            choice range {
                                mandatory true;
                                case any {

                                    leaf any {
                                        type empty;
                                        description "Match any protocol ID";
                                    }

                                }
                                case id {

                                    container id {
                                        presence "Enable the id context";
                                        description "Enable the id context";

                                        choice id {
                                            mandatory true;
                                            case tcp {

                                                container tcp {
                                                    description "Enter the tcp context";

                                                    choice port {
                                                        case opaque-port {

                                                            leaf opaque {
                                                                type empty;
                                                                description "Support OPAQUE ports";
                                                            }

                                                        }
                                                        case port-range {

                                                            container port-range {
                                                                presence "Enable the port-range context";
                                                                description "Enable the port-range context";

                                                                leaf begin {
                                                                    type uint32 {
                                                                        range "0..65535";
                                                                    }
                                                                    mandatory true;
                                                                    description "Lower bound of the port range";
                                                                }

                                                                leaf end {
                                                                    type uint32 {
                                                                        range "0..65535";
                                                                    }
                                                                    mandatory true;
                                                                    description "Upper bound of the port range";
                                                                }

                                                            } // container port-range

                                                        }
                                                    }
                                                } // container tcp

                                            }
                                            case udp {

                                                container udp {
                                                    description "Enter the udp context";

                                                    choice port {
                                                        case opaque-port {

                                                            leaf opaque {
                                                                type empty;
                                                                description "Support OPAQUE ports";
                                                            }

                                                        }
                                                        case port-range {

                                                            container port-range {
                                                                presence "Enable the port-range context";
                                                                description "Enable the port-range context";

                                                                leaf begin {
                                                                    type uint32 {
                                                                        range "0..65535";
                                                                    }
                                                                    mandatory true;
                                                                    description "Lower bound of the port range";
                                                                }

                                                                leaf end {
                                                                    type uint32 {
                                                                        range "0..65535";
                                                                    }
                                                                    mandatory true;
                                                                    description "Upper bound of the port range";
                                                                }

                                                            } // container port-range

                                                        }
                                                    }
                                                } // container udp

                                            }
                                            case sctp {

                                                container sctp {
                                                    description "Enter the sctp context";

                                                    choice port {
                                                        case opaque-port {

                                                            leaf opaque {
                                                                type empty;
                                                                description "Support OPAQUE ports";
                                                            }

                                                        }
                                                        case port-range {

                                                            container port-range {
                                                                presence "Enable the port-range context";
                                                                description "Enable the port-range context";

                                                                leaf begin {
                                                                    type uint32 {
                                                                        range "0..65535";
                                                                    }
                                                                    mandatory true;
                                                                    description "Lower bound of the port range";
                                                                }

                                                                leaf end {
                                                                    type uint32 {
                                                                        range "0..65535";
                                                                    }
                                                                    mandatory true;
                                                                    description "Upper bound of the port range";
                                                                }

                                                            } // container port-range

                                                        }
                                                    }
                                                } // container sctp

                                            }
                                            case icmp {

                                                container icmp {
                                                    description "Enter the icmp context";

                                                    choice port {
                                                        case opaque-port {

                                                            leaf opaque {
                                                                type empty;
                                                                description "Support OPAQUE ports";
                                                            }

                                                        }
                                                        case port-range {

                                                            container port-range {
                                                                presence "Enable the port-range context";
                                                                description "Enable the port-range context";

                                                                leaf begin-icmp-type {
                                                                    type uint16 {
                                                                        range "0..255";
                                                                    }
                                                                    mandatory true;
                                                                    description "Lower bound of the ICMP type range";
                                                                }

                                                                leaf begin-icmp-code {
                                                                    type uint16 {
                                                                        range "0..255";
                                                                    }
                                                                    mandatory true;
                                                                    description "Lower bound of the ICMP code range";
                                                                }

                                                                leaf end-icmp-type {
                                                                    type uint16 {
                                                                        range "0..255";
                                                                    }
                                                                    mandatory true;
                                                                    description "Upper bound of the ICMP type range";
                                                                }

                                                                leaf end-icmp-code {
                                                                    type uint16 {
                                                                        range "0..255";
                                                                    }
                                                                    mandatory true;
                                                                    description "Upper bound of the ICMP code range";
                                                                }

                                                            } // container port-range

                                                        }
                                                    }
                                                } // container icmp

                                            }
                                            case icmp6 {

                                                container icmp6 {
                                                    description "Enter the icmp6 context";

                                                    choice port {
                                                        case opaque-port {

                                                            leaf opaque {
                                                                type empty;
                                                                description "Support OPAQUE ports";
                                                            }

                                                        }
                                                        case port-range {

                                                            container port-range {
                                                                presence "Enable the port-range context";
                                                                description "Enable the port-range context";

                                                                leaf begin-icmp-type {
                                                                    type uint16 {
                                                                        range "0..255";
                                                                    }
                                                                    mandatory true;
                                                                    description "Lower bound of the ICMP type range";
                                                                }

                                                                leaf begin-icmp-code {
                                                                    type uint16 {
                                                                        range "0..255";
                                                                    }
                                                                    mandatory true;
                                                                    description "Lower bound of the ICMP code range";
                                                                }

                                                                leaf end-icmp-type {
                                                                    type uint16 {
                                                                        range "0..255";
                                                                    }
                                                                    mandatory true;
                                                                    description "Upper bound of the ICMP type range";
                                                                }

                                                                leaf end-icmp-code {
                                                                    type uint16 {
                                                                        range "0..255";
                                                                    }
                                                                    mandatory true;
                                                                    description "Upper bound of the ICMP code range";
                                                                }

                                                            } // container port-range

                                                        }
                                                    }
                                                } // container icmp6

                                            }
                                            case mipv6 {

                                                container mipv6 {
                                                    description "Enter the mipv6 context";

                                                    choice port {
                                                        case opaque-port {

                                                            leaf opaque {
                                                                type empty;
                                                                description "Support OPAQUE ports";
                                                            }

                                                        }
                                                        case port-range {

                                                            container port-range {
                                                                presence "Enable the port-range context";
                                                                description "Enable the port-range context";

                                                                leaf begin {
                                                                    type uint16 {
                                                                        range "0..255";
                                                                    }
                                                                    mandatory true;
                                                                    description "Lower bound of the port range";
                                                                }

                                                                leaf end {
                                                                    type uint16 {
                                                                        range "0..255";
                                                                    }
                                                                    mandatory true;
                                                                    description "Upper bound of the port range";
                                                                }

                                                            } // container port-range

                                                        }
                                                    }
                                                } // container mipv6

                                            }
                                            case any {

                                                leaf protocol-id-with-any-port {
                                                    type union {
                                                        type enumeration {
                                                            enum icmp                           { value 1; }
                                                            enum tcp                            { value 6; }
                                                            enum udp                            { value 17; }
                                                            enum icmp6                          { value 58; }
                                                            enum sctp                           { value 132; }
                                                            enum mipv6                          { value 135; }
                                                        }
                                                        type int32 {
                                                            range "1..255";
                                                        }
                                                    }
                                                    description "Protocol ID that accepts any port value";
                                                }

                                            }
                                        }
                                    } // container id

                                }
                            }
                        } // container protocol

                    } // list entry

                } // container local

                container remote {
                    description "Enter the remote context";

                    list entry {
                        key "id";
                        description "Enter the entry list instance";

                        leaf id {
                            type uint32 {
                                range "1..32";
                            }
                            description "TS list entry ID";
                        }

                        leaf-list apply-groups {
                            type leafref {
                                path "../../../../../groups/group/name";
                            }
                            max-elements 8;
                            ordered-by user;
                            description "Apply a configuration group at this level";
                        }

                        leaf-list apply-groups-exclude {
                            type leafref {
                                path "../../../../../groups/group/name";
                            }
                            max-elements 8;
                            ordered-by user;
                            description "Exclude a configuration group at this level";
                        }

                        container address {
                            presence "Enable the address context";
                            description "Enable the address context";

                            choice address-range {
                                mandatory true;
                                case prefix {

                                    leaf prefix {
                                        type types-sros:ip-prefix;
                                        description "IP prefix for address range in IKEv2 traffic selector";
                                    }

                                }
                                case range {

                                    container range {
                                        presence "Enable the range context";
                                        description "Enable the range context";

                                        leaf begin {
                                            type types-sros:ip-address;
                                            mandatory true;
                                            description "Lower bound of the IP address range for the entry";
                                        }

                                        leaf end {
                                            type types-sros:ip-address;
                                            mandatory true;
                                            description "Upper bound of the IP address range";
                                        }

                                    } // container range

                                }
                            }
                        } // container address

                        container protocol {
                            presence "Enable the protocol context";
                            description "Enable the protocol context";

                            choice range {
                                mandatory true;
                                case any {

                                    leaf any {
                                        type empty;
                                        description "Match any protocol ID";
                                    }

                                }
                                case id {

                                    container id {
                                        presence "Enable the id context";
                                        description "Enable the id context";

                                        choice id {
                                            mandatory true;
                                            case tcp {

                                                container tcp {
                                                    description "Enter the tcp context";

                                                    choice port {
                                                        case opaque-port {

                                                            leaf opaque {
                                                                type empty;
                                                                description "Support OPAQUE ports";
                                                            }

                                                        }
                                                        case port-range {

                                                            container port-range {
                                                                presence "Enable the port-range context";
                                                                description "Enable the port-range context";

                                                                leaf begin {
                                                                    type uint32 {
                                                                        range "0..65535";
                                                                    }
                                                                    mandatory true;
                                                                    description "Lower bound of the port range";
                                                                }

                                                                leaf end {
                                                                    type uint32 {
                                                                        range "0..65535";
                                                                    }
                                                                    mandatory true;
                                                                    description "Upper bound of the port range";
                                                                }

                                                            } // container port-range

                                                        }
                                                    }
                                                } // container tcp

                                            }
                                            case udp {

                                                container udp {
                                                    description "Enter the udp context";

                                                    choice port {
                                                        case opaque-port {

                                                            leaf opaque {
                                                                type empty;
                                                                description "Support OPAQUE ports";
                                                            }

                                                        }
                                                        case port-range {

                                                            container port-range {
                                                                presence "Enable the port-range context";
                                                                description "Enable the port-range context";

                                                                leaf begin {
                                                                    type uint32 {
                                                                        range "0..65535";
                                                                    }
                                                                    mandatory true;
                                                                    description "Lower bound of the port range";
                                                                }

                                                                leaf end {
                                                                    type uint32 {
                                                                        range "0..65535";
                                                                    }
                                                                    mandatory true;
                                                                    description "Upper bound of the port range";
                                                                }

                                                            } // container port-range

                                                        }
                                                    }
                                                } // container udp

                                            }
                                            case sctp {

                                                container sctp {
                                                    description "Enter the sctp context";

                                                    choice port {
                                                        case opaque-port {

                                                            leaf opaque {
                                                                type empty;
                                                                description "Support OPAQUE ports";
                                                            }

                                                        }
                                                        case port-range {

                                                            container port-range {
                                                                presence "Enable the port-range context";
                                                                description "Enable the port-range context";

                                                                leaf begin {
                                                                    type uint32 {
                                                                        range "0..65535";
                                                                    }
                                                                    mandatory true;
                                                                    description "Lower bound of the port range";
                                                                }

                                                                leaf end {
                                                                    type uint32 {
                                                                        range "0..65535";
                                                                    }
                                                                    mandatory true;
                                                                    description "Upper bound of the port range";
                                                                }

                                                            } // container port-range

                                                        }
                                                    }
                                                } // container sctp

                                            }
                                            case icmp {

                                                container icmp {
                                                    description "Enter the icmp context";

                                                    choice port {
                                                        case opaque-port {

                                                            leaf opaque {
                                                                type empty;
                                                                description "Support OPAQUE ports";
                                                            }

                                                        }
                                                        case port-range {

                                                            container port-range {
                                                                presence "Enable the port-range context";
                                                                description "Enable the port-range context";

                                                                leaf begin-icmp-type {
                                                                    type uint16 {
                                                                        range "0..255";
                                                                    }
                                                                    mandatory true;
                                                                    description "Lower bound of the ICMP type range";
                                                                }

                                                                leaf begin-icmp-code {
                                                                    type uint16 {
                                                                        range "0..255";
                                                                    }
                                                                    mandatory true;
                                                                    description "Lower bound of the ICMP code range";
                                                                }

                                                                leaf end-icmp-type {
                                                                    type uint16 {
                                                                        range "0..255";
                                                                    }
                                                                    mandatory true;
                                                                    description "Upper bound of the ICMP type range";
                                                                }

                                                                leaf end-icmp-code {
                                                                    type uint16 {
                                                                        range "0..255";
                                                                    }
                                                                    mandatory true;
                                                                    description "Upper bound of the ICMP code range";
                                                                }

                                                            } // container port-range

                                                        }
                                                    }
                                                } // container icmp

                                            }
                                            case icmp6 {

                                                container icmp6 {
                                                    description "Enter the icmp6 context";

                                                    choice port {
                                                        case opaque-port {

                                                            leaf opaque {
                                                                type empty;
                                                                description "Support OPAQUE ports";
                                                            }

                                                        }
                                                        case port-range {

                                                            container port-range {
                                                                presence "Enable the port-range context";
                                                                description "Enable the port-range context";

                                                                leaf begin-icmp-type {
                                                                    type uint16 {
                                                                        range "0..255";
                                                                    }
                                                                    mandatory true;
                                                                    description "Lower bound of the ICMP type range";
                                                                }

                                                                leaf begin-icmp-code {
                                                                    type uint16 {
                                                                        range "0..255";
                                                                    }
                                                                    mandatory true;
                                                                    description "Lower bound of the ICMP code range";
                                                                }

                                                                leaf end-icmp-type {
                                                                    type uint16 {
                                                                        range "0..255";
                                                                    }
                                                                    mandatory true;
                                                                    description "Upper bound of the ICMP type range";
                                                                }

                                                                leaf end-icmp-code {
                                                                    type uint16 {
                                                                        range "0..255";
                                                                    }
                                                                    mandatory true;
                                                                    description "Upper bound of the ICMP code range";
                                                                }

                                                            } // container port-range

                                                        }
                                                    }
                                                } // container icmp6

                                            }
                                            case mipv6 {

                                                container mipv6 {
                                                    description "Enter the mipv6 context";

                                                    choice port {
                                                        case opaque-port {

                                                            leaf opaque {
                                                                type empty;
                                                                description "Support OPAQUE ports";
                                                            }

                                                        }
                                                        case port-range {

                                                            container port-range {
                                                                presence "Enable the port-range context";
                                                                description "Enable the port-range context";

                                                                leaf begin {
                                                                    type uint16 {
                                                                        range "0..255";
                                                                    }
                                                                    mandatory true;
                                                                    description "Lower bound of the port range";
                                                                }

                                                                leaf end {
                                                                    type uint16 {
                                                                        range "0..255";
                                                                    }
                                                                    mandatory true;
                                                                    description "Upper bound of the port range";
                                                                }

                                                            } // container port-range

                                                        }
                                                    }
                                                } // container mipv6

                                            }
                                            case any {

                                                leaf protocol-id-with-any-port {
                                                    type union {
                                                        type enumeration {
                                                            enum icmp                           { value 1; }
                                                            enum tcp                            { value 6; }
                                                            enum udp                            { value 17; }
                                                            enum icmp6                          { value 58; }
                                                            enum sctp                           { value 132; }
                                                            enum mipv6                          { value 135; }
                                                        }
                                                        type int32 {
                                                            range "1..255";
                                                        }
                                                    }
                                                    description "Protocol ID that accepts any port value";
                                                }

                                            }
                                        }
                                    } // container id

                                }
                            }
                        } // container protocol

                    } // list entry

                } // container remote

            } // list ts-list

            list tunnel-template {
                key "id";
                max-elements 2048;
                description "Enter the tunnel-template list instance";

                leaf id {
                    type types-ipsec:tunnel-template-id;
                    description "Tunnel template ID";
                }

                leaf description {
                    type types-sros:description;
                    description "Text description";
                }

                leaf clear-df-bit {
                    type boolean;
                    default "false";
                    description "Clear the Do-not-Fragment (DF) bit";
                }

                leaf encapsulated-ip-mtu {
                    type uint32 {
                        range "512..9000";
                    }
                    units "octets";
                    description "Maximum size of the encapsulated tunnel packet";
                }

                leaf ip-mtu {
                    type uint32 {
                        range "512..9000";
                    }
                    units "octets";
                    description "Maximum size of the IP MTU for the payload packets";
                }

                leaf private-tcp-mss-adjust {
                    type int32 {
                        range "512..9000";
                    }
                    units "octets";
                    description "New TCP MSS value on the private side";
                }

                leaf public-tcp-mss-adjust {
                    type union {
                        type uint32 {
                            range "512..9000";
                        }
                        type enumeration {
                            enum auto                           { value 0; }
                        }
                    }
                    units "octets";
                    description "New TCP MSS value on the public side";
                }

                leaf replay-window {
                    type uint32 {
                        range "32|64|128|256|512";
                    }
                    description "Anti-replay window size for the tunnel template";
                }

                leaf sp-reverse-route {
                    type enumeration {
                        enum none                           { value 0; }
                        enum use-security-policy            { value 1; }
                    }
                    default "none";
                    description "Reverse route creation method in private service";
                }

                leaf-list ipsec-transform {
                    type leafref {
                        path "../../ipsec-transform/id";
                    }
                    max-elements 4;
                    description "IPsec transform ID for the tunnel template";
                }

                leaf ignore-default-route {
                    type boolean;
                    default "false";
                    description "Ignore any full range traffic selector in TSi";
                }

                leaf copy-traffic-class-upon-decapsulation {
                    type boolean;
                    default "false";
                    description "Enable traffic class copy upon decapsulation";
                }

                leaf ppk-list {
                    type leafref {
                        path "../../ppk-list/name";
                    }
                    description "PPK list to use in the tunnel template";
                }

                leaf propagate-pmtu-v4 {
                    type boolean;
                    default "true";
                    description "Enable propagation of the path MTU to IPv4 hosts";
                }

                leaf propagate-pmtu-v6 {
                    type boolean;
                    default "true";
                    description "Enable propagation of the path MTU to IPv6 hosts";
                }

                leaf pmtu-discovery-aging {
                    type uint32 {
                        range "900..3600";
                    }
                    units "seconds";
                    default "900";
                    description "Aging out time of the learned path MTU";
                }

                leaf-list apply-groups {
                    type leafref {
                        path "../../../groups/group/name";
                    }
                    max-elements 8;
                    ordered-by user;
                    description "Apply a configuration group at this level";
                }

                leaf-list apply-groups-exclude {
                    type leafref {
                        path "../../../groups/group/name";
                    }
                    max-elements 8;
                    ordered-by user;
                    description "Exclude a configuration group at this level";
                }

                container icmp6-generation {
                    description "Enter the icmp6-generation context";

                    container pkt-too-big {
                        description "Enter the pkt-too-big context";

                        leaf admin-state {
                            type types-sros:admin-state;
                            default "enable";
                            description "Administrative state of Packet Too Big message sends";
                        }

                        leaf interval {
                            type uint32 {
                                range "1..60";
                            }
                            units "seconds";
                            default "10";
                            description "Maximum interval during which PTB messages can be sent";
                        }

                        leaf message-count {
                            type uint32 {
                                range "10..1000";
                            }
                            default "100";
                            description "Max ICMPv6 messages that can be sent during interval";
                        }

                    } // container pkt-too-big

                } // container icmp6-generation

                container reverse-route {
                    description "Enter the reverse-route context";

                    leaf metric {
                        type uint32 {
                            range "0..65535";
                        }
                        default "0";
                        description "Metric used for DL2L tunnel reverse routes";
                    }

                    leaf preference {
                        type uint32 {
                            range "0..255";
                        }
                        default "0";
                        description "Preference used for DL2L tunnel reverse routes";
                    }

                } // container reverse-route

                container icmp-generation {
                    description "Enter the icmp-generation context";

                    container frag-required {
                        description "Enter the frag-required context";

                        leaf admin-state {
                            type types-sros:admin-state;
                            default "enable";
                            description "Administrative state of sending ICMP messages";
                        }

                        leaf message-count {
                            type uint32 {
                                range "10..1000";
                            }
                            default "100";
                            description "Maximum number of ICMP messages that can be sent";
                        }

                        leaf interval {
                            type uint32 {
                                range "1..60";
                            }
                            units "seconds";
                            default "10";
                            description "Interval for sending ICMP messages";
                        }

                    } // container frag-required

                } // container icmp-generation

            } // list tunnel-template

            list trust-anchor-profile {
                key "name";
                max-elements 10128;
                description "Enter the trust-anchor-profile list instance";

                leaf name {
                    type types-sros:named-item;
                    description "Trust anchor profile name for IPsec tunnel or gateway";
                }

                leaf-list apply-groups {
                    type leafref {
                        path "../../../groups/group/name";
                    }
                    max-elements 8;
                    ordered-by user;
                    description "Apply a configuration group at this level";
                }

                leaf-list apply-groups-exclude {
                    type leafref {
                        path "../../../groups/group/name";
                    }
                    max-elements 8;
                    ordered-by user;
                    description "Exclude a configuration group at this level";
                }

                list trust-anchor {
                    key "ca-profile";
                    max-elements 8;
                    description "Add a list entry for trust-anchor";

                    leaf ca-profile {
                        type leafref {
                            path "../../../../system/security/pki/ca-profile/ca-profile-name";
                        }
                        description "Name of the CA profile as a trust anchor profile";
                    }

                } // list trust-anchor

            } // list trust-anchor-profile

            list ipsec-transport-mode-profile {
                key "name";
                description "Enter the ipsec-transport-mode-profile list instance";

                leaf name {
                    type types-sros:named-item;
                    description "IPsec transport mode profile name string";
                }

                leaf description {
                    type types-sros:description;
                    description "Text description";
                }

                leaf replay-window {
                    type uint32 {
                        range "32|64|128|256|512";
                    }
                    units "packets";
                    description "Anti-replay window size";
                }

                leaf-list apply-groups {
                    type leafref {
                        path "../../../groups/group/name";
                    }
                    max-elements 8;
                    ordered-by user;
                    description "Apply a configuration group at this level";
                }

                leaf-list apply-groups-exclude {
                    type leafref {
                        path "../../../groups/group/name";
                    }
                    max-elements 8;
                    ordered-by user;
                    description "Exclude a configuration group at this level";
                }

                container key-exchange {
                    description "Enter the key-exchange context";

                    container dynamic {
                        description "Enter the dynamic context";

                        leaf auto-establish {
                            type boolean;
                            default "false";
                            description "Attempt to establish a phase 1 exchange automatically";
                        }

                        leaf ike-policy {
                            type leafref {
                                path "../../../../ike-policy/id";
                            }
                            description "IKE policy ID";
                        }

                        leaf-list ipsec-transform {
                            type leafref {
                                path "../../../../ipsec-transform/id";
                            }
                            max-elements 4;
                            description "IPsec transform IDs used by the dynamic key";
                        }

                        leaf pre-shared-key {
                            type types-sros:encrypted-leaf {
                                length "1..115";
                            }
                            description "Pre-shared key for IKE authentication";
                        }

                        container cert {
                            description "Enter the cert context";

                            leaf cert-profile {
                                type leafref {
                                    path "../../../../../cert-profile/name";
                                }
                                description "Certificate profile name";
                            }

                            leaf trust-anchor-profile {
                                type leafref {
                                    path "../../../../../trust-anchor-profile/name";
                                }
                                description "Trust anchor profile name";
                            }

                            container status-verify {
                                description "Enter the status-verify context";

                                leaf default-result {
                                    type enumeration {
                                        enum revoked                        { value 0; }
                                        enum good                           { value 1; }
                                    }
                                    default "revoked";
                                    description "Default result for Certificate Status Verification";
                                }

                                leaf primary {
                                    type types-ipsec:cert-revocation-status;
                                    default "crl";
                                    description "Primary method of CSV to verify the revocation status";
                                }

                                leaf secondary {
                                    type types-ipsec:cert-revocation-status-with-none;
                                    default "none";
                                    description "Secondary method used to verify certificate revocation";
                                }

                            } // container status-verify

                        } // container cert

                        container id {
                            description "Enter the id context";

                            choice id {
                                case ipv4 {

                                    leaf ipv4 {
                                        type types-sros:ipv4-unicast-address;
                                        description "IPv4 as the local ID type";
                                    }

                                }
                                case ipv6 {

                                    leaf ipv6 {
                                        type types-sros:ip-address;
                                        description "IPv6 used as the local IKE ID type";
                                    }

                                }
                                case fqdn {

                                    leaf fqdn {
                                        type types-sros:fully-qualified-domain-name;
                                        description "FQDN used as the local ID IKE type";
                                    }

                                }
                            }
                        } // container id

                        container ppk {
                            description "Enter the ppk context";

                            leaf list {
                                type leafref {
                                    path "../../../../../ppk-list/name";
                                }
                                description "PPK list instance name";
                            }

                            leaf id {
                                type leafref {
                                    path "../../../../../ppk-list[name=current()/../list]/ppk/ppk-id";
                                }
                                description "PPK ID";
                            }

                        } // container ppk

                    } // container dynamic

                } // container key-exchange

                container max-history-key-records {
                    description "Enter the max-history-key-records context";

                    leaf ike {
                        type uint32 {
                            range "1..3";
                        }
                        description "Maximum number of historical IKE key records";
                    }

                    leaf esp {
                        type uint32 {
                            range "1..48";
                        }
                        description "Maximum number of recent records";
                    }

                } // container max-history-key-records

            } // list ipsec-transport-mode-profile

            container radius {
                description "Enter the radius context";

                list accounting-policy {
                    key "name";
                    max-elements 100;
                    description "Enter the accounting-policy list instance";

                    leaf name {
                        type types-sros:named-item;
                        description "RADIUS accounting policy name";
                    }

                    leaf radius-server-policy {
                        type leafref {
                            path "../../../../aaa/radius/server-policy/name";
                        }
                        description "Referenced RADIUS server policy";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                    container update-interval {
                        description "Enter the update-interval context";

                        leaf value {
                            type int32 {
                                range "0|5..259200";
                            }
                            units "minutes";
                            default "10";
                            description "Update interval of the RADIUS accounting data";
                        }

                        leaf jitter {
                            type int32 {
                                range "0..3600";
                            }
                            units "seconds";
                            description "Jitter interval for sending each interim-update packet";
                        }

                    } // container update-interval

                    container include-radius-attribute {
                        description "Enter the include-radius-attribute context";

                        leaf called-station-id {
                            type boolean;
                            default "false";
                            description "Include the Called-Station-Id attribute";
                        }

                        leaf calling-station-id {
                            type boolean;
                            default "false";
                            description "Include the Calling-Station-Id attribute";
                        }

                        leaf nas-identifier {
                            type boolean;
                            default "false";
                            description "Include the NAS-Identifier attribute";
                        }

                        leaf nas-ip-addr {
                            type boolean;
                            default "false";
                            description "Include the NAS-IP-Address attribute";
                        }

                        leaf nas-port-id {
                            type boolean;
                            default "false";
                            description "Include the NAS-Port-Id attribute";
                        }

                        leaf acct-stats {
                            type boolean;
                            default "false";
                            description "Include accounting attributes in RADIUS packets";
                        }

                        leaf framed-ip-addr {
                            type boolean;
                            default "false";
                            description "Include the Framed-IP-Address attribute";
                        }

                        leaf framed-ipv6-prefix {
                            type boolean;
                            default "false";
                            description "Include the Framed-IPv6-Prefix attribute";
                        }

                    } // container include-radius-attribute

                } // list accounting-policy

                list authentication-policy {
                    key "name";
                    max-elements 100;
                    description "Enter the authentication-policy list instance";

                    leaf name {
                        type types-sros:named-item;
                        description "RADIUS authentication policy name";
                    }

                    leaf radius-server-policy {
                        type leafref {
                            path "../../../../aaa/radius/server-policy/name";
                        }
                        description "Referenced RADIUS server policy";
                    }

                    leaf password {
                        type types-sros:encrypted-leaf {
                            length "1..115";
                        }
                        description "Password used in RADIUS access requests";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                    container include-radius-attribute {
                        description "Enter the include-radius-attribute context";

                        leaf called-station-id {
                            type boolean;
                            default "false";
                            description "Include the Called-Station-Id attribute";
                        }

                        leaf calling-station-id {
                            type boolean;
                            default "false";
                            description "Include the Calling-Station-Id attribute";
                        }

                        leaf nas-identifier {
                            type boolean;
                            default "false";
                            description "Include the NAS-Identifier attribute";
                        }

                        leaf nas-ip-addr {
                            type boolean;
                            default "false";
                            description "Include the NAS-IP-Address attribute";
                        }

                        leaf nas-port-id {
                            type boolean;
                            default "false";
                            description "Include the NAS-Port-Id attribute";
                        }

                        leaf client-cert-subject-key-id {
                            type boolean;
                            default "false";
                            description "Include the Subject Key Identifier";
                        }

                    } // container include-radius-attribute

                } // list authentication-policy

            } // container radius

        } // container ipsec

    } // grouping conf-ipsec

}
