module nokia-sr-openconfig-if-aggregate-deviations {

    namespace "urn:nokia.com:sros:ns:yang:sr:openconfig-if-aggregate-deviations";

    prefix "nokia-oc-lag-devs";

    import nokia-sros-yang-extensions     { prefix "sros-ext"; }
    import openconfig-if-aggregate        { prefix "oc-lag"; }
    import openconfig-interfaces          { prefix "oc-if"; }

    sros-ext:sros-major-release "rel25";
    organization "Nokia";
    contact
        "Nokia SR OS Support
         Web: <http://www.nokia.com>";
    description
        "This module contains the list of deviations against the openconfig-if-aggregate
         module for the Nokia SR OS based routers.

         Copyright 2016 Nokia. All rights reserved. Reproduction of this document
         is authorized on the condition that the foregoing copyright notice is included.

         This nokia-sr-openconfig-if-aggregate-deviations YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";
    revision "2025-03-12";

    deviation /oc-if:interfaces/oc-if:interface/oc-lag:aggregation/oc-lag:config/oc-lag:lag-type {
        deviate add {
            default "STATIC";
        }
    }

    deviation /oc-if:interfaces/oc-if:interface/oc-lag:aggregation/oc-lag:config/oc-lag:min-links {
        deviate replace {
            type uint16 {
                range "0..63";
            }
        }
        deviate add {
            default "0";
        }
    }

    deviation /oc-if:interfaces/oc-if:interface/oc-lag:aggregation/oc-lag:state/oc-lag:lag-type {
        deviate add {
            default "STATIC";
        }
    }

    deviation /oc-if:interfaces/oc-if:interface/oc-lag:aggregation/oc-lag:state/oc-lag:min-links {
        deviate replace {
            type uint16 {
                range "0..63";
            }
        }
        deviate add {
            default "0";
        }
    }

    deviation /oc-if:interfaces/oc-if:interface/oc-lag:aggregation/oc-lag:state/oc-lag:lag-speed {
        deviate replace {
            units "megabps";
        }
    }

    deviation /oc-if:interfaces/oc-if:interface/oc-lag:aggregation/oc-lag:state/oc-lag:member {
        deviate add {
            max-elements 64;
        }
    }

}
