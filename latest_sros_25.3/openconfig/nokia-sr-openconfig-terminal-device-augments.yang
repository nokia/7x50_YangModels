module nokia-sr-openconfig-terminal-device-augments {

    namespace "urn:nokia.com:sros:ns:yang:sr:openconfig-terminal-device-augments";

    prefix "nokia-oc-opt-term-augs";

    import ietf-yang-types                { prefix "yang"; }
    import nokia-sros-yang-extensions     { prefix "sros-ext"; }
    import openconfig-platform            { prefix "oc-platform"; }
    import openconfig-types               { prefix "oc-types"; }

    sros-ext:sros-major-release "rel25";
    organization "Nokia";
    contact
        "Nokia SR OS Support
         Web: <http://www.nokia.com>";
    description
        "This module contains the list of augments against the openconfig-terminal-device
         module for the Nokia SR OS based routers.

         Copyright 2016 Nokia. All rights reserved. Reproduction of this document
         is authorized on the condition that the foregoing copyright notice is included.

         This nokia-sr-openconfig-terminal-device-augments YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";
    revision "2025-03-12";

    augment /oc-platform:components/oc-platform:component {
        description
            "Adding optical channel extended data to physical inventory. This
             augmentation is only valid when the type of the component
             is OPTICAL_CHANNEL.";

        container optical-channel-ext {
            config false;
            description
                "Enclosing container with optical channel data that is currently not modeled
                 in openconfig.";

            container state {
                description "State data for optical channels that are currently not modeled in openconfig.";

                leaf rx-quality-margin {
                    type decimal64 {
                        fraction-digits 2;
                    }
                    units "dB";
                    description
                        "Quality margin (current value) as reported by the receiver in dB of
                         a channel with two decimal precision.";
                }

                container differential-group-delay {
                    description
                        "The differential group delay of an optical channel as reported
                         by the receiver in picoseconds. Values include the instantaneous,
                         average, minimum, and maximum statistics. If avg/min/max statistics
                         are not supported, the target is expected to just supply the instant
                         value.";

                    leaf instant {
                        type decimal64 {
                            fraction-digits 2;
                        }
                        units "ps";
                        description "The instantaneous value of the statistic.";
                    }

                    leaf avg {
                        type decimal64 {
                            fraction-digits 2;
                        }
                        units "ps";
                        description
                            "The arithmetic mean value of the statistic over the
                             time interval.";
                    }

                    leaf min {
                        type decimal64 {
                            fraction-digits 2;
                        }
                        units "ps";
                        description "The minimum value of the statistic over the time interval.";
                    }

                    leaf max {
                        type decimal64 {
                            fraction-digits 2;
                        }
                        units "ps";
                        description "The maximum value of the statistic over the time interval.";
                    }

                    leaf interval {
                        type oc-types:stat-interval;
                        description
                            "If supported by the system, this reports the time interval
                             over which the min/max/average statistics are computed by
                             the system.";
                    }

                } // container differential-group-delay

                container frame-rate-error-count {
                    description
                        "The frame rate error count of an optical channel as reported
                         by the receiver. Values include the instantaneous, average,
                         minimum, and maximum statistics. If avg/min/max statistics are not
                         supported, the target is expected to just supply the instant value.";

                    leaf instant {
                        type yang:gauge64;
                        description "The instantaneous value of the statistic.";
                    }

                    leaf avg {
                        type yang:gauge64;
                        description
                            "The arithmetic mean value of the statistic over the
                             time interval.";
                    }

                    leaf min {
                        type yang:gauge64;
                        description
                            "The minimum value of the statistic over the time
                             interval.";
                    }

                    leaf max {
                        type yang:gauge64;
                        description "The maximum value of the statistic over the time interval.";
                    }

                    leaf interval {
                        type oc-types:stat-interval;
                        description
                            "If supported by the system, this reports the time interval
                             over which the min/max/average statistics are computed by
                             the system.";
                    }

                } // container frame-rate-error-count

            } // container state

        } // container optical-channel-ext

    }

}
