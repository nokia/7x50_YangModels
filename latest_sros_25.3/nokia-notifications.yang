module nokia-notifications {

    yang-version "1.1";

    namespace "urn:nokia.com:sros:ns:yang:sr:notifications";

    prefix "notif";

    import ietf-netconf-notifications     { prefix "ietf-ncn"; }
    import nokia-sros-yang-extensions     { prefix "sros-ext"; }
    import nokia-types-log                { prefix "types-log"; }
    import nokia-types-sros               { prefix "types-sros"; }

    sros-ext:sros-major-release "rel25";
    organization "Nokia";
    contact
        "Nokia SR OS Support
         Web: <http://www.nokia.com>";
    description
        "Description of the notifications which are available in the system and can be
         sent out by the logger.

         Copyright 2016 Nokia. All rights reserved. Reproduction of this document
         is authorized on the condition that the foregoing copyright notice is included.

         This nokia-notifications YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";
    revision "2025-03-12";

    augment /ietf-ncn:netconf-config-change/ietf-ncn:edit {
        ///netconf-config-change/edit/value
        leaf value {
            type string;
            description "The new value of the target.";
        }

    }

    ///sros-config-change-event
    notification sros-config-change-event {
        description
            "Generated when the configuration of the system gets created,
             modified or deleted.";

        ///sros-config-change-event/sequence-number
        leaf sequence-number {
            type uint64;
            description
                "A sequence number to indicate the ordering of log events in the log-id.
                 If the event is replayed, the sequence number is replayed as well.";
        }

        ///sros-config-change-event/severity
        leaf severity {
            type types-log:severity-level;
            description "The severity level of the log event.";
        }

        ///sros-config-change-event/application
        leaf application {
            type types-log:application;
            description "The name of the application that reports the log event.";
        }

        ///sros-config-change-event/event-id
        leaf event-id {
            type uint32 {
                range "1..max";
            }
            description
                "The id the event that was generated.
                 Each log event type has a unique identifying number.  This number is
                 unique within a particular software application, such as IP, MPLS,
                 OSPF, etc.; but it is not necessarily unique across different software
                 applications.  That is MPLS event #1001 may be different from OSPF
                 event #1001.";
        }

        ///sros-config-change-event/event-name
        leaf event-name {
            type types-sros:named-item;
            description "The name of the log event that was generated.";
        }

        ///sros-config-change-event/router-name
        leaf router-name {
            type types-sros:named-item-or-empty;
            description "The router context name that generated the log event.";
        }

        ///sros-config-change-event/subject
        leaf subject {
            type types-sros:named-item;
            description
                "The router context name that generated the log event.
                 The subject is the entity that originated the event, such as the Port ID.";
        }

        ///sros-config-change-event/message
        leaf message {
            type string {
                length "1..4100";
            }
            description "The log event message.";
        }

        ///sros-config-change-event/event-params
        anyxml event-params {
            description "The event specific data splitted in parameters.";

        } // anyxml event-params

    } // notification sros-config-change-event

    ///sros-state-change-event
    notification sros-state-change-event {
        description "Generated on state changes in the system.";

        ///sros-state-change-event/sequence-number
        leaf sequence-number {
            type uint64;
            description
                "A sequence number to indicate the ordering of log events in the log-id.
                 If the event is replayed, the sequence number is replayed as well.";
        }

        ///sros-state-change-event/severity
        leaf severity {
            type types-log:severity-level;
            description "The severity level of the log event.";
        }

        ///sros-state-change-event/application
        leaf application {
            type types-log:application;
            description "The name of the application that reports the log event.";
        }

        ///sros-state-change-event/event-id
        leaf event-id {
            type uint32 {
                range "1..max";
            }
            description
                "The id the event that was generated.
                 Each log event type has a unique identifying number.  This number is
                 unique within a particular software application, such as IP, MPLS,
                 OSPF, etc.; but it is not necessarily unique across different software
                 applications.  That is MPLS event #1001 may be different from OSPF
                 event #1001.";
        }

        ///sros-state-change-event/event-name
        leaf event-name {
            type types-sros:named-item;
            description "The name of the log event that was generated.";
        }

        ///sros-state-change-event/router-name
        leaf router-name {
            type types-sros:named-item-or-empty;
            description "The router context name that generated the log event.";
        }

        ///sros-state-change-event/subject
        leaf subject {
            type types-sros:named-item;
            description
                "The router context name that generated the log event.
                 The subject is the entity that originated the event, such as the Port ID.";
        }

        ///sros-state-change-event/message
        leaf message {
            type string {
                length "1..4100";
            }
            description "The log event message.";
        }

        ///sros-state-change-event/event-params
        anyxml event-params {
            description "The event specific data splitted in parameters.";

        } // anyxml event-params

    } // notification sros-state-change-event

    ///sros-command-accounting-event
    notification sros-command-accounting-event {
        description "Generated when a user executes a command on a management interface.";

        ///sros-command-accounting-event/sequence-number
        leaf sequence-number {
            type uint64;
            description
                "A sequence number to indicate the ordering of log events in the log-id.
                 If the event is replayed, the sequence number is replayed as well.";
        }

        ///sros-command-accounting-event/severity
        leaf severity {
            type types-log:severity-level;
            description "The severity level of the log event.";
        }

        ///sros-command-accounting-event/application
        leaf application {
            type types-log:application;
            description "The name of the application that reports the log event.";
        }

        ///sros-command-accounting-event/event-id
        leaf event-id {
            type uint32 {
                range "1..max";
            }
            description
                "The id the event that was generated.
                 Each log event type has a unique identifying number.  This number is
                 unique within a particular software application, such as IP, MPLS,
                 OSPF, etc.; but it is not necessarily unique across different software
                 applications.  That is MPLS event #1001 may be different from OSPF
                 event #1001.";
        }

        ///sros-command-accounting-event/event-name
        leaf event-name {
            type types-sros:named-item;
            description "The name of the log event that was generated.";
        }

        ///sros-command-accounting-event/router-name
        leaf router-name {
            type types-sros:named-item-or-empty;
            description "The router context name that generated the log event.";
        }

        ///sros-command-accounting-event/subject
        leaf subject {
            type types-sros:named-item;
            description
                "The router context name that generated the log event.
                 The subject is the entity that originated the event, such as the Port ID.";
        }

        ///sros-command-accounting-event/message
        leaf message {
            type string {
                length "1..4100";
            }
            description "The log event message.";
        }

        ///sros-command-accounting-event/event-params
        anyxml event-params {
            description "The event specific data splitted in parameters.";

        } // anyxml event-params

    } // notification sros-command-accounting-event

    ///sros-md-rpc-accounting-event
    notification sros-md-rpc-accounting-event {
        description "Generated when a user executes a RPC on a management interface.";

        ///sros-md-rpc-accounting-event/sequence-number
        leaf sequence-number {
            type uint64;
            description
                "A sequence number to indicate the ordering of log events in the log-id.
                 If the event is replayed, the sequence number is replayed as well.";
        }

        ///sros-md-rpc-accounting-event/severity
        leaf severity {
            type types-log:severity-level;
            description "The severity level of the log event.";
        }

        ///sros-md-rpc-accounting-event/application
        leaf application {
            type types-log:application;
            description "The name of the application that reports the log event.";
        }

        ///sros-md-rpc-accounting-event/event-id
        leaf event-id {
            type uint32 {
                range "1..max";
            }
            description
                "The id the event that was generated.
                 Each log event type has a unique identifying number.  This number is
                 unique within a particular software application, such as IP, MPLS,
                 OSPF, etc.; but it is not necessarily unique across different software
                 applications.  That is MPLS event #1001 may be different from OSPF
                 event #1001.";
        }

        ///sros-md-rpc-accounting-event/event-name
        leaf event-name {
            type types-sros:named-item;
            description "The name of the log event that was generated.";
        }

        ///sros-md-rpc-accounting-event/router-name
        leaf router-name {
            type types-sros:named-item-or-empty;
            description "The router context name that generated the log event.";
        }

        ///sros-md-rpc-accounting-event/subject
        leaf subject {
            type types-sros:named-item;
            description
                "The router context name that generated the log event.
                 The subject is the entity that originated the event, such as the Port ID.";
        }

        ///sros-md-rpc-accounting-event/message
        leaf message {
            type string {
                length "1..4100";
            }
            description "The log event message.";
        }

        ///sros-md-rpc-accounting-event/event-params
        anyxml event-params {
            description "The event specific data splitted in parameters.";

        } // anyxml event-params

    } // notification sros-md-rpc-accounting-event

    ///sros-operation-status-change-event
    notification sros-operation-status-change-event {
        description "Generated on operation status change.";

        ///sros-operation-status-change-event/sequence-number
        leaf sequence-number {
            type uint64;
            description
                "A sequence number to indicate the ordering of log events in the log-id.
                 If the event is replayed, the sequence number is replayed as well.";
        }

        ///sros-operation-status-change-event/severity
        leaf severity {
            type types-log:severity-level;
            description "The severity level of the log event.";
        }

        ///sros-operation-status-change-event/application
        leaf application {
            type types-log:application;
            description "The name of the application that reports the log event.";
        }

        ///sros-operation-status-change-event/event-id
        leaf event-id {
            type uint32 {
                range "1..max";
            }
            description
                "The id the event that was generated.
                 Each log event type has a unique identifying number.  This number is
                 unique within a particular software application, such as IP, MPLS,
                 OSPF, etc.; but it is not necessarily unique across different software
                 applications.  That is MPLS event #1001 may be different from OSPF
                 event #1001.";
        }

        ///sros-operation-status-change-event/event-name
        leaf event-name {
            type types-sros:named-item;
            description "The name of the log event that was generated.";
        }

        ///sros-operation-status-change-event/router-name
        leaf router-name {
            type types-sros:named-item-or-empty;
            description "The router context name that generated the log event.";
        }

        ///sros-operation-status-change-event/subject
        leaf subject {
            type types-sros:named-item;
            description
                "The router context name that generated the log event.
                 The subject is the entity that originated the event, such as the Port ID.";
        }

        ///sros-operation-status-change-event/message
        leaf message {
            type string {
                length "1..4100";
            }
            description "The log event message.";
        }

        ///sros-operation-status-change-event/event-params
        anyxml event-params {
            description "The event specific data splitted in parameters.";

        } // anyxml event-params

    } // notification sros-operation-status-change-event

    ///sros-log-generic-event
    notification sros-log-generic-event {
        description
            "Generated on any event that is generated in the system
             that is not modeled by a more specific event.";

        ///sros-log-generic-event/sequence-number
        leaf sequence-number {
            type uint64;
            description
                "A sequence number to indicate the ordering of log events in the log-id.
                 If the event is replayed, the sequence number is replayed as well.";
        }

        ///sros-log-generic-event/severity
        leaf severity {
            type types-log:severity-level;
            description "The severity level of the log event.";
        }

        ///sros-log-generic-event/application
        leaf application {
            type types-log:application;
            description "The name of the application that reports the log event.";
        }

        ///sros-log-generic-event/event-id
        leaf event-id {
            type uint32 {
                range "1..max";
            }
            description
                "The id the event that was generated.
                 Each log event type has a unique identifying number.  This number is
                 unique within a particular software application, such as IP, MPLS,
                 OSPF, etc.; but it is not necessarily unique across different software
                 applications.  That is MPLS event #1001 may be different from OSPF
                 event #1001.";
        }

        ///sros-log-generic-event/event-name
        leaf event-name {
            type types-sros:named-item;
            description "The name of the log event that was generated.";
        }

        ///sros-log-generic-event/router-name
        leaf router-name {
            type types-sros:named-item-or-empty;
            description "The router context name that generated the log event.";
        }

        ///sros-log-generic-event/subject
        leaf subject {
            type types-sros:named-item;
            description
                "The router context name that generated the log event.
                 The subject is the entity that originated the event, such as the Port ID.";
        }

        ///sros-log-generic-event/message
        leaf message {
            type string {
                length "1..4100";
            }
            description "The log event message.";
        }

        ///sros-log-generic-event/event-params
        anyxml event-params {
            description "The event specific data splitted in parameters.";

        } // anyxml event-params

    } // notification sros-log-generic-event

}
