module nokia-types-ospf {

    yang-version "1.1";

    namespace "urn:nokia.com:sros:ns:yang:sr:types-ospf";

    prefix "types-ospf";

    import nokia-sros-yang-extensions     { prefix "sros-ext"; }
    import nokia-types-sros               { prefix "types-sros"; }

    sros-ext:sros-major-release "rel22";

    organization "Nokia";

    contact
        "Nokia SR OS Support
         Web: <http://www.nokia.com>";

    description
        "Common OSPF data types used in the SR OS management system.

         Copyright 2016 Nokia. All rights reserved. Reproduction of this document
         is authorized on the condition that the foregoing copyright notice is included.

         This nokia-types-ospf YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";

    revision "2022-03-02";

    typedef ipv4-or-uint32 {
        type union {
            type types-sros:ipv4-address;
            type uint32 {
                range "0..max";
            }
        }
        description "IPv4 address or 32-bit unsigned integer.";
    }

    typedef ipv4-or-non-zero-uint32 {
        type union {
            type types-sros:ipv4-address;
            type uint32 {
                range "1..max";
            }
            type enumeration {
                enum "none"                         { value 0; }
            }
        }
        default "none";
        description "IPv4 address or non-zero 32-bit unsigned integer.";
    }

    typedef vpn-domain-type {
        type enumeration {
            enum "0005"                         { value 5; }
            enum "0105"                         { value 261; }
            enum "0205"                         { value 517; }
            enum "8005"                         { value 32773; }
        }
        description "VPN domain type <0005|0105|0205|8005>.";
    }

    typedef advertise-router-capability-type {
        type enumeration {
            enum "false"                        { value 0; }
            enum "link"                         { value 1; }
            enum "area"                         { value 2; }
            enum "as"                           { value 3; }
        }
        description "Scope to advertise router-capability.";
    }

    typedef extended-lsa-mode {
        type enumeration {
            enum "sparse"                       { value 0; }
            enum "only"                         { value 1; }
        }
        description "OSPFv3 extended LSA mode.";
    }

    typedef area-extended-lsa-mode {
        type enumeration {
            enum "only"                         { value 1; }
        }
        description "Define extended LSA mode for this area.";
    }

    typedef interface-type {
        type enumeration {
            enum "broadcast"                    { value 1; }
            enum "non-broadcast"                { value 2; }
            enum "point-to-point"               { value 3; }
            enum "secondary"                    { value 6; }
        }
        description "Interface type.";
    }

    typedef lsa-filter-out {
        type enumeration {
            enum "none"                         { value 0; }
            enum "all"                          { value 1; }
            enum "except-own-rtrlsa"            { value 2; }
            enum "except-own-rtrlsa-and-defaults" { value 3; }
        }
        description "Configure LSA flooding reduction";
    }

    typedef rib-priority {
        type enumeration {
            enum "high"                         { value 2; }
        }
        description "Configure RIB priority for OSPF";
    }

    typedef authentication-type {
        type enumeration {
            enum "password"                     { value 1; }
            enum "message-digest"               { value 2; }
        }
        description
            "Enable/disable authentication and specify authentication type to be used on
             the interface";
    }

    typedef neighbor-oper-state-type {
        type enumeration {
            enum "down"                         { value 1; }
            enum "attempt"                      { value 2; }
            enum "init"                         { value 3; }
            enum "two-way"                      { value 4; }
            enum "exchange-start"               { value 5; }
            enum "exchange"                     { value 6; }
            enum "loading"                      { value 7; }
            enum "full"                         { value 8; }
        }
        description "Operational state of the neighbor.";
    }

    typedef restart-reason-type {
        type union {
            type uint32 {
                range "4..max";
            }
            type enumeration {
                enum "unknown"                      { value 0; }
                enum "sw-restart"                   { value 1; }
                enum "sw-reload"                    { value 2; }
                enum "switch-red"                   { value 3; }
            }
        }
        description "the value of restart-reason indicates the OSPF neighbor's graceful restart reason.";
    }

    typedef route-type {
        type enumeration {
            enum "network"                      { value 0; }
            enum "router"                       { value 1; }
        }
        description "The OSPF router type, network or router.";
    }

    typedef route-path-type {
        type enumeration {
            enum "intra-area"                   { value 0; }
            enum "inter-area"                   { value 1; }
            enum "external-type-1"              { value 2; }
            enum "external-type-2"              { value 3; }
            enum "nssa-type-1"                  { value 4; }
            enum "nssa-type-2"                  { value 5; }
            enum "summary-aggregate"            { value 6; }
            enum "nssa-aggregate"               { value 7; }
            enum "invalid"                      { value 8; }
        }
        description " Path type for a certain destination.";
    }

    typedef route-dest-type {
        type enumeration {
            enum "router"                       { value 0; }
            enum "asbr"                         { value 1; }
            enum "abr"                          { value 2; }
            enum "abr-asbr"                     { value 3; }
            enum "pnde"                         { value 4; }
            enum "prtr"                         { value 5; }
            enum "network"                      { value 6; }
            enum "stub"                         { value 7; }
            enum "host"                         { value 8; }
            enum "external"                     { value 9; }
            enum "nssa"                         { value 10; }
        }
        description "Route destination type.";
    }

    typedef rtm-status {
        type enumeration {
            enum "success"                      { value 0; }
            enum "failed"                       { value 1; }
            enum "not-reported"                 { value 2; }
            enum "discarded"                    { value 3; }
        }
        description "Status of the RTM updated.";
    }

    typedef neighbor-event {
        type enumeration {
            enum "create"                       { value 0; }
            enum "hello-received"               { value 1; }
            enum "start"                        { value 2; }
            enum "two-way-received"             { value 3; }
            enum "negotiation-done"             { value 4; }
            enum "exchange-done"                { value 5; }
            enum "bad-ls-request"               { value 6; }
            enum "loading-done"                 { value 7; }
            enum "adj-ok"                       { value 8; }
            enum "seq-number-mismatch"          { value 9; }
            enum "one-way-received"             { value 10; }
            enum "kill"                         { value 11; }
            enum "inactivity-timer"             { value 12; }
            enum "lower-level-down"             { value 13; }
            enum "bfd-down"                     { value 14; }
        }
        description "Events causing neighbor changes as defined in RFC2328.";
    }

    typedef packet-drop-reason {
        type enumeration {
            enum "bad-length"                   { value 1; }
            enum "bad-version"                  { value 2; }
            enum "area-mismatch"                { value 3; }
            enum "unknown-nbma-nbr"             { value 4; }
            enum "unknown-virtual-nbr"          { value 5; }
            enum "auth-type-mismatch"           { value 6; }
            enum "auth-failure"                 { value 7; }
            enum "net-mask-mismatch"            { value 8; }
            enum "hello-interval-mismatch"      { value 9; }
            enum "dead-interval-mismatch"       { value 10; }
            enum "option-mismatch"              { value 11; }
            enum "mtu-mismatch"                 { value 12; }
            enum "duplicate-router-id"          { value 13; }
            enum "if-type-mismatch"             { value 14; }
            enum "null-router-id"               { value 15; }
            enum "if-passive"                   { value 16; }
            enum "bad-packet-type"              { value 17; }
            enum "wrong-format"                 { value 18; }
            enum "wrong-checksum"               { value 19; }
            enum "if-oper-down"                 { value 20; }
            enum "bad-dst-addr"                 { value 21; }
            enum "bad-src-addr"                 { value 22; }
            enum "no-memory"                    { value 23; }
            enum "instance-mismatch"            { value 24; }
            enum "too-many-nbr-in-init"         { value 25; }
            enum "duplicate-nbr-addr"           { value 26; }
            enum "subnet-mismatch"              { value 27; }
            enum "too-many-nbr-on-interface"    { value 28; }
        }
        description "Reasons for which a packet can be dropped.";
    }

}
