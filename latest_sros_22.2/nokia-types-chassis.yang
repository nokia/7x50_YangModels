module nokia-types-chassis {

    yang-version "1.1";

    namespace "urn:nokia.com:sros:ns:yang:sr:types-chassis";

    prefix "types-chassis";

    import nokia-sros-yang-extensions     { prefix "sros-ext"; }

    sros-ext:sros-major-release "rel22";

    organization "Nokia";

    contact
        "Nokia SR OS Support
         Web: <http://www.nokia.com>";

    description
        "Common chassis types data types used in the SR OS management system.

         Copyright 2016 Nokia. All rights reserved. Reproduction of this document
         is authorized on the condition that the foregoing copyright notice is included.

         This nokia-types-chassis YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";

    revision "2021-11-23";

    typedef alarm-state {
        type enumeration {
            enum "unknown"                      { value 0; }
            enum "active"                       { value 1; }
            enum "cleared"                      { value 2; }
        }
        description
            "Specifies an enumerated integer whose value indicates the
             current alarm state of a physical or logical component in the
             Nokia SROS series system.";
    }

    typedef chassis-class {
        type enumeration {
            enum "router"                       { value 3; }
        }
    }

    typedef equipped-platform-type {
        type enumeration {
            enum "platform-unknown"             { value 0; }
            enum "platform-7750"                { value 1; }
            enum "platform-7450"                { value 2; }
            enum "platform-7710"                { value 3; }
            enum "platform-7950"                { value 4; }
            enum "platform-7705"                { value 5; }
            enum "platform-7250"                { value 6; }
        }
        description
            "Indicates the platform type of the installed hardware
             component, as read from the EEPROM.";
    }

    typedef sat-id {
        type uint32 {
            range "1..20";
        }
        description "The unique index identifying a satellite";
    }

    typedef sat-type {
        type enumeration {
            enum "es48-1gb-sfp"                 { value 4; }
            enum "es24-1gb-sfp"                 { value 6; }
            enum "es48-1gb-tx"                  { value 7; }
            enum "es24-1gb-tx"                  { value 8; }
            enum "es64-10gb-sfpp+4-100gb-cfp4"  { value 13; }
            enum "es24-sass-1gb-sfp"            { value 15; }
            enum "es48-sass-1gb-sfp"            { value 16; }
            enum "es24-sasmxp-1gb-sfp"          { value 17; }
            enum "es64-10gb-sfpp+4-100gb-qsfp28" { value 18; }
        }
        description "The provisioned satellite type.";
    }

    typedef sat-type-state {
        type enumeration {
            enum "not-equipped"                 { value 1; }
            enum "es48-1gb-sfp"                 { value 4; }
            enum "es24-1gb-sfp"                 { value 6; }
            enum "es48-1gb-tx"                  { value 7; }
            enum "es24-1gb-tx"                  { value 8; }
            enum "es64-10gb-sfpp+4-100gb-cfp4"  { value 13; }
            enum "es24-sass-1gb-sfp"            { value 15; }
            enum "es48-sass-1gb-sfp"            { value 16; }
            enum "es24-sasmxp-1gb-sfp"          { value 17; }
            enum "es64-10gb-sfpp+4-100gb-qsfp28" { value 18; }
        }
        description "The equipped satellite type.";
    }

    typedef pcm-type {
        type enumeration {
            enum "dual"                         { value 3; }
            enum "quad"                         { value 4; }
        }
        description "The provisioned pcm type.";
    }

    typedef pcm-type-state {
        type enumeration {
            enum "unassigned"                   { value 1; }
            enum "indeterminate"                { value 2; }
            enum "dual"                         { value 3; }
            enum "quad"                         { value 4; }
        }
        description "The equipped pcm type.";
    }

    typedef power-shelf-type {
        type enumeration {
            enum "ps-a10-shelf-dc"              { value 2; }
            enum "ps-b10-shelf-ac/hv"           { value 3; }
            enum "ps-a4-shelf-dc"               { value 4; }
            enum "ps-b3-shelf-ac/hv"            { value 5; }
        }
    }

    typedef power-shelf-type-state {
        type enumeration {
            enum "unassigned"                   { value 1; }
            enum "ps-a10-shelf-dc"              { value 2; }
            enum "ps-b10-shelf-ac/hv"           { value 3; }
            enum "ps-a4-shelf-dc"               { value 4; }
            enum "ps-b3-shelf-ac/hv"            { value 5; }
        }
    }

    typedef power-module-type {
        type enumeration {
            enum "ps-b-ac/hv-6000"              { value 6; }
            enum "ps-a-dc-4400"                 { value 8; }
            enum "ps-a-dc-6000"                 { value 9; }
            enum "ixr-ac-hvdc-3000"             { value 11; }
            enum "ixr-dc-3000"                  { value 12; }
        }
    }

    typedef power-module-type-state {
        type enumeration {
            enum "unassigned"                   { value 1; }
            enum "ps-b-ac/hv-6000"              { value 6; }
            enum "ps-a-dc-4400"                 { value 8; }
            enum "ps-a-dc-6000"                 { value 9; }
            enum "ixr-ac-hvdc-3000"             { value 11; }
            enum "ixr-dc-3000"                  { value 12; }
        }
    }

    typedef hw-event-action {
        type enumeration {
            enum "none"                         { value 0; }
            enum "log-only"                     { value 1; }
            enum "reset"                        { value 2; }
            enum "fail"                         { value 3; }
        }
    }

    typedef hw-oper-state {
        type enumeration {
            enum "unknown"                      { value 1; }
            enum "in-service"                   { value 2; }
            enum "out-of-service"               { value 3; }
            enum "diagnosing"                   { value 4; }
            enum "failed"                       { value 5; }
            enum "booting"                      { value 6; }
            enum "empty"                        { value 7; }
            enum "provisioned"                  { value 8; }
            enum "unprovisioned"                { value 9; }
            enum "upgrade"                      { value 10; }
            enum "downgrade"                    { value 11; }
            enum "in-service-upgrade"           { value 12; }
            enum "in-service-downgrade"         { value 13; }
            enum "reset-pending"                { value 14; }
            enum "soft-reset"                   { value 15; }
            enum "pre-extension"                { value 16; }
            enum "downloading"                  { value 17; }
        }
        description "Indicates the operational status of the hardware component.";
    }

}
