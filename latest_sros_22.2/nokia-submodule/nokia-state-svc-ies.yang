submodule nokia-state-svc-ies {

    yang-version "1.1";

    belongs-to nokia-state { prefix "state"; }

    import ietf-yang-types                { prefix "yang"; }
    import nokia-sros-yang-extensions     { prefix "sros-ext"; }
    import nokia-types-card               { prefix "types-card"; }
    import nokia-types-eth-cfm            { prefix "types-eth-cfm"; }
    import nokia-types-ipsec              { prefix "types-ipsec"; }
    import nokia-types-isa                { prefix "types-isa"; }
    import nokia-types-qos                { prefix "types-qos"; }
    import nokia-types-services           { prefix "types-services"; }
    import nokia-types-sros               { prefix "types-sros"; }
    import nokia-types-subscriber-mgmt    { prefix "types-submgt"; }

    include nokia-state-eth-cfm;
    include nokia-state-service;
    include nokia-state-svc-ies-sub-if;
    include nokia-state-svc-ies-vdo-if;


    sros-ext:sros-major-release "rel22";

    organization "Nokia";

    contact
        "Nokia SR OS Support
         Web: <http://www.nokia.com>";

    description
        "Nokia YANG Data model with operational state for ies services on SR OS based routers.

         Copyright 2016 Nokia. All rights reserved. Reproduction of this document
         is authorized on the condition that the foregoing copyright notice is included.

         This nokia-state-svc-ies YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";

    revision "2021-12-14";

    grouping state-svc-ies {
        list ies {
            key "service-name";
            description "Enter the ies list instance";

            leaf service-name {
                type types-services:service-name;
                description "Administrative service name";
            }

            leaf oper-service-id {
                type types-services:service-id;
                description "Service identifier";
            }

            leaf oper-state {
                type types-sros:oper-state;
                description "Operational state.";
            }

            leaf sap-count {
                type int32;
                description "Number of SAPs";
            }

            leaf sdp-bind-count {
                type int32;
                description "Number of SDP binds";
            }

            leaf template-used {
                type string;
                description "Template used to create this service";
            }

            leaf creation-origin {
                type types-sros:creation-origin;
                description "Creation origin of the service";
            }

            container subscriber-mgmt {
                description "Enter the subscriber-mgmt context";

                container up-resiliency {
                    description "Enter the up-resiliency context";

                    list monitor-oper-group {
                        key "oper-group";
                        description "Enter the monitor-oper-group list instance";

                        leaf oper-group {
                            type leafref {
                                path "../../../../../oper-group/name";
                            }
                            description "Operational group name";
                        }

                        leaf actual-health-drop {
                            type uint32;
                            description "The actual health drop caused by this monitor port or operational group";
                        }

                    } // list monitor-oper-group

                } // container up-resiliency

            } // container subscriber-mgmt

            list aa-interface {
                key "interface-name";
                description "Enter the aa-interface list instance";

                leaf interface-name {
                    type types-sros:interface-name;
                    description "Interface name";
                }

                leaf if-index {
                    type int32;
                    description "The interface index.";
                }

                leaf system-if-index {
                    type int32;
                    description "The interface system index.";
                }

                leaf oper-state {
                    type enumeration {
                        enum "up"                           { value 1; }
                        enum "down"                         { value 2; }
                        enum "testing"                      { value 3; }
                        enum "unknown"                      { value 4; }
                        enum "dormant"                      { value 5; }
                        enum "not-present"                  { value 6; }
                        enum "lower-layer-down"             { value 7; }
                    }
                    description
                        "The current operational state of the interface.
                         This leaf has the same semantics as ifOperStatus. 
                         in RFC 2863: The Interfaces Group MIB";
                }

                leaf oper-ip-mtu {
                    type uint32;
                    units "bytes";
                    description "Indicates the interface operational IP MTU.";
                }

                leaf creation-origin {
                    type types-sros:creation-origin;
                    description "Indicates the mechanism used to create this entry.";
                }

                leaf last-oper-change {
                    type yang:date-and-time;
                    description "The sysUpTime when the operational state of this interface last changed.";
                }

                list sap {
                    key "sap-id";
                    description "Enter the sap list instance";

                    leaf sap-id {
                        type types-sros:sap;
                        description "SAP ID";
                    }

                    leaf oper-dist-cpu-prot-policy {
                        type types-sros:named-item-or-empty;
                        description "Operational Distributed CPU Protection Policy.";
                    }

                    container statistics {
                        description "Enter the statistics context";

                        container authentication {
                            description "Enter the authentication context";

                            leaf discarded-packets {
                                type yang:counter32;
                                description
                                    "The number of DHCP packets discarded
                                     as result of authentication.";
                            }

                            leaf success-packets {
                                type yang:counter32;
                                description "The number of DHCP packets successfully authenticated.";
                            }

                        } // container authentication

                    } // container statistics

                    container ingress {
                        description "Enter the ingress context";

                        container qos {
                            description "Enter the qos context";

                            container sap-ingress {
                                description "Enter the sap-ingress context";

                                container forwarding-engine {
                                    description "Enter the forwarding-engine context";

                                    container statistics {
                                        description "Enter the statistics context";

                                        leaf dropped-packets {
                                            type yang:counter64;
                                            description
                                                "The number of packets dropped by the
                                                 ingress packet processor due to: SAP state,
                                                 ingress MAC, IP or IPv6 filter, same segment
                                                 discard, bad checksum, etc.";
                                        }

                                        leaf dropped-octets {
                                            type yang:counter64;
                                            description
                                                "The number of octets dropped by the
                                                 ingress packet processor due to: SAP state,
                                                 ingress MAC, IP or IPv6 filter, same segment
                                                 discard, bad checksum, etc.";
                                        }

                                        leaf received-valid-packets {
                                            type yang:counter64;
                                            description
                                                "The value of received-valid indicates
                                                 number of received valid packets, as determined by the SAP
                                                 ingress QoS policy, offered by the packet processor to the traffic manager.";
                                        }

                                        leaf received-valid-octets {
                                            type yang:counter64;
                                            description
                                                "The value of received-valid indicates
                                                 number of received valid octets, as determined by the SAP
                                                 ingress QoS policy, offered by the packet processor to the traffic manager.";
                                        }

                                        leaf high-priority-offered-packets {
                                            type yang:counter64;
                                            description
                                                "The number of high priority packets,
                                                 as determined by the SAP ingress QoS
                                                 policy, offered by the packet processor to the
                                                 traffic manager.";
                                        }

                                        leaf high-priority-offered-octets {
                                            type yang:counter64;
                                            description
                                                "The number of high priority octets,
                                                 as determined by the SAP ingress QoS
                                                 policy, offered by the packet processor to the
                                                 traffic manager.";
                                        }

                                        leaf low-priority-offered-packets {
                                            type yang:counter64;
                                            description
                                                "The number of low priority packets,
                                                 as determined by the SAP ingress QoS
                                                 policy, offered by the packet processor to the
                                                 traffic manager.";
                                        }

                                        leaf low-priority-offered-octets {
                                            type yang:counter64;
                                            description
                                                "The number of low priority octets,
                                                 as determined by the SAP ingress QoS
                                                 policy, offered by the packet processor to the
                                                 traffic manager.";
                                        }

                                        leaf uncolor-offered-packets {
                                            type yang:counter64;
                                            description
                                                "The number of uncolored packets,
                                                 as determined by the SAP ingress QoS
                                                 policy, offered by the packet processor to the
                                                 traffic manager.";
                                        }

                                        leaf uncolor-offered-octets {
                                            type yang:counter64;
                                            description
                                                "The number of uncolored octets,
                                                 as determined by the SAP ingress QoS
                                                 policy, offered by the packet processor to the
                                                 traffic manager.";
                                        }

                                        leaf managed-offered-packets {
                                            type yang:counter64;
                                            description
                                                "The value of managed-offered indicates
                                                 number of managed multicast packets, as determined by the SAP
                                                 ingress QoS policy, offered by the packet processor to the traffic manager.";
                                        }

                                        leaf managed-offered-octets {
                                            type yang:counter64;
                                            description
                                                "The value of managed-offered indicates
                                                 number of managed multicast octets, as determined by the SAP
                                                 ingress QoS policy, offered by the packet processor to the traffic manager.";
                                        }

                                        leaf aggregate-offered-packets {
                                            type yang:counter64;
                                            description
                                                "The value of aggregate-offered indicates aggregate
                                                 number of hi, lo priority and uncolour packets,
                                                 as determined by the SAP ingress QoS policy,
                                                 offered by the packet processor to the traffic manager.";
                                        }

                                        leaf aggregate-offered-octets {
                                            type yang:counter64;
                                            description
                                                "The value of managed-offered indicates aggregate
                                                 number of hi, lo priority and uncolour octets,
                                                 as determined by the SAP ingress QoS policy,
                                                 offered by the packet processor to the traffic manager.";
                                        }

                                        leaf last-cleared-time {
                                            type yang:date-and-time;
                                            description "Time when the counters in this table were last cleared.";
                                        }

                                    } // container statistics

                                } // container forwarding-engine

                                container traffic-manager {
                                    description "Enter the traffic-manager context";

                                    container statistics {
                                        description "Enter the statistics context";

                                        leaf cpm-packets {
                                            type yang:counter64;
                                            description
                                                "The value of cpm-packets indicates
                                                 ingress traffic in terms of packets destined to CPM
                                                 associated with this SAP.";
                                        }

                                        leaf cpm-octets {
                                            type yang:counter64;
                                            description
                                                "The value of cpm indicates
                                                 ingress traffic in terms of bytes destined to CPM
                                                 associated with this SAP.";
                                        }

                                        leaf high-priority-dropped-packets {
                                            type yang:counter64;
                                            description
                                                "The number of high priority packets,
                                                 as determined by the SAP ingress QoS
                                                 policy, dropped by the traffic manager due to:
                                                 MBS exceeded, buffer pool limit
                                                 exceeded, etc.";
                                        }

                                        leaf high-priority-dropped-octets {
                                            type yang:counter64;
                                            description
                                                "The number of high priority octets,
                                                 as determined by the SAP ingress QoS
                                                 policy, dropped by the traffic manager due to:
                                                 MBS exceeded, buffer pool limit
                                                 exceeded, etc.";
                                        }

                                        leaf low-priority-dropped-packets {
                                            type yang:counter64;
                                            description
                                                "The number of low priority packets,
                                                 as determined by the SAP ingress QoS
                                                 policy, dropped by the traffic manager due to:
                                                 MBS exceeded, buffer pool limit
                                                 exceeded, etc.";
                                        }

                                        leaf low-priority-dropped-octets {
                                            type yang:counter64;
                                            description
                                                "The number of low priority octets,
                                                 as determined by the SAP ingress QoS
                                                 policy, dropped by the traffic manager due to:
                                                 MBS exceeded, buffer pool limit
                                                 exceeded, etc.";
                                        }

                                        leaf in-profile-forwarded-packets {
                                            type yang:counter64;
                                            description
                                                "The number of in-profile packets
                                                 (rate below CIR) forwarded by the
                                                 ingress traffic manager.";
                                        }

                                        leaf in-profile-forwarded-octets {
                                            type yang:counter64;
                                            description
                                                "The number of in-profile octets
                                                 (rate below CIR) forwarded by the
                                                 ingress traffic manager.";
                                        }

                                        leaf out-profile-forwarded-packets {
                                            type yang:counter64;
                                            description
                                                "The number of out-of-profile packets
                                                 (rate above CIR) forwarded by the
                                                 ingress traffic manager.";
                                        }

                                        leaf out-profile-forwarded-octets {
                                            type yang:counter64;
                                            description
                                                "The number of out-of-profile octets
                                                 (rate above CIR) forwarded by the
                                                 ingress traffic manager.";
                                        }

                                        leaf aggregate-forwarded-packets {
                                            type yang:counter64;
                                            description
                                                "The aggregate number of in and out-of profile
                                                  packets forwarded by the ingress traffic manager.";
                                        }

                                        leaf aggregate-forwarded-octets {
                                            type yang:counter64;
                                            description
                                                "The aggregate number of in and out-of-profile
                                                 octets forwarded by the ingress traffic manager.";
                                        }

                                        leaf aggregate-dropped-packets {
                                            type yang:counter64;
                                            description
                                                "The aggregate number of in and out-of profile
                                                 packets, dropped by the traffic manager due to:
                                                 MBS exceeded, buffer pool limit
                                                 exceeded, etc.";
                                        }

                                        leaf aggregate-dropped-octets {
                                            type yang:counter64;
                                            description
                                                "The aggregate number of in and out-of profile
                                                 octets, dropped by the traffic manager due to:
                                                 MBS exceeded, buffer pool limit
                                                 exceeded, etc.";
                                        }

                                        leaf last-cleared-time {
                                            type yang:date-and-time;
                                            description "Time when the counters in this table were last cleared.";
                                        }

                                    } // container statistics

                                } // container traffic-manager

                            } // container sap-ingress

                        } // container qos

                    } // container ingress

                    container egress {
                        description "Enter the egress context";

                        container vlan-qos {
                            description "Enter the vlan-qos context";

                        } // container vlan-qos

                        container qos {
                            description "Enter the qos context";

                            container sap-egress {
                                description "Enter the sap-egress context";

                                container traffic-manager {
                                    description "Enter the traffic-manager context";

                                    container statistics {
                                        description "Enter the statistics context";

                                        leaf in-inplus-profile-dropped-packets {
                                            type yang:counter64;
                                            description
                                                "The number of in-profile packets
                                                 discarded by the egress traffic manager due
                                                 to: MBS exceeded, buffer pool limit
                                                 exceeded, etc.";
                                        }

                                        leaf in-inplus-profile-dropped-octets {
                                            type yang:counter64;
                                            description
                                                "The number of in-profile octets
                                                 discarded by the egress traffic manager due
                                                 to: MBS exceeded, buffer pool limit
                                                 exceeded, etc.";
                                        }

                                        leaf out-exceed-profile-dropped-packets {
                                            type yang:counter64;
                                            description
                                                "The number of out-of-profile packets
                                                 discarded by the egress traffic manager due
                                                 to: MBS exceeded, buffer pool limit
                                                 exceeded, etc.";
                                        }

                                        leaf out-exceed-profile-dropped-octets {
                                            type yang:counter64;
                                            description
                                                "The number of out-of-profile packets
                                                 discarded by the egress traffic manager due
                                                 to: MBS exceeded, buffer pool limit
                                                 exceeded, etc.";
                                        }

                                        leaf in-inplus-profile-forwarded-packets {
                                            type yang:counter64;
                                            description
                                                "The number of in-profile packets
                                                 (rate below CIR) forwarded by the
                                                 egress traffic manager.";
                                        }

                                        leaf in-inplus-profile-forwarded-octets {
                                            type yang:counter64;
                                            description
                                                "The number of in-profile octets
                                                 (rate below CIR) forwarded by the
                                                 egress traffic manager.";
                                        }

                                        leaf out-exceed-profile-forwarded-packets {
                                            type yang:counter64;
                                            description
                                                "The number of out-of-profile packets
                                                 (rate above CIR) forwarded by the
                                                 egress traffic manager.";
                                        }

                                        leaf out-exceed-profile-forwarded-octets {
                                            type yang:counter64;
                                            description
                                                "The number of out-of-profile octets
                                                 (rate above CIR) forwarded by the
                                                 egress traffic manager.";
                                        }

                                        leaf aggregate-forwarded-packets {
                                            type yang:counter64;
                                            description
                                                "The aggregate number of in and out-of profile
                                                 packets forwarded by the egress traffic manager.";
                                        }

                                        leaf aggregate-forwarded-octets {
                                            type yang:counter64;
                                            description
                                                "The aggregate number of in and out-of profile
                                                 octets forwarded by the egress traffic manager.";
                                        }

                                        leaf aggregate-dropped-packets {
                                            type yang:counter64;
                                            description
                                                "The aggregate number of in and out-of profile
                                                 packets discarded by the egress traffic manager due
                                                 to: MBS exceeded, buffer pool limit
                                                 exceeded, etc.";
                                        }

                                        leaf aggregate-dropped-octets {
                                            type yang:counter64;
                                            description
                                                "The aggregate number of in and out-of profile
                                                 octets discarded by the egress traffic manager due
                                                 to: MBS exceeded, buffer pool limit
                                                 exceeded, etc.";
                                        }

                                        leaf last-cleared-time {
                                            type yang:date-and-time;
                                            description "Time when the counters in this table were last cleared.";
                                        }

                                    } // container statistics

                                } // container traffic-manager

                            } // container sap-egress

                        } // container qos

                    } // container egress

                    container lag {
                        description "Enter the lag context";

                        leaf active-port {
                            type types-sros:port;
                            description
                                "Port on the lag associated with this SAP, that is used when
                                 lag-per-link-hash is enabled on the lag or when lag-link-map-profile
                                 is configured on this SAP.";
                        }

                    } // container lag

                    list locked-out-host {
                        key "id";
                        description "Enter the locked-out-host list instance";

                        leaf id {
                            type uint32;
                            description "Id of the locked out host";
                        }

                        leaf mac-address {
                            type yang:mac-address;
                            description "Mac-address of the locked out host";
                        }

                        leaf circuit-id {
                            type binary {
                                length "1..256";
                            }
                            description "Circuit-id of the locked out host";
                        }

                        leaf remote-id {
                            type binary {
                                length "1..256";
                            }
                            description "Remote-id of the locked out host";
                        }

                        leaf elapsed-reset-time {
                            type uint32;
                            units "seconds";
                            description "Elapsed reset time";
                        }

                        leaf elapsed-lock-time {
                            type uint32;
                            units "seconds";
                            description "Elapsed lock time";
                        }

                        leaf current-lock-timeout {
                            type uint32;
                            units "seconds";
                            description "The timeout for the current lock interval";
                        }

                        leaf next-lock-timeout {
                            type uint32;
                            units "seconds";
                            description "The timeout for the next lock interval";
                        }

                        leaf lockout-count {
                            type uint32;
                            description "Number of lockouts";
                        }

                        leaf lockout-state {
                            type enumeration {
                                enum "graceful"                     { value 1; description "The host is allowed to authenticate and the reset timer
                                is running. Another authentication failure for this host
                                while in this state while change the state to active.
                                If the reset timer expires, the lock out for this host
                                is removed."; }
                                enum "active"                       { value 2; description "The host is not allowed to authenticate and the lock-out
                                timer is running. When the timer expires, the state is
                                changed to graceful."; }
                            }
                            description "Lockout state for this host";
                        }

                    } // list locked-out-host

                } // list sap

                container ipv4 {
                    description "Enter the ipv4 context";

                    leaf oper-state {
                        type types-sros:oper-state;
                        description "The current IPv4 operational status of this router interface.";
                    }

                    leaf down-reason {
                        type bits {
                            bit admin-disabled                 { position 0; }
                            bit service-admin-disabled         { position 1; }
                            bit port-down                      { position 2; }
                            bit address-or-parent-not-ready    { position 3; }
                            bit associated-object-not-ready    { position 4; }
                            bit rvpls-down                     { position 5; }
                            bit operational-group-down         { position 6; }
                            bit admin-destroy                  { position 7; }
                            bit no-address                     { position 8; }
                            bit no-info                        { position 9; }
                            bit hold-down-timer-running        { position 10; }
                            bit protocol-down                  { position 11; }
                            bit invalid-port-configuration     { position 12; }
                            bit unknown                        { position 13; }
                            bit no-route-distinguisher         { position 14; }
                            bit wlan-gateway-redundancy-standby { position 15; }
                            bit wlan-gateway-group-degraded    { position 16; }
                            bit ip-control-tunnel-down         { position 17; }
                            bit pdn-address-mismatch           { position 18; }
                            bit ping-check-failure             { position 19; }
                            bit port-internal-loopback         { position 20; }
                        }
                        description
                            "Indicates the reason for why the interface is operationally down.
                                             
                             Values:
                                 admin-disabled                  - Administratively disabled.
                                 service-admin-disabled          - Assiocated service is administratively disabled.
                                 port-down                       - Associated SAP/port is operationally down.
                                 address-or-parent-not-ready     - Associated address or parent interface is not ready.
                                 associated-object-not-ready     - Associated object is not ready.
                                 rvpls-down                      - Associated R-VPLS service is operationally down.
                                 operational-group-down          - Associated operational group is operationally down.
                                 admin-destroy                   - The interface is being destroyed.
                                 no-address                      - There is no address configured.
                                 no-info                         - The interface info is not present.
                                 hold-down-timer-running         - The hold down timer is running.
                                 protocol-down                   - The protocols are operationally down.
                                 invalid-port-configuration      - Invalid port configuration.
                                 unknown                         - The interface is operationally down due to some unknown reason.
                                 no-route-distinguisher          - No route-distinguisher configured in the VRF.
                                 wlan-gateway-redundancy-standby - The interface is in standby state for WLAN-GW redundancy.
                                 wlan-gateway-group-degraded     - The interface associated WLAN-GW group is in a degraded state.
                                 ip-control-tunnel-down          - The IP tunnel associated to a control-tunnel interface is operationally down.
                                 pdn-address-mismatch            - The IP address learned from the packet data network does not match the configured primary IP address.
                                 ping-check-failure              - The IP interface is or went down because of a ping-template failure.
                                 port-internal-loopback          - The IP interface is bound to a port that has an internal loopback configured.";
                    }

                    container statistics {
                        description "Enter the statistics context";

                        leaf out-packets {
                            type yang:counter64;
                            description "The number of packets transmitted by this interface.";
                        }

                        leaf out-octets {
                            type yang:counter64;
                            description "The number of octets transmitted by this interface.";
                        }

                        leaf out-discard-packets {
                            type yang:counter64;
                            description "The number of transmit packets discarded.";
                        }

                        leaf out-discard-octets {
                            type yang:counter64;
                            description "The number of transmit octets discarded.";
                        }

                        leaf in-packets {
                            type yang:counter64;
                            description "The number of packets received.";
                        }

                        leaf in-octets {
                            type yang:counter64;
                            description "The number of octets received.";
                        }

                        leaf urpf-check-fail-packets {
                            type yang:counter64;
                            description "The number of packets that fail uRPF check on this interface.";
                        }

                        leaf urpf-check-fail-octets {
                            type yang:counter64;
                            description "The number of octets in the packets that fail uRPF check.";
                        }

                        leaf out-discard-dbcast-packets {
                            type yang:counter64;
                            description "The number of directed-broadcast packets dropped.";
                        }

                        leaf out-discard-dbcast-octets {
                            type yang:counter64;
                            description "The number of directed-broadcast octets dropped.";
                        }

                        leaf in-ip-helper-redirects-packets {
                            type yang:counter64;
                            description "The number of packets redirected to the ip-helper gateway.";
                        }

                        leaf in-ip-helper-redirects-octets {
                            type yang:counter64;
                            description "The number of bytes redirected to the ip-helper gateway.";
                        }

                    } // container statistics

                    container primary {
                        description "Enter the primary context";

                        leaf oper-address {
                            type types-sros:ip-address;
                            description "Indicates the operational address of this entry.";
                        }

                        leaf creation-origin {
                            type types-sros:creation-origin;
                            description "Indicates the mechanism used to create this entry.";
                        }

                    } // container primary

                } // container ipv4

                container ipv6 {
                    description "Enter the ipv6 context";

                    container statistics {
                        description "Enter the statistics context";

                        leaf out-packets {
                            type yang:counter64;
                            description "The number of packets transmitted by this interface.";
                        }

                        leaf out-octets {
                            type yang:counter64;
                            description "The number of octets transmitted by this interface.";
                        }

                        leaf out-discard-packets {
                            type yang:counter64;
                            description "The number of transmit packets discarded.";
                        }

                        leaf out-discard-octets {
                            type yang:counter64;
                            description "The number of transmit octets discarded.";
                        }

                        leaf in-packets {
                            type yang:counter64;
                            description "The number of packets received.";
                        }

                        leaf in-octets {
                            type yang:counter64;
                            description "The number of octets received.";
                        }

                        leaf urpf-check-fail-packets {
                            type yang:counter64;
                            description "The number of packets that fail uRPF check on this interface.";
                        }

                        leaf urpf-check-fail-octets {
                            type yang:counter64;
                            description "The number of octets in the packets that fail uRPF check.";
                        }

                    } // container statistics

                } // container ipv6

                container statistics {
                    description "Enter the statistics context";

                    container ip {
                        description "Enter the ip context";

                        leaf out-packets {
                            type yang:counter64;
                            description "The number of packets transmitted by this interface.";
                        }

                        leaf out-octets {
                            type yang:counter64;
                            description "The number of octets transmitted by this interface.";
                        }

                        leaf out-discard-packets {
                            type yang:counter64;
                            description "The number of transmit packets discarded.";
                        }

                        leaf out-discard-octets {
                            type yang:counter64;
                            description "The number of transmit octets discarded.";
                        }

                        leaf in-packets {
                            type yang:counter64;
                            description "The number of packets received.";
                        }

                        leaf in-octets {
                            type yang:counter64;
                            description "The number of octets received.";
                        }

                        leaf urpf-check-fail-packets {
                            type yang:counter64;
                            description "The number of packets that fail uRPF check on this interface.";
                        }

                        leaf urpf-check-fail-octets {
                            type yang:counter64;
                            description "The number of octets in the packets that fail uRPF check.";
                        }

                    } // container ip

                    list mac {
                        key "mac-address";
                        description "Enter the mac list instance";

                        leaf mac-address {
                            type yang:mac-address;
                            description "Mac-address";
                        }

                        leaf out-packets {
                            type yang:counter64;
                            description "The number of packets sent to the mac address";
                        }

                        leaf out-octets {
                            type yang:counter64;
                            description "The number of bytes sent to the mac address";
                        }

                        leaf in-packets {
                            type yang:counter64;
                            description "The number of packets received from the mac address";
                        }

                        leaf in-octets {
                            type yang:counter64;
                            description "The number of bytes received from the mac address";
                        }

                    } // list mac

                } // container statistics

            } // list aa-interface

            list interface {
                key "interface-name";
                description "Enter the interface list instance";

                leaf interface-name {
                    type types-sros:interface-name;
                    description "Interface name";
                }

                leaf if-index {
                    type int32;
                    description "The interface index.";
                }

                leaf system-if-index {
                    type int32;
                    description "The interface system index.";
                }

                leaf oper-state {
                    type enumeration {
                        enum "up"                           { value 1; }
                        enum "down"                         { value 2; }
                        enum "testing"                      { value 3; }
                        enum "unknown"                      { value 4; }
                        enum "dormant"                      { value 5; }
                        enum "not-present"                  { value 6; }
                        enum "lower-layer-down"             { value 7; }
                    }
                    description
                        "The current operational state of the interface.
                         This leaf has the same semantics as ifOperStatus. 
                         in RFC 2863: The Interfaces Group MIB";
                }

                leaf mcast-net-domain-egr {
                    type enumeration {
                        enum "not-applicable"               { value 1; }
                        enum "not-available"                { value 2; }
                        enum "consistent"                   { value 3; }
                        enum "inconsistent"                 { value 4; }
                    }
                    description "The value of this object indicates whether the spoke sdp leaves the router interface in the multicast network domain indicated by vRtrIfMcastNetworkDomainName";
                }

                leaf protocol {
                    type bits {
                        bit ospfv2                         { position 0; }
                        bit rip                            { position 1; }
                        bit isis                           { position 2; }
                        bit bgp                            { position 3; }
                        bit mpls                           { position 4; }
                        bit rsvp                           { position 5; }
                        bit ldp                            { position 6; }
                        bit igmp                           { position 7; }
                        bit pim                            { position 8; }
                        bit ospfv3                         { position 9; }
                        bit mld                            { position 10; }
                        bit ripng                          { position 11; }
                    }
                    description
                        "Indicates which protocols are configured on the interface.;
                                         
                         Values:
                             ospfv2 - Indicates if OSPFv2 is configured.
                             rip    - Indicates if RIP is configured.
                             isis   - Indicates if ISIS is configured.
                             bgp    - Indicates if BGP is configured.
                             mpls   - Indicates if MPLS is configured.
                             rsvp   - Indicates if RSVP is configured.
                             ldp    - Indicates if LDP is configured.
                             igmp   - Indicates if IGMP is configured.
                             pim    - Indicates if PIM is configured.
                             ospfv3 - Indicates if OSPFv3 is configured.
                             mld    - Indicates if MLD is configured.
                             ripng  - Indicates if RIPng is configured.";
                }

                leaf oper-ip-mtu {
                    type uint32;
                    units "bytes";
                    description "Indicates the interface operational IP MTU.";
                }

                leaf creation-origin {
                    type types-sros:creation-origin;
                    description "Indicates the mechanism used to create this entry.";
                }

                leaf last-oper-change {
                    type yang:date-and-time;
                    description "The sysUpTime when the operational state of this interface last changed.";
                }

                container ingress {
                    description "Enter the ingress context";

                    container statistics {
                        description "Enter the statistics context";

                        container policy-accounting {
                            description "Enter the policy-accounting context";

                            list source-class {
                                key "index";
                                description "Enter the source-class list instance";

                                leaf index {
                                    type types-sros:class-index;
                                    description "Source-class index";
                                }

                                leaf forwarded-packets {
                                    type yang:counter64;
                                    units "packets";
                                    description
                                        "Indicates the total number of packets received
                                         for this class that were forwarded.";
                                }

                                leaf forwarded-bytes {
                                    type yang:counter64;
                                    units "bytes";
                                    description
                                        "Indicates the total number of bytes received
                                         for this class that were forwarded.";
                                }

                                leaf incomplete-counts {
                                    type boolean;
                                    description "Indicates if the counts are incomplete.";
                                }

                            } // list source-class

                            list destination-class {
                                key "index";
                                description "Enter the destination-class list instance";

                                leaf index {
                                    type types-sros:class-index;
                                    description "Destination-class index";
                                }

                                leaf policer {
                                    type uint32 {
                                        range "1..63";
                                    }
                                    description "Indicates the policer associated with this destination class.";
                                }

                                leaf forwarded-packets {
                                    type yang:counter64;
                                    units "packets";
                                    description
                                        "Indicates the total number of packets received
                                         for this class that were forwarded.";
                                }

                                leaf forwarded-bytes {
                                    type yang:counter64;
                                    units "bytes";
                                    description
                                        "Indicates the total number of bytes received
                                         for this class that were forwarded.";
                                }

                                leaf incomplete-counts {
                                    type boolean;
                                    description "Indicates if the counts are incomplete.";
                                }

                            } // list destination-class

                            list policer {
                                key "index";
                                description "Enter the policer list instance";

                                leaf index {
                                    type uint32 {
                                        range "1..63";
                                    }
                                    description "Policer index";
                                }

                                leaf dropped-packets {
                                    type yang:counter64;
                                    units "packets";
                                    description
                                        "Indicates the total number of packets
                                         that were dropped by this policer.";
                                }

                                leaf dropped-bytes {
                                    type yang:counter64;
                                    units "bytes";
                                    description
                                        "Indicates the total number of bytes
                                         that were dropped by this policer.";
                                }

                                leaf forwarded-packets {
                                    type yang:counter64;
                                    units "packets";
                                    description
                                        "Indicates the total number of packets
                                         that were forwarded by this policer.";
                                }

                                leaf forwarded-bytes {
                                    type yang:counter64;
                                    units "bytes";
                                    description
                                        "Indicates the total number of bytes
                                         that were forwarded by this policer.";
                                }

                                leaf incomplete-counts {
                                    type boolean;
                                    description "Indicates if the counts are incomplete.";
                                }

                            } // list policer

                        } // container policy-accounting

                    } // container statistics

                } // container ingress

                container ping-template {
                    description "Enter the ping-template context";

                    leaf dscp {
                        type types-qos:dscp-name;
                        description "The DSCP value used in the outgoing ping packet";
                    }

                    leaf dot1p {
                        type types-qos:dot1p-priority;
                        description "The dot1p value used in the Ethernet header of the outgoing ping packet";
                    }

                    leaf interval {
                        type uint32 {
                            range "1..60";
                        }
                        units "seconds";
                        description "The ping interval";
                    }

                    leaf timeout {
                        type uint32 {
                            range "1..60";
                        }
                        units "seconds";
                        description "The ping timeout";
                    }

                    leaf failure-threshold {
                        type uint32 {
                            range "1..10";
                        }
                        description "The number of consecutive failed ping attempts needed to declare the interconnectivity down";
                    }

                    leaf fail-counter {
                        type yang:counter32;
                        description "The number of consecutive failed ping attempts while interconnectivity is up";
                    }

                    leaf reactivation-interval {
                        type uint32 {
                            range "1..60";
                        }
                        units "seconds";
                        description "The ping reactivation interval";
                    }

                    leaf reactivation-failure-threshold {
                        type uint32 {
                            range "0..10";
                        }
                        description "The number of consecutive failures without previous successes";
                    }

                    leaf reactivation-timeout {
                        type uint32 {
                            range "1..60";
                        }
                        units "seconds";
                        description "The ping reactivation timeout";
                    }

                    leaf reactivation-threshold {
                        type uint32 {
                            range "1..10";
                        }
                        description "The number of consecutive successful ping attempts needed to declare the interconnectivity up";
                    }

                    leaf pass-counter {
                        type yang:counter32;
                        description "The number of consecutive successful ping attempts while interconnectivity is down";
                    }

                    leaf size {
                        type uint32 {
                            range "12..9786";
                        }
                        units "octets";
                        description "The size of the Data (i.e. padding) field of the outgoing ICMP Echo packet";
                    }

                    leaf ttl {
                        type uint32 {
                            range "1..255";
                        }
                        description "The TTL value used in the outgoing ping packet";
                    }

                    leaf current-interval {
                        type enumeration {
                            enum "interval"                     { value 0; }
                            enum "reactivation"                 { value 1; }
                        }
                        description "The ping template current interval";
                    }

                    leaf current-state {
                        type enumeration {
                            enum "operational"                  { value 0; }
                            enum "recovering"                   { value 1; }
                            enum "failed"                       { value 2; }
                        }
                        description "The ping template current state";
                    }

                } // container ping-template

                list spoke-sdp {
                    key "sdp-bind-id";
                    description "Enter the spoke-sdp list instance";

                    leaf sdp-bind-id {
                        type types-services:sdp-bind-id;
                        description "SDP binding ID";
                    }

                    leaf oper-state {
                        type enumeration {
                            enum "up"                           { value 1; }
                            enum "down"                         { value 5; }
                        }
                        description "Indicates the operating status of this Service-SDP binding.";
                    }

                    leaf oper-flags {
                        type bits {
                            bit sdp-bind-admin-down            { position 0; }
                            bit svc-admin-down                 { position 1; }
                            bit stitching-svc-txdown           { position 2; }
                            bit sdp-oper-down                  { position 3; }
                            bit sdp-path-mtu-too-small         { position 4; }
                            bit no-ingress-vc-label            { position 5; }
                            bit no-egress-vc-label             { position 6; }
                            bit svc-mtu-mismatch               { position 7; }
                            bit vc-type-mismatch               { position 8; }
                            bit relearn-limit-exceeded         { position 9; }
                            bit ies-if-admin-down              { position 10; }
                            bit released-ingress-vc-label      { position 11; }
                            bit labels-exhausted               { position 12; }
                            bit svc-param-mismatch             { position 13; }
                            bit insufficient-bandwidth         { position 14; }
                            bit pw-peer-fault-status-bits      { position 15; }
                            bit mesh-sdp-down                  { position 16; }
                            bit not-managed-by-mcring          { position 17; }
                            bit out-of-resource                { position 18; }
                            bit mh-standby                     { position 19; }
                            bit oam-down-mep-fault             { position 20; }
                            bit oam-up-mep-fault               { position 21; }
                            bit standby-sig-slave-tx-down      { position 22; }
                            bit oper-grp-down                  { position 23; }
                            bit withdrawn-ingress-vc-label     { position 24; }
                            bit vpls-pmsi-down                 { position 25; }
                            bit rec-prot-src-mac               { position 26; }
                            bit peer-fault-status-tx-down      { position 27; }
                            bit evpn-route-conflict            { position 28; }
                            bit admin-locked                   { position 29; }
                            bit evpn-p2mp-conflict             { position 30; }
                            bit label-stack-limit-exceeded     { position 31; }
                            bit vccv-bfd-down                  { position 32; }
                            bit stitching-svc-pw-fault         { position 33; }
                        }
                        description
                            "This object indicates all the conditions that affect the
                             operating status of this SDP Bind.";
                    }

                    leaf pw-peer-status-bits {
                        type bits {
                            bit pw-not-forwarding              { position 0; }
                            bit lac-ingress-fault              { position 1; }
                            bit lac-egress-fault               { position 2; }
                            bit psn-ingress-fault              { position 3; }
                            bit psn-egress-fault               { position 4; }
                            bit pw-fwding-standby              { position 5; }
                        }
                        description
                            "Indicates bits set by the LDP peer when there is a fault on its
                             side of the pseudowire";
                    }

                    leaf pw-local-status-bits {
                        type bits {
                            bit pw-not-forwarding              { position 0; }
                            bit lac-ingress-fault              { position 1; }
                            bit lac-egress-fault               { position 2; }
                            bit psn-ingress-fault              { position 3; }
                            bit psn-egress-fault               { position 4; }
                            bit pw-fwding-standby              { position 5; }
                        }
                        description "Indicates locally set bits when there is a fault.";
                    }

                    leaf peer-vccv-cv-bits {
                        type bits {
                            bit icmp-ping                      { position 0; }
                            bit lsp-ping                       { position 1; }
                            bit bfd-fault-detection            { position 2; }
                            bit bfd-fault-detection-and-signalling { position 3; }
                        }
                        description "Indicates CV type bits set by the LDP peer if it supports VCCV.";
                    }

                    leaf peer-vccv-cc-bits {
                        type bits {
                            bit pwe3-control-word              { position 0; }
                            bit mpls-router-alert-label        { position 1; }
                            bit mpls-pw-demultiplex-or-label   { position 2; }
                        }
                        description "Indicates CC type bits set by the LDP peer if it supports VCCV.";
                    }

                    leaf oper-control-word {
                        type boolean;
                        description "Status of control word.";
                    }

                    leaf pw-fault-ip-address {
                        type types-sros:ip-address;
                        description "Faulty IP address sent by peer.";
                    }

                    leaf class-forwarding-oper-state {
                        type types-sros:oper-state;
                        description "Operational state of forwarding-class based forwarding on this SDP bind.";
                    }

                    leaf creation-origin {
                        type types-sros:creation-origin;
                        description "Creation origin of the service.";
                    }

                    leaf oper-hash-label {
                        type boolean;
                        description "Indicates the negotiated value of hash lavel that is used on this SDP binding.";
                    }

                    leaf min-required-sdp-oper-mtu {
                        type int32;
                        description "Minimum required SDP MTU size used with this SDP binding.";
                    }

                    container ingress {
                        description "Enter the ingress context";

                        leaf oper-label {
                            type uint32;
                            description "MPLS service label used by the far-end device to send packets to the local PEs sdp-bind.";
                        }

                        container statistics {
                            description "Enter the statistics context";

                            leaf forwarded-packets {
                                type yang:counter64;
                                description "Forwarded packets";
                            }

                            leaf forwarded-octets {
                                type yang:counter64;
                                description "Forwarded octets";
                            }

                            leaf dropped-packets {
                                type yang:counter64;
                                description "Dropped packets";
                            }

                            leaf dropped-octets {
                                type yang:counter64;
                                description "Dropped octets";
                            }

                        } // container statistics

                    } // container ingress

                    container egress {
                        description "Enter the egress context";

                        leaf oper-label {
                            type uint32;
                            description "MPLS service label used to send packets to the far-end device via this sdp-bind.";
                        }

                        container statistics {
                            description "Enter the statistics context";

                            leaf forwarded-packets {
                                type yang:counter64;
                                description "Forwarded packets";
                            }

                            leaf forwarded-octets {
                                type yang:counter64;
                                description "Forwarded octets";
                            }

                        } // container statistics

                    } // container egress

                    container bfd {
                        description "Enter the bfd context";

                        leaf oper-state {
                            type types-services:bfd-oper-state;
                            description "BFD oper state";
                        }

                        leaf remaining-up-time {
                            type int32;
                            units "seconds";
                            description "Remaining uptime";
                        }

                    } // container bfd

                    container eth-cfm {
                        description "Enter the eth-cfm context";

                        list mep {
                            key "md-admin-name ma-admin-name mep-id";
                            description "Enter the mep list instance";

                            leaf md-admin-name {
                                type leafref {
                                    path "../../../../../../../eth-cfm/domain/md-admin-name";
                                }
                                description "Admin-assigned maintenance domain index value";
                            }

                            leaf ma-admin-name {
                                type leafref {
                                    path "../../../../../../../eth-cfm/domain[md-admin-name=current()/../md-admin-name]/association/ma-admin-name";
                                }
                                description "Maintenance association name";
                            }

                            leaf mep-id {
                                type types-eth-cfm:mep-id-type;
                                description "Maintenance endpoint ID";
                            }

                            leaf if-index {
                                type uint32;
                                description "Port ID of the MEP.";
                            }

                            leaf oper-mac-address {
                                type yang:mac-address;
                                description "Operational MAC address of the MEP.";
                            }

                            container csf {
                                description "Enter the csf context";

                                container received {
                                    description "Enter the received context";

                                    leaf state {
                                        type enumeration {
                                            enum "los"                          { value 0; }
                                            enum "ais"                          { value 1; }
                                            enum "rdi"                          { value 2; }
                                            enum "dci"                          { value 3; }
                                        }
                                        description
                                            "Indicates the state of the received CSF frames for the MEP.
                                                los (0) - Client Loss of Signal
                                                ais (1) - Client Forward Defect Indication
                                                rdi (2) - Client Reverse Defect Indication
                                                dci (3) - Client Defect Clear Indication.";
                                    }

                                    leaf interval {
                                        type uint32 {
                                            range "1|60";
                                        }
                                        units "seconds";
                                        description "Indicates the CSF Interval received in the most recent CSF frame.";
                                    }

                                } // container received

                            } // container csf

                            container grace {
                                description "Enter the grace context";

                                container transmitted {
                                    description "Enter the transmitted context";

                                    leaf grace-notification {
                                        type enumeration {
                                            enum "no-transmit"                  { value 0; }
                                            enum "grace"                        { value 1; }
                                            enum "eth-ed"                       { value 2; }
                                        }
                                        description "Indicates the state of the MEP grace period PDU transmission.";
                                    }

                                } // container transmitted

                                container received {
                                    description "Enter the received context";

                                    leaf process-grace-notification {
                                        type boolean;
                                        description
                                            "Indicates whether the local MEP is receiving and processing grace notifications
                                             from one or more peer MEPs. A value of 'true ' indicates the local MEP is
                                             receiving and processing grace from at least one peer MEP. A value
                                             of 'false' indicates that no peer grace notifications are being
                                             received and processed.";
                                    }

                                } // container received

                            } // container grace

                            container ccm-states {
                                description "Enter the ccm-states context";

                                leaf transmit-status {
                                    type enumeration {
                                        enum "no-transmit"                  { value 0; }
                                        enum "transmit"                     { value 1; }
                                        enum "suppressed"                   { value 2; }
                                    }
                                    description
                                        "Indicates the state of the MEP CCM PDU transmission.

                                         Values:
                                            noTransmit (0) - no CCM PDUs are being transmitted by the MEP
                                            transmit   (1) - MEP is currently transmitting CCM PDUs
                                            suppressed (2) - MEP should be transmitting CCM PDUs but is suppressing
                                                            them due to an internal condition";
                                }

                                leaf sequence-error {
                                    type yang:counter32;
                                    description "The total number of out-of-sequence CCMs received from all remote MEPs.";
                                }

                                leaf fng-state {
                                    type types-eth-cfm:fng-state-type;
                                    description "Current state of the MEP Fault Notification Generator State Machine.";
                                }

                                container transmitted {
                                    description "Enter the transmitted context";

                                    leaf count {
                                        type yang:counter32;
                                        description "Total number of CCMs transmitted.";
                                    }

                                    leaf interface-status {
                                        type types-eth-cfm:interface-status;
                                        description
                                            "Indicates the interface status TLV information included in the most
                                             recent Connectivity Check Message (CCM) transmission from the local MEP.
                                             If the local MEP CCM transmissions are not enabled, or if no interface
                                             status TLV was included in the most recent transmission, then
                                             ccm-tx-if-status will return a value of is-no-interface-status-tlv (0).";
                                    }

                                    leaf port-status {
                                        type types-eth-cfm:port-status;
                                        description
                                            "Indicates the port status TLV information included in the most recent
                                             Connectivity Check Message (CCM) transmission from the local MEP.

                                             If the local MEP CCM transmissions are not enabled, or if no port
                                             status TLV was included in the most recent transmission, then
                                             ccm-tx-port-status will return a value of ps-no-port-state-tlv (0).";
                                    }

                                    leaf remote-defect-indicator {
                                        type boolean;
                                        description
                                            "Indicates whether or not the Remote Defect Indication (RDI) bit was set
                                             on the most recent Connectivity Check Message (CCM) transmission from the
                                             local MEP.

                                             If the local MEP CCM transmissions are not eanbled, or if the RDI bit
                                             was not set in the most recent transmission, then ccm-tx-rdi will return
                                             a value of 'false (2)'.";
                                    }

                                } // container transmitted

                                container received {
                                    description "Enter the received context";

                                    leaf highest-priority-defect {
                                        type types-eth-cfm:highest-priority-defect-type;
                                        description
                                            "The highest priority defect that has been present since the
                                             MEPs Fault Notification Generator State Machine was last in
                                             the reset state.";
                                    }

                                    leaf defect-flags {
                                        type types-eth-cfm:mep-defect-flags;
                                        description "A vector of boolean error conditions, any of which may be true.";
                                    }

                                    list remote-mep-peer {
                                        key "remote-mep-id";
                                        description "Enter the remote-mep-peer list instance";

                                        leaf remote-mep-id {
                                            type types-eth-cfm:mep-id-type;
                                            description "The Remote MEP ID within the same Maintenance Association.";
                                        }

                                        leaf auto-discovered {
                                            type boolean;
                                            description
                                                "Specifies whether or not the remote peer was automatically discovered
                                                 ('true') or not. Auto-discovered remote peers are created by the system
                                                 only, and are of a 'volatile' storage type. Specifying the value of
                                                 'false' will mark an auto-discovered remote peer as permanently configured.";
                                        }

                                        leaf receiving-ccm {
                                            type types-eth-cfm:remote-mep-state-type;
                                            description "The operational CCM receiving state of the remote MEP.";
                                        }

                                        leaf ccm-status-since {
                                            type yang:date-and-time;
                                            description
                                                "The time at which the Remote MEP
                                                 last entered either the mep-failed or mep-ok state. ";
                                        }

                                        leaf peer-mac-address {
                                            type yang:mac-address;
                                            description "The MAC address of the remote MEP.";
                                        }

                                        leaf receiving-remote-defect-indicator {
                                            type boolean;
                                            description
                                                "State of the RDI bit in the last received CCM (true for rdi=1), or false
                                                 if none has been received.";
                                        }

                                        leaf port-status-tlv {
                                            type types-eth-cfm:port-status;
                                            description
                                                "An enumerated value of the Port status TLV received in the
                                                 last CCM from the remote MEP or the default value
                                                 ps-no-port-state-tlv indicating either no CCM has been received,
                                                 or that no port status TLV was received in the last CCM. ";
                                        }

                                        leaf interface-status-tlv {
                                            type types-eth-cfm:interface-status;
                                            description
                                                "An enumerated value of the Interface status TLV received
                                                 in the last CCM from the remote MEP or the default value
                                                 is-no-interface-status-tlv indicating either no CCM has been
                                                 received, or that no interface status TLV was received in
                                                 the last CCM.";
                                        }

                                    } // list remote-mep-peer

                                } // container received

                            } // container ccm-states

                            container mc-lag {
                                description "Enter the mc-lag context";

                                leaf inactive-state {
                                    type enumeration {
                                        enum "not-applicable"               { value 0; }
                                        enum "standby"                      { value 1; }
                                        enum "active"                       { value 2; }
                                    }
                                    description
                                        "Indicates the MC-LAG inactive state of the mep.  The value of
                                         system/eth-cfm/redundancy/mc-lag/standby-mep must be 'true (1)' 
                                         on the node for this leaf to have meaning.";
                                }

                            } // container mc-lag

                            container statistics {
                                description "Enter the statistics context";

                                list opcode {
                                    key "opcode-name";
                                    description "Enter the opcode list instance";

                                    leaf opcode-name {
                                        type types-eth-cfm:statistics-opcode-name;
                                        description "Integer that defines which CFM PDU Opcode the statictics refer to.";
                                    }

                                    leaf transmitted {
                                        type yang:counter32;
                                        description "The total number of PDUs transmitted from the node with the specified Opcode.";
                                    }

                                    leaf received {
                                        type yang:counter32;
                                        description "The total number of PDUs received on the node with the specified Opcode.";
                                    }

                                } // list opcode

                            } // container statistics

                        } // list mep

                    } // container eth-cfm

                } // list spoke-sdp

                list sap {
                    key "sap-id";
                    description "Enter the sap list instance";

                    leaf sap-id {
                        type types-sros:sap;
                        description "SAP ID";
                    }

                    leaf oper-state {
                        type enumeration {
                            enum "up"                           { value 1; }
                            enum "down"                         { value 2; }
                        }
                        description "Operating state of this SAP";
                    }

                    leaf oper-flags {
                        type types-services:l3-sap-oper-flags;
                        description "Conditions that affect the operating status of this SAP.";
                    }

                    leaf mirror-state {
                        type enumeration {
                            enum "ingress"                      { value 1; }
                            enum "egress"                       { value 2; }
                            enum "ingress-and-egress"           { value 3; }
                            enum "disabled"                     { value 4; }
                        }
                        description "Indicates whether traffic mirroring has been enabled on this SAP";
                    }

                    leaf template-used {
                        type types-sros:named-item-or-empty;
                        description "Name of the sap-template used to create this sap.";
                    }

                    leaf oper-dist-cpu-prot-policy {
                        type types-sros:named-item-or-empty;
                        description "Operational Distributed CPU Protection Policy.";
                    }

                    container statistics {
                        description "Enter the statistics context";

                        container authentication {
                            description "Enter the authentication context";

                            leaf discarded-packets {
                                type yang:counter32;
                                description
                                    "The number of DHCP packets discarded
                                     as result of authentication.";
                            }

                            leaf success-packets {
                                type yang:counter32;
                                description "The number of DHCP packets successfully authenticated.";
                            }

                        } // container authentication

                    } // container statistics

                    container ingress {
                        description "Enter the ingress context";

                        container qos {
                            description "Enter the qos context";

                            container sap-ingress {
                                description "Enter the sap-ingress context";

                                container forwarding-engine {
                                    description "Enter the forwarding-engine context";

                                    container statistics {
                                        description "Enter the statistics context";

                                        leaf dropped-packets {
                                            type yang:counter64;
                                            description "Policy ID";
                                        }

                                        leaf dropped-octets {
                                            type yang:counter64;
                                            description
                                                "The number of octets dropped by the
                                                 ingress packet processor due to: SAP state,
                                                 ingress MAC, IP or IPv6 filter, same segment
                                                 discard, bad checksum, etc.";
                                        }

                                        leaf received-valid-packets {
                                            type yang:counter64;
                                            description
                                                "The value of received-valid indicates
                                                 number of received valid packets, as determined by the SAP
                                                 ingress QoS policy, offered by the packet processor to the traffic manager.";
                                        }

                                        leaf received-valid-octets {
                                            type yang:counter64;
                                            description
                                                "The value of received-valid indicates
                                                 number of received valid octets, as determined by the SAP
                                                 ingress QoS policy, offered by the packet processor to the traffic manager.";
                                        }

                                        leaf high-priority-offered-packets {
                                            type yang:counter64;
                                            description
                                                "The number of high priority packets,
                                                 as determined by the SAP ingress QoS
                                                 policy, offered by the packet processor to the
                                                 traffic manager.";
                                        }

                                        leaf high-priority-offered-octets {
                                            type yang:counter64;
                                            description
                                                "The number of high priority octets,
                                                 as determined by the SAP ingress QoS
                                                 policy, offered by the packet processor to the
                                                 traffic manager.";
                                        }

                                        leaf low-priority-offered-packets {
                                            type yang:counter64;
                                            description
                                                "The number of low priority packets,
                                                 as determined by the SAP ingress QoS
                                                 policy, offered by the packet processor to the
                                                 traffic manager.";
                                        }

                                        leaf low-priority-offered-octets {
                                            type yang:counter64;
                                            description
                                                "The number of low priority octets,
                                                 as determined by the SAP ingress QoS
                                                 policy, offered by the packet processor to the
                                                 traffic manager.";
                                        }

                                        leaf uncolor-offered-packets {
                                            type yang:counter64;
                                            description
                                                "The number of uncolored packets,
                                                 as determined by the SAP ingress QoS
                                                 policy, offered by the packet processor to the
                                                 traffic manager.";
                                        }

                                        leaf uncolor-offered-octets {
                                            type yang:counter64;
                                            description
                                                "The number of uncolored octets,
                                                 as determined by the SAP ingress QoS
                                                 policy, offered by the packet processor to the
                                                 traffic manager.";
                                        }

                                        leaf managed-offered-packets {
                                            type yang:counter64;
                                            description
                                                "The value of managed-offered indicates
                                                 number of managed multicast packets, as determined by the SAP
                                                 ingress QoS policy, offered by the packet processor to the traffic manager.";
                                        }

                                        leaf managed-offered-octets {
                                            type yang:counter64;
                                            description
                                                "The value of managed-offered indicates
                                                 number of managed multicast octets, as determined by the SAP
                                                 ingress QoS policy, offered by the packet processor to the traffic manager.";
                                        }

                                        leaf aggregate-offered-packets {
                                            type yang:counter64;
                                            description
                                                "The value of aggregate-offered indicates aggregate
                                                 number of hi, lo priority and uncolour packets,
                                                 as determined by the SAP ingress QoS policy,
                                                 offered by the packet processor to the traffic manager.";
                                        }

                                        leaf aggregate-offered-octets {
                                            type yang:counter64;
                                            description
                                                "The value of managed-offered indicates aggregate
                                                 number of hi, lo priority and uncolour octets,
                                                 as determined by the SAP ingress QoS policy,
                                                 offered by the packet processor to the traffic manager.";
                                        }

                                        leaf last-cleared-time {
                                            type yang:date-and-time;
                                            description "Time when the counters in this table were last cleared.";
                                        }

                                    } // container statistics

                                } // container forwarding-engine

                                container traffic-manager {
                                    description "Enter the traffic-manager context";

                                    container statistics {
                                        description "Enter the statistics context";

                                        leaf cpm-packets {
                                            type yang:counter64;
                                            description
                                                "The value of cpm-packets indicates
                                                 ingress traffic in terms of packets destined to CPM
                                                 associated with this SAP.";
                                        }

                                        leaf cpm-octets {
                                            type yang:counter64;
                                            description
                                                "The value of cpm indicates
                                                 ingress traffic in terms of bytes destined to CPM
                                                 associated with this SAP.";
                                        }

                                        leaf high-priority-dropped-packets {
                                            type yang:counter64;
                                            description
                                                "The number of high priority packets,
                                                 as determined by the SAP ingress QoS
                                                 policy, dropped by the traffic manager due to:
                                                 MBS exceeded, buffer pool limit
                                                 exceeded, etc.";
                                        }

                                        leaf high-priority-dropped-octets {
                                            type yang:counter64;
                                            description
                                                "The number of high priority octets,
                                                 as determined by the SAP ingress QoS
                                                 policy, dropped by the traffic manager due to:
                                                 MBS exceeded, buffer pool limit
                                                 exceeded, etc.";
                                        }

                                        leaf low-priority-dropped-packets {
                                            type yang:counter64;
                                            description
                                                "The number of low priority packets,
                                                 as determined by the SAP ingress QoS
                                                 policy, dropped by the traffic manager due to:
                                                 MBS exceeded, buffer pool limit
                                                 exceeded, etc.";
                                        }

                                        leaf low-priority-dropped-octets {
                                            type yang:counter64;
                                            description
                                                "The number of low priority octets,
                                                 as determined by the SAP ingress QoS
                                                 policy, dropped by the traffic manager due to:
                                                 MBS exceeded, buffer pool limit
                                                 exceeded, etc.";
                                        }

                                        leaf in-profile-forwarded-packets {
                                            type yang:counter64;
                                            description
                                                "The number of in-profile packets
                                                 (rate below CIR) forwarded by the
                                                 ingress traffic manager.";
                                        }

                                        leaf in-profile-forwarded-octets {
                                            type yang:counter64;
                                            description
                                                "The number of in-profile octets
                                                 (rate below CIR) forwarded by the
                                                 ingress traffic manager.";
                                        }

                                        leaf out-profile-forwarded-packets {
                                            type yang:counter64;
                                            description
                                                "The number of out-of-profile packets
                                                 (rate above CIR) forwarded by the
                                                 ingress traffic manager.";
                                        }

                                        leaf out-profile-forwarded-octets {
                                            type yang:counter64;
                                            description
                                                "The number of out-of-profile octets
                                                 (rate above CIR) forwarded by the
                                                 ingress traffic manager.";
                                        }

                                        leaf aggregate-forwarded-packets {
                                            type yang:counter64;
                                            description
                                                "The aggregate number of in and out-of profile
                                                  packets forwarded by the ingress traffic manager.";
                                        }

                                        leaf aggregate-forwarded-octets {
                                            type yang:counter64;
                                            description
                                                "The aggregate number of in and out-of-profile
                                                 octets forwarded by the ingress traffic manager.";
                                        }

                                        leaf aggregate-dropped-packets {
                                            type yang:counter64;
                                            description
                                                "The aggregate number of in and out-of profile
                                                 packets, dropped by the traffic manager due to:
                                                 MBS exceeded, buffer pool limit
                                                 exceeded, etc.";
                                        }

                                        leaf aggregate-dropped-octets {
                                            type yang:counter64;
                                            description
                                                "The aggregate number of in and out-of profile
                                                 octets, dropped by the traffic manager due to:
                                                 MBS exceeded, buffer pool limit
                                                 exceeded, etc.";
                                        }

                                        leaf last-cleared-time {
                                            type yang:date-and-time;
                                            description "Time when the counters in this table were last cleared.";
                                        }

                                    } // container statistics

                                } // container traffic-manager

                                container qos-traffic {
                                    description "Enter the qos-traffic context";

                                    container statistics {
                                        description "Enter the statistics context";

                                        leaf ingress-packets {
                                            type yang:counter64;
                                            description "The number of ingress packets on this SAP.";
                                        }

                                        leaf ingress-octets {
                                            type yang:counter64;
                                            description "The number of ingress octets on this SAP.";
                                        }

                                    } // container statistics

                                } // container qos-traffic

                                list hardware-queue {
                                    key "hardware-queue-string";
                                    description "Enter the hardware-queue list instance";

                                    leaf hardware-queue-string {
                                        type types-sros:named-item-255;
                                        description "Name of the queue formatted by IOM.";
                                    }

                                    leaf dest-tap {
                                        type string;
                                        description "Destination TAP.";
                                    }

                                    leaf dest-fp {
                                        type uint32;
                                        description "Destination FP.";
                                    }

                                    leaf adapted-admin-mbs {
                                        type int64;
                                        units "bytes";
                                        description "Admin MBS.";
                                    }

                                    leaf adapted-admin-cbs {
                                        type types-qos:bytes;
                                        units "bytes";
                                        description "Admin CBS.";
                                    }

                                    leaf operational-mbs {
                                        type int64;
                                        units "bytes";
                                        description "Oper MBS.";
                                    }

                                    leaf depth {
                                        type union {
                                            type enumeration {
                                                enum "max"                          { value -1; }
                                            }
                                            type int64;
                                        }
                                        description "Depth CIR.";
                                    }

                                    leaf operational-cir {
                                        type union {
                                            type enumeration {
                                                enum "max"                          { value -1; }
                                            }
                                            type int64;
                                        }
                                        description "Oper CIR.";
                                    }

                                    leaf operational-fir {
                                        type union {
                                            type enumeration {
                                                enum "max"                          { value -1; }
                                            }
                                            type int64;
                                        }
                                        description "Oper FIR.";
                                    }

                                    leaf operational-pir {
                                        type union {
                                            type enumeration {
                                                enum "max"                          { value -1; }
                                            }
                                            type int64;
                                        }
                                        description "Oper PIR.";
                                    }

                                    leaf exceed-droptail {
                                        type union {
                                            type int64 {
                                                range "0..max";
                                            }
                                            type enumeration {
                                                enum "auto"                         { value -1; }
                                            }
                                        }
                                        description "Exceed droptail.";
                                    }

                                    leaf high-droptail {
                                        type union {
                                            type int64 {
                                                range "0..max";
                                            }
                                            type enumeration {
                                                enum "auto"                         { value -1; }
                                            }
                                        }
                                        description "High droptail.";
                                    }

                                    leaf highplus-droptail {
                                        type union {
                                            type int64 {
                                                range "0..max";
                                            }
                                            type enumeration {
                                                enum "auto"                         { value -1; }
                                            }
                                        }
                                        description "Highplus droptail.";
                                    }

                                    leaf low-droptail {
                                        type union {
                                            type int64 {
                                                range "0..max";
                                            }
                                            type enumeration {
                                                enum "auto"                         { value -1; }
                                            }
                                        }
                                        description "Low droptail.";
                                    }

                                } // list hardware-queue

                                list queue {
                                    key "queue-id";
                                    description "Enter the queue list instance";

                                    leaf queue-id {
                                        type types-qos:ingress-queue-id;
                                        description "The unique identifier for the queue.";
                                    }

                                    container statistics {
                                        description "Enter the statistics context";

                                        choice stat-mode {
                                            case unicast-priority {

                                                container unicast-priority {
                                                    description "Enter the unicast-priority context";

                                                    leaf high-priority-offered-packets {
                                                        type yang:counter64;
                                                        description "The number of high-priority packets offered by packet processor to traffic manager.";
                                                    }

                                                    leaf high-priority-offered-octets {
                                                        type yang:counter64;
                                                        description "The number of high-priority octets offered by packet processor to traffic manager.";
                                                    }

                                                    leaf low-priority-offered-packets {
                                                        type yang:counter64;
                                                        description "The number of low-priority packets offered by packet processor to traffic manager.";
                                                    }

                                                    leaf low-priority-offered-octets {
                                                        type yang:counter64;
                                                        description "The number of low-priority octets offered by packet processor to traffic manager.";
                                                    }

                                                    leaf high-priority-dropped-packets {
                                                        type yang:counter64;
                                                        description "The number of high-priority packets dropped by packet processor to traffic manager.";
                                                    }

                                                    leaf high-priority-dropped-octets {
                                                        type yang:counter64;
                                                        description "The number of high-priority octets dropped by packet processor to traffic manager.";
                                                    }

                                                    leaf low-priority-dropped-packets {
                                                        type yang:counter64;
                                                        description "The number of low-priority packets dropped by packet processor to traffic manager.";
                                                    }

                                                    leaf low-priority-dropped-octets {
                                                        type yang:counter64;
                                                        description "The number of low-priority octets dropped by packet processor to traffic manager.";
                                                    }

                                                    leaf in-profile-forwarded-packets {
                                                        type yang:counter64;
                                                        description "The number of in-profile packets (rate below CIR) forwarded.";
                                                    }

                                                    leaf in-profile-forwarded-octets {
                                                        type yang:counter64;
                                                        description "The number of in-profile octets (rate below CIR) forwarded.";
                                                    }

                                                    leaf out-profile-forwarded-packets {
                                                        type yang:counter64;
                                                        description "The number of out-of-profile packets (rate below CIR) forwarded.";
                                                    }

                                                    leaf out-profile-forwarded-octets {
                                                        type yang:counter64;
                                                        description "The number of out-of-profile octets (rate below CIR) forwarded.";
                                                    }

                                                } // container unicast-priority

                                            }
                                            case unicast-profile {

                                                container unicast-profile {
                                                    description "Enter the unicast-profile context";

                                                    leaf color-in-offered-packets {
                                                        type yang:counter64;
                                                        description "The number of color-in packets offered to traffic manager.";
                                                    }

                                                    leaf color-in-offered-octets {
                                                        type yang:counter64;
                                                        description "The number of color-in octets offered to traffic manager.";
                                                    }

                                                    leaf color-out-offered-packets {
                                                        type yang:counter64;
                                                        description "The number of color-out packets offered to traffic manager.";
                                                    }

                                                    leaf color-out-offered-octets {
                                                        type yang:counter64;
                                                        description "The number of color-out octets offered to traffic manager.";
                                                    }

                                                    leaf color-offered-packets {
                                                        type yang:counter64;
                                                        description "The number of color packets offered to traffic manager.";
                                                    }

                                                    leaf color-offered-octets {
                                                        type yang:counter64;
                                                        description "The number of color octets offered to traffic manager.";
                                                    }

                                                    leaf uncolor-offered-packets {
                                                        type yang:counter64;
                                                        description "The number of uncolor packets offered to traffic manager.";
                                                    }

                                                    leaf uncolor-offered-octets {
                                                        type yang:counter64;
                                                        description "The number of uncolor octets offered to traffic manager.";
                                                    }

                                                    leaf color-out-dropped-packets {
                                                        type yang:counter64;
                                                        description "The number of color-out packets dropped.";
                                                    }

                                                    leaf color-out-dropped-octets {
                                                        type yang:counter64;
                                                        description "The number of color-out octets dropped.";
                                                    }

                                                    leaf color-in-uncolor-dropped-packets {
                                                        type yang:counter64;
                                                        description "The number of color-in/uncolor packets dropped.";
                                                    }

                                                    leaf color-in-uncolor-dropped-octets {
                                                        type yang:counter64;
                                                        description "The number of color-in/uncolor octets dropped.";
                                                    }

                                                    leaf in-profile-forwarded-packets {
                                                        type yang:counter64;
                                                        description "The number of in-profile packets (rate below CIR) forwarded.";
                                                    }

                                                    leaf in-profile-forwarded-octets {
                                                        type yang:counter64;
                                                        description "The number of in-profile octets (rate below CIR) forwarded.";
                                                    }

                                                    leaf out-profile-forwarded-packets {
                                                        type yang:counter64;
                                                        description "The number of out-of-profile packets (rate below CIR) forwarded.";
                                                    }

                                                    leaf out-profile-forwarded-octets {
                                                        type yang:counter64;
                                                        description "The number of out-of-profile octets (rate below CIR) forwarded.";
                                                    }

                                                } // container unicast-profile

                                            }
                                            case multipoint-priority {

                                                container multipoint-priority {
                                                    description "Enter the multipoint-priority context";

                                                    leaf high-priority-offered-packets {
                                                        type yang:counter64;
                                                        description "The number of high-priority packets offered by packet processor to traffic manager.";
                                                    }

                                                    leaf high-priority-offered-octets {
                                                        type yang:counter64;
                                                        description "The number of high-priority octets offered by packet processor to traffic manager.";
                                                    }

                                                    leaf low-priority-offered-packets {
                                                        type yang:counter64;
                                                        description "The number of low-priority packets offered by packet processor to traffic manager.";
                                                    }

                                                    leaf low-priority-offered-octets {
                                                        type yang:counter64;
                                                        description "The number of low-priority octets offered by packet processor to traffic manager.";
                                                    }

                                                    leaf combined-offered-packets {
                                                        type yang:counter64;
                                                        description "The number of combined high and low priority packets offered by packet processor to traffic manager.";
                                                    }

                                                    leaf combined-offered-octets {
                                                        type yang:counter64;
                                                        description "The number of combined high and low priority octets offered by packet processor to traffic manager.";
                                                    }

                                                    leaf managed-offered-packets {
                                                        type yang:counter64;
                                                        description "The number of managed packets offered by packet processor to traffic manager.";
                                                    }

                                                    leaf managed-offered-octets {
                                                        type yang:counter64;
                                                        description "The number of managed octets offered by packet processor to traffic manager.";
                                                    }

                                                    leaf high-priority-dropped-packets {
                                                        type yang:counter64;
                                                        description "The number of high-priority packets dropped by packet processor to traffic manager.";
                                                    }

                                                    leaf high-priority-dropped-octets {
                                                        type yang:counter64;
                                                        description "The number of high-priority octets dropped by packet processor to traffic manager.";
                                                    }

                                                    leaf low-priority-dropped-packets {
                                                        type yang:counter64;
                                                        description "The number of low-priority packets dropped by packet processor to traffic manager.";
                                                    }

                                                    leaf low-priority-dropped-octets {
                                                        type yang:counter64;
                                                        description "The number of low-priority octets dropped by packet processor to traffic manager.";
                                                    }

                                                    leaf in-profile-forwarded-packets {
                                                        type yang:counter64;
                                                        description "The number of in-profile packets (rate below CIR) forwarded.";
                                                    }

                                                    leaf in-profile-forwarded-octets {
                                                        type yang:counter64;
                                                        description "The number of in-profile octets (rate below CIR) forwarded.";
                                                    }

                                                    leaf out-profile-forwarded-packets {
                                                        type yang:counter64;
                                                        description "The number of out-of-profile packets (rate below CIR) forwarded.";
                                                    }

                                                    leaf out-profile-forwarded-octets {
                                                        type yang:counter64;
                                                        description "The number of out-of-profile octets (rate below CIR) forwarded.";
                                                    }

                                                } // container multipoint-priority

                                            }
                                            case multipoint-profile {

                                                container multipoint-profile {
                                                    description "Enter the multipoint-profile context";

                                                    leaf color-in-offered-packets {
                                                        type yang:counter64;
                                                        description "The number of color-in packets offered to traffic manager.";
                                                    }

                                                    leaf color-in-offered-octets {
                                                        type yang:counter64;
                                                        description "The number of color-in octets offered to traffic manager.";
                                                    }

                                                    leaf color-out-offered-packets {
                                                        type yang:counter64;
                                                        description "The number of color-out packets offered to traffic manager.";
                                                    }

                                                    leaf color-out-offered-octets {
                                                        type yang:counter64;
                                                        description "The number of color-out octets offered to traffic manager.";
                                                    }

                                                    leaf uncolor-offered-packets {
                                                        type yang:counter64;
                                                        description "The number of uncolor packets offered to traffic manager.";
                                                    }

                                                    leaf uncolor-offered-octets {
                                                        type yang:counter64;
                                                        description "The number of uncolor octets offered to traffic manager.";
                                                    }

                                                    leaf combined-offered-packets {
                                                        type yang:counter64;
                                                        description "The number of combined colored in, out and uncolored packets offered to traffic manager.";
                                                    }

                                                    leaf combined-offered-octets {
                                                        type yang:counter64;
                                                        description "The number of combined colored in, out and uncolored octets offered to traffic manager.";
                                                    }

                                                    leaf managed-offered-packets {
                                                        type yang:counter64;
                                                        description "The number of managed packets offered by packet processor to traffic manager.";
                                                    }

                                                    leaf managed-offered-octets {
                                                        type yang:counter64;
                                                        description "The number of managed octets offered by packet processor to traffic manager.";
                                                    }

                                                    leaf color-out-dropped-packets {
                                                        type yang:counter64;
                                                        description "The number of color-out packets dropped.";
                                                    }

                                                    leaf color-out-dropped-octets {
                                                        type yang:counter64;
                                                        description "The number of color-out octets dropped.";
                                                    }

                                                    leaf color-in-uncolor-dropped-packets {
                                                        type yang:counter64;
                                                        description "The number of color-in/uncolor packets dropped.";
                                                    }

                                                    leaf color-in-uncolor-dropped-octets {
                                                        type yang:counter64;
                                                        description "The number of color-in/uncolor octets dropped.";
                                                    }

                                                    leaf in-profile-forwarded-packets {
                                                        type yang:counter64;
                                                        description "The number of in-profile packets (rate below CIR) forwarded.";
                                                    }

                                                    leaf in-profile-forwarded-octets {
                                                        type yang:counter64;
                                                        description "The number of in-profile octets (rate below CIR) forwarded.";
                                                    }

                                                    leaf out-profile-forwarded-packets {
                                                        type yang:counter64;
                                                        description "The number of out-of-profile packets (rate below CIR) forwarded.";
                                                    }

                                                    leaf out-profile-forwarded-octets {
                                                        type yang:counter64;
                                                        description "The number of out-of-profile octets (rate below CIR) forwarded.";
                                                    }

                                                } // container multipoint-profile

                                            }
                                            case v4-v6 {

                                                container v4-v6 {
                                                    description "Enter the v4-v6 context";

                                                    leaf ipv4-offered-packets {
                                                        type yang:counter64;
                                                        description "The number of ipv4 packets offered by packet processor to traffic manager.";
                                                    }

                                                    leaf ipv4-offered-octets {
                                                        type yang:counter64;
                                                        description "The number of ipv4 octets offered by packet processor to traffic manager.";
                                                    }

                                                    leaf ipv6-offered-packets {
                                                        type yang:counter64;
                                                        description "The number of ipv6 packets offered by packet processor to traffic manager.";
                                                    }

                                                    leaf ipv6-offered-octets {
                                                        type yang:counter64;
                                                        description "The number of ipv6 octets offered by packet processor to traffic manager.";
                                                    }

                                                    leaf ipv4-dropped-packets {
                                                        type yang:counter64;
                                                        description "The number of ipv4 packets dropped by packet processor to traffic manager.";
                                                    }

                                                    leaf ipv4-dropped-octets {
                                                        type yang:counter64;
                                                        description "The number of ipv4 octets dropped by packet processor to traffic manager.";
                                                    }

                                                    leaf ipv6-dropped-packets {
                                                        type yang:counter64;
                                                        description "The number of ipv6 packets dropped by packet processor to traffic manager.";
                                                    }

                                                    leaf ipv6-dropped-octets {
                                                        type yang:counter64;
                                                        description "The number of ipv6 octets dropped by packet processor to traffic manager.";
                                                    }

                                                    leaf ipv4-forwarded-packets {
                                                        type yang:counter64;
                                                        description "The number of ipv4 packets forwarded.";
                                                    }

                                                    leaf ipv4-forwarded-octets {
                                                        type yang:counter64;
                                                        description "The number of ipv4 octets forwarded.";
                                                    }

                                                    leaf ipv6-forwarded-packets {
                                                        type yang:counter64;
                                                        description "The number of ipv6 packets forwarded.";
                                                    }

                                                    leaf ipv6-forwarded-octets {
                                                        type yang:counter64;
                                                        description "The number of ipv6 octets forwarded.";
                                                    }

                                                } // container v4-v6

                                            }
                                        }
                                    } // container statistics

                                    container queue-depth {
                                        description "Enter the queue-depth context";

                                        leaf elapsed-time {
                                            type types-sros:time-interval;
                                            description "Indicated the elapsed time.";
                                        }

                                        leaf depth-0-to-10-percent {
                                            type decimal64 {
                                                fraction-digits 2;
                                            }
                                            description "Indicated the depth 0 to 10 percent.";
                                        }

                                        leaf depth-11-to-20-percent {
                                            type decimal64 {
                                                fraction-digits 2;
                                            }
                                            description "Indicated the depth 0 to 20 percent.";
                                        }

                                        leaf depth-21-to-30-percent {
                                            type decimal64 {
                                                fraction-digits 2;
                                            }
                                            description "Indicated the depth 0 to 30 percent.";
                                        }

                                        leaf depth-31-to-40-percent {
                                            type decimal64 {
                                                fraction-digits 2;
                                            }
                                            description "Indicated the depth 0 to 40 percent.";
                                        }

                                        leaf depth-41-to-50-percent {
                                            type decimal64 {
                                                fraction-digits 2;
                                            }
                                            description "Indicated the depth 0 to 50 percent.";
                                        }

                                        leaf depth-51-to-60-percent {
                                            type decimal64 {
                                                fraction-digits 2;
                                            }
                                            description "Indicated the depth 0 to 60 percent.";
                                        }

                                        leaf depth-61-to-70-percent {
                                            type decimal64 {
                                                fraction-digits 2;
                                            }
                                            description "Indicated the depth 0 to 70 percent.";
                                        }

                                        leaf depth-71-to-80-percent {
                                            type decimal64 {
                                                fraction-digits 2;
                                            }
                                            description "Indicated the depth 0 to 80 percent.";
                                        }

                                        leaf depth-81-to-90-percent {
                                            type decimal64 {
                                                fraction-digits 2;
                                            }
                                            description "Indicated the depth 0 to 90 percent.";
                                        }

                                        leaf depth-91-to-100-percent {
                                            type decimal64 {
                                                fraction-digits 2;
                                            }
                                            description "Indicated the depth 0 to 100 percent.";
                                        }

                                        leaf queue-polling-interval {
                                            type types-sros:time-interval;
                                            description "Indicates the queue polling interval.";
                                        }

                                    } // container queue-depth

                                } // list queue

                                list policer {
                                    key "policer-id";
                                    description "Enter the policer list instance";

                                    leaf policer-id {
                                        type types-qos:ingress-policer-id;
                                        description "The unique identifier for the policer.";
                                    }

                                    container statistics {
                                        description "Enter the statistics context";

                                        choice stat-mode {
                                            case minimal {

                                                container minimal {
                                                    description "Enter the minimal context";

                                                    leaf all-offered-packets {
                                                        type yang:counter64;
                                                        description "The number of all the priority packets offered by the packet processor to traffic manager";
                                                    }

                                                    leaf all-offered-octets {
                                                        type yang:counter64;
                                                        description "The number of all the priority octets offered by the packet processor to traffic manager";
                                                    }

                                                    leaf all-dropped-packets {
                                                        type yang:counter64;
                                                        description "The number of all the priority packets dropped by the packet processor to traffic manager";
                                                    }

                                                    leaf all-dropped-octets {
                                                        type yang:counter64;
                                                        description "The number of all the priority octets dropped by the packet processor to traffic manager";
                                                    }

                                                    leaf all-forwarded-packets {
                                                        type yang:counter64;
                                                        description "The number of all the priority packets forwarded by the packet processor to traffic manager";
                                                    }

                                                    leaf all-forwarded-octets {
                                                        type yang:counter64;
                                                        description "The number of all the priority octets forwarded by the packet processor to traffic manager";
                                                    }

                                                } // container minimal

                                            }
                                            case offered-profile-no-cir {

                                                container offered-profile-no-cir {
                                                    description "Enter the offered-profile-no-cir context";

                                                    leaf in-profile-offered-packets {
                                                        type yang:counter64;
                                                        description "The number of in-profile packets offered by the packet processor to traffic manager";
                                                    }

                                                    leaf in-profile-offered-octets {
                                                        type yang:counter64;
                                                        description "The number of in-profile octets offered by the packet processor to traffic manager";
                                                    }

                                                    leaf out-profile-offered-packets {
                                                        type yang:counter64;
                                                        description "The number of out-of-profile packets offered by the packet processor to traffic manager";
                                                    }

                                                    leaf out-profile-offered-octets {
                                                        type yang:counter64;
                                                        description "The number of out-of-profile octets offered by the packet processor to traffic manager";
                                                    }

                                                    leaf in-profile-dropped-packets {
                                                        type yang:counter64;
                                                        description "The number of in-profile packets dropped by the packet processor to traffic manager";
                                                    }

                                                    leaf in-profile-dropped-octets {
                                                        type yang:counter64;
                                                        description "The number of in-profile octets dropped by the packet processor to traffic manager";
                                                    }

                                                    leaf out-profile-dropped-packets {
                                                        type yang:counter64;
                                                        description "The number of out-of-profile packets dropped by the packet processor to traffic manager";
                                                    }

                                                    leaf out-profile-dropped-octets {
                                                        type yang:counter64;
                                                        description "The number of out-of-profile octets dropped by the packet processor to traffic manager";
                                                    }

                                                    leaf in-profile-forwarded-packets {
                                                        type yang:counter64;
                                                        description "The number of in-profile packets forwarded by the packet processor to traffic manager";
                                                    }

                                                    leaf in-profile-forwarded-octets {
                                                        type yang:counter64;
                                                        description "The number of in-profile octets forwarded by the packet processor to traffic manager";
                                                    }

                                                    leaf out-profile-forwarded-packets {
                                                        type yang:counter64;
                                                        description "The number of out-of-profile packets forwarded by the packet processor to traffic manager";
                                                    }

                                                    leaf out-profile-forwarded-octets {
                                                        type yang:counter64;
                                                        description "The number of out-of-profile octets forwarded by the packet processor to traffic manager";
                                                    }

                                                } // container offered-profile-no-cir

                                            }
                                            case offered-priority-no-cir {

                                                container offered-priority-no-cir {
                                                    description "Enter the offered-priority-no-cir context";

                                                    leaf high-priority-offered-packets {
                                                        type yang:counter64;
                                                        description "The number of high-priority packets offered by the packet processor to traffic manager";
                                                    }

                                                    leaf high-priority-offered-octets {
                                                        type yang:counter64;
                                                        description "The number of high-priority octets offered by the packet processor to traffic manager";
                                                    }

                                                    leaf low-priority-offered-packets {
                                                        type yang:counter64;
                                                        description "The number of low-priority packets offered by the packet processor to traffic manager";
                                                    }

                                                    leaf low-priority-offered-octets {
                                                        type yang:counter64;
                                                        description "The number of low-priority octets offered by the packet processor to traffic manager";
                                                    }

                                                    leaf high-priority-dropped-packets {
                                                        type yang:counter64;
                                                        description "The number of high-priority packets dropped by the packet processor to traffic manager";
                                                    }

                                                    leaf high-priority-dropped-octets {
                                                        type yang:counter64;
                                                        description "The number of high-priority octets dropped by the packet processor to traffic manager";
                                                    }

                                                    leaf low-priority-dropped-packets {
                                                        type yang:counter64;
                                                        description "The number of low-priority packets dropped by the packet processor to traffic manager";
                                                    }

                                                    leaf low-priority-dropped-octets {
                                                        type yang:counter64;
                                                        description "The number of low-priority octets dropped by the packet processor to traffic manager";
                                                    }

                                                    leaf high-priority-forwarded-packets {
                                                        type yang:counter64;
                                                        description "The number of high-priority packets forwarded by the packet processor to traffic manager";
                                                    }

                                                    leaf high-priority-forwarded-octets {
                                                        type yang:counter64;
                                                        description "The number of high-priority octets forwarded by the packet processor to traffic manager";
                                                    }

                                                    leaf low-priority-forwarded-packets {
                                                        type yang:counter64;
                                                        description "The number of low-priority packets forwarded by the packet processor to traffic manager";
                                                    }

                                                    leaf low-priority-forwarded-octets {
                                                        type yang:counter64;
                                                        description "The number of low-priority octets forwarded by the packet processor to traffic manager";
                                                    }

                                                } // container offered-priority-no-cir

                                            }
                                            case offered-profile-cir {

                                                container offered-profile-cir {
                                                    description "Enter the offered-profile-cir context";

                                                    leaf in-profile-offered-packets {
                                                        type yang:counter64;
                                                        description "The number of in-profile packets offered by the packet processor to traffic manager";
                                                    }

                                                    leaf in-profile-offered-octets {
                                                        type yang:counter64;
                                                        description "The number of in-profile octets offered by the packet processor to traffic manager";
                                                    }

                                                    leaf out-profile-offered-packets {
                                                        type yang:counter64;
                                                        description "The number of out-of-profile packets offered by the packet processor to traffic manager";
                                                    }

                                                    leaf out-profile-offered-octets {
                                                        type yang:counter64;
                                                        description "The number of out-of-profile octets offered by the packet processor to traffic manager";
                                                    }

                                                    leaf uncolor-offered-packets {
                                                        type yang:counter64;
                                                        description "The number of uncolor packets offered by the packet processor to traffic manager";
                                                    }

                                                    leaf uncolor-offered-octets {
                                                        type yang:counter64;
                                                        description "The number of uncolor octets offered by the packet processor to traffic manager";
                                                    }

                                                    leaf in-profile-dropped-packets {
                                                        type yang:counter64;
                                                        description "The number of in-profile packets dropped by the packet processor to traffic manager";
                                                    }

                                                    leaf in-profile-dropped-octets {
                                                        type yang:counter64;
                                                        description "The number of in-profile octets dropped by the packet processor to traffic manager";
                                                    }

                                                    leaf out-profile-dropped-packets {
                                                        type yang:counter64;
                                                        description "The number of out-of-profile packets dropped by the packet processor to traffic manager";
                                                    }

                                                    leaf out-profile-dropped-octets {
                                                        type yang:counter64;
                                                        description "The number of out-of-profile octets dropped by the packet processor to traffic manager";
                                                    }

                                                    leaf in-profile-forwarded-packets {
                                                        type yang:counter64;
                                                        description "The number of in-profile packets forwarded by the packet processor to traffic manager";
                                                    }

                                                    leaf in-profile-forwarded-octets {
                                                        type yang:counter64;
                                                        description "The number of in-profile octets forwarded by the packet processor to traffic manager";
                                                    }

                                                    leaf out-profile-forwarded-packets {
                                                        type yang:counter64;
                                                        description "The number of out-of-profile packets forwarded by the packet processor to traffic manager";
                                                    }

                                                    leaf out-profile-forwarded-octets {
                                                        type yang:counter64;
                                                        description "The number of out-of-profile octets forwarded by the packet processor to traffic manager";
                                                    }

                                                } // container offered-profile-cir

                                            }
                                            case offered-priority-cir {

                                                container offered-priority-cir {
                                                    description "Enter the offered-priority-cir context";

                                                    leaf high-priority-offered-packets {
                                                        type yang:counter64;
                                                        description "The number of high-priority packets offered by the packet processor to traffic manager";
                                                    }

                                                    leaf high-priority-offered-octets {
                                                        type yang:counter64;
                                                        description "The number of high-priority octets offered by the packet processor to traffic manager";
                                                    }

                                                    leaf low-priority-offered-packets {
                                                        type yang:counter64;
                                                        description "The number of low-priority packets offered by the packet processor to traffic manager";
                                                    }

                                                    leaf low-priority-offered-octets {
                                                        type yang:counter64;
                                                        description "The number of low-priority octets offered by the packet processor to traffic manager";
                                                    }

                                                    leaf in-profile-dropped-packets {
                                                        type yang:counter64;
                                                        description "The number of in-profile packets dropped by the packet processor to traffic manager";
                                                    }

                                                    leaf in-profile-dropped-octets {
                                                        type yang:counter64;
                                                        description "The number of in-profile octets dropped by the packet processor to traffic manager";
                                                    }

                                                    leaf out-profile-dropped-packets {
                                                        type yang:counter64;
                                                        description "The number of out-of-profile packets dropped by the packet processor to traffic manager";
                                                    }

                                                    leaf out-profile-dropped-octets {
                                                        type yang:counter64;
                                                        description "The number of out-of-profile octets dropped by the packet processor to traffic manager";
                                                    }

                                                    leaf in-profile-forwarded-packets {
                                                        type yang:counter64;
                                                        description "The number of in-profile packets forwarded by the packet processor to traffic manager";
                                                    }

                                                    leaf in-profile-forwarded-octets {
                                                        type yang:counter64;
                                                        description "The number of in-profile octets forwarded by the packet processor to traffic manager";
                                                    }

                                                    leaf out-profile-forwarded-packets {
                                                        type yang:counter64;
                                                        description "The number of out-of-profile packets forwarded by the packet processor to traffic manager";
                                                    }

                                                    leaf out-profile-forwarded-octets {
                                                        type yang:counter64;
                                                        description "The number of out-of-profile octets forwarded by the packet processor to traffic manager";
                                                    }

                                                } // container offered-priority-cir

                                            }
                                            case offered-total-cir {

                                                container offered-total-cir {
                                                    description "Enter the offered-total-cir context";

                                                    leaf all-offered-packets {
                                                        type yang:counter64;
                                                        description "The number of all the priority packets offered by the packet processor to traffic manager";
                                                    }

                                                    leaf all-offered-octets {
                                                        type yang:counter64;
                                                        description "The number of all the priority octets offered by the packet processor to traffic manager";
                                                    }

                                                    leaf in-profile-dropped-packets {
                                                        type yang:counter64;
                                                        description "The number of in-profile packets dropped by the packet processor to traffic manager";
                                                    }

                                                    leaf in-profile-dropped-octets {
                                                        type yang:counter64;
                                                        description "The number of in-profile octets dropped by the packet processor to traffic manager";
                                                    }

                                                    leaf out-profile-dropped-packets {
                                                        type yang:counter64;
                                                        description "The number of out-of-profile packets dropped by the packet processor to traffic manager";
                                                    }

                                                    leaf out-profile-dropped-octets {
                                                        type yang:counter64;
                                                        description "The number of out-of-profile octets dropped by the packet processor to traffic manager";
                                                    }

                                                    leaf in-profile-forwarded-packets {
                                                        type yang:counter64;
                                                        description "The number of in-profile packets forwarded by the packet processor to traffic manager";
                                                    }

                                                    leaf in-profile-forwarded-octets {
                                                        type yang:counter64;
                                                        description "The number of in-profile octets forwarded by the packet processor to traffic manager";
                                                    }

                                                    leaf out-profile-forwarded-packets {
                                                        type yang:counter64;
                                                        description "The number of out-of-profile packets forwarded by the packet processor to traffic manager";
                                                    }

                                                    leaf out-profile-forwarded-octets {
                                                        type yang:counter64;
                                                        description "The number of out-of-profile octets forwarded by the packet processor to traffic manager";
                                                    }

                                                } // container offered-total-cir

                                            }
                                            case offered-limited-profile-cir {

                                                container offered-limited-profile-cir {
                                                    description "Enter the offered-limited-profile-cir context";

                                                    leaf out-profile-offered-packets {
                                                        type yang:counter64;
                                                        description "The number of out-of-profile packets offered by the packet processor to traffic manager";
                                                    }

                                                    leaf out-profile-offered-octets {
                                                        type yang:counter64;
                                                        description "The number of out-of-profile octets offered by the packet processor to traffic manager";
                                                    }

                                                    leaf uncolor-offered-packets {
                                                        type yang:counter64;
                                                        description "The number of uncolor packets offered by the packet processor to traffic manager";
                                                    }

                                                    leaf uncolor-offered-octets {
                                                        type yang:counter64;
                                                        description "The number of uncolor octets offered by the packet processor to traffic manager";
                                                    }

                                                    leaf in-profile-dropped-packets {
                                                        type yang:counter64;
                                                        description "The number of in-profile packets dropped by the packet processor to traffic manager";
                                                    }

                                                    leaf in-profile-dropped-octets {
                                                        type yang:counter64;
                                                        description "The number of in-profile octets dropped by the packet processor to traffic manager";
                                                    }

                                                    leaf out-profile-dropped-packets {
                                                        type yang:counter64;
                                                        description "The number of out-of-profile packets dropped by the packet processor to traffic manager";
                                                    }

                                                    leaf out-profile-dropped-octets {
                                                        type yang:counter64;
                                                        description "The number of out-of-profile octets dropped by the packet processor to traffic manager";
                                                    }

                                                    leaf in-profile-forwarded-packets {
                                                        type yang:counter64;
                                                        description "The number of in-profile packets forwarded by the packet processor to traffic manager";
                                                    }

                                                    leaf in-profile-forwarded-octets {
                                                        type yang:counter64;
                                                        description "The number of in-profile octets forwarded by the packet processor to traffic manager";
                                                    }

                                                    leaf out-profile-forwarded-packets {
                                                        type yang:counter64;
                                                        description "The number of out-of-profile packets forwarded by the packet processor to traffic manager";
                                                    }

                                                    leaf out-profile-forwarded-octets {
                                                        type yang:counter64;
                                                        description "The number of out-of-profile octets forwarded by the packet processor to traffic manager";
                                                    }

                                                } // container offered-limited-profile-cir

                                            }
                                            case offered-profile-capped-cir {

                                                container offered-profile-capped-cir {
                                                    description "Enter the offered-profile-capped-cir context";

                                                    leaf in-profile-offered-packets {
                                                        type yang:counter64;
                                                        description "The number of in-profile packets offered by the packet processor to traffic manager";
                                                    }

                                                    leaf in-profile-offered-octets {
                                                        type yang:counter64;
                                                        description "The number of in-profile octets offered by the packet processor to traffic manager";
                                                    }

                                                    leaf out-profile-offered-packets {
                                                        type yang:counter64;
                                                        description "The number of out-of-profile packets offered by the packet processor to traffic manager";
                                                    }

                                                    leaf out-profile-offered-octets {
                                                        type yang:counter64;
                                                        description "The number of out-of-profile octets offered by the packet processor to traffic manager";
                                                    }

                                                    leaf uncolor-offered-packets {
                                                        type yang:counter64;
                                                        description "The number of uncolor packets offered by the packet processor to traffic manager";
                                                    }

                                                    leaf uncolor-offered-octets {
                                                        type yang:counter64;
                                                        description "The number of uncolor octets offered by the packet processor to traffic manager";
                                                    }

                                                    leaf in-profile-dropped-packets {
                                                        type yang:counter64;
                                                        description "The number of in-profile packets dropped by the packet processor to traffic manager";
                                                    }

                                                    leaf in-profile-dropped-octets {
                                                        type yang:counter64;
                                                        description "The number of in-profile octets dropped by the packet processor to traffic manager";
                                                    }

                                                    leaf out-profile-dropped-packets {
                                                        type yang:counter64;
                                                        description "The number of out-of-profile packets dropped by the packet processor to traffic manager";
                                                    }

                                                    leaf out-profile-dropped-octets {
                                                        type yang:counter64;
                                                        description "The number of out-of-profile octets dropped by the packet processor to traffic manager";
                                                    }

                                                    leaf in-profile-forwarded-packets {
                                                        type yang:counter64;
                                                        description "The number of in-profile packets forwarded by the packet processor to traffic manager";
                                                    }

                                                    leaf in-profile-forwarded-octets {
                                                        type yang:counter64;
                                                        description "The number of in-profile octets forwarded by the packet processor to traffic manager";
                                                    }

                                                    leaf out-profile-forwarded-packets {
                                                        type yang:counter64;
                                                        description "The number of out-of-profile packets forwarded by the packet processor to traffic manager";
                                                    }

                                                    leaf out-profile-forwarded-octets {
                                                        type yang:counter64;
                                                        description "The number of out-of-profile octets forwarded by the packet processor to traffic manager";
                                                    }

                                                } // container offered-profile-capped-cir

                                            }
                                            case offered-profile-with-discards {

                                                container offered-profile-with-discards {
                                                    description "Enter the offered-profile-with-discards context";

                                                    leaf in-profile-forwarded-packets {
                                                        type yang:counter64;
                                                        description "The number of in-profile packets forwarded by the packet processor to traffic manager";
                                                    }

                                                    leaf in-profile-forwarded-octets {
                                                        type yang:counter64;
                                                        description "The number of in-profile octets forwarded by the packet processor to traffic manager";
                                                    }

                                                    leaf out-profile-forwarded-packets {
                                                        type yang:counter64;
                                                        description "The number of out-profile packets forwarded by the packet processor to traffic manager";
                                                    }

                                                    leaf out-profile-forwarded-octets {
                                                        type yang:counter64;
                                                        description "The number of out-profile octets forwarded by the packet processor to traffic manager";
                                                    }

                                                    leaf dropped-exceed-profile-packets {
                                                        type yang:counter64;
                                                        description "The number of dropped-exceed-profile packets by the packet processor to traffic manager";
                                                    }

                                                    leaf dropped-exceed-profile-octets {
                                                        type yang:counter64;
                                                        description "The number of dropped-exceed-profile octets by the packet processor to traffic manager";
                                                    }

                                                } // container offered-profile-with-discards

                                            }
                                            case offered-limited-capped-cir {

                                                container offered-limited-capped-cir {
                                                    description "Enter the offered-limited-capped-cir context";

                                                    leaf in-profile-offered-packets {
                                                        type yang:counter64;
                                                        description "The number of in-profile packets offered by the packet processor to traffic manager";
                                                    }

                                                    leaf in-profile-offered-octets {
                                                        type yang:counter64;
                                                        description "The number of in-profile octets offered by the packet processor to traffic manager";
                                                    }

                                                    leaf in-profile-dropped-packets {
                                                        type yang:counter64;
                                                        description "The number of in-profile packets dropped by the packet processor to traffic manager";
                                                    }

                                                    leaf in-profile-dropped-octets {
                                                        type yang:counter64;
                                                        description "The number of in-profile octets dropped by the packet processor to traffic manager";
                                                    }

                                                    leaf out-profile-dropped-packets {
                                                        type yang:counter64;
                                                        description "The number of out-of-profile packets dropped by the packet processor to traffic manager";
                                                    }

                                                    leaf out-profile-dropped-octets {
                                                        type yang:counter64;
                                                        description "The number of out-of-profile octets dropped by the packet processor to traffic manager";
                                                    }

                                                    leaf in-profile-forwarded-packets {
                                                        type yang:counter64;
                                                        description "The number of in-profile packets forwarded by the packet processor to traffic manager";
                                                    }

                                                    leaf in-profile-forwarded-octets {
                                                        type yang:counter64;
                                                        description "The number of in-profile octets forwarded by the packet processor to traffic manager";
                                                    }

                                                    leaf out-profile-forwarded-packets {
                                                        type yang:counter64;
                                                        description "The number of out-of-profile packets forwarded by the packet processor to traffic manager";
                                                    }

                                                    leaf out-profile-forwarded-octets {
                                                        type yang:counter64;
                                                        description "The number of out-of-profile octets forwarded by the packet processor to traffic manager";
                                                    }

                                                    leaf uncolor-offered-packets {
                                                        type yang:counter64;
                                                        description "The number of out-of-rofile packets offered by the packet processor to traffic manager";
                                                    }

                                                    leaf uncolor-offered-octets {
                                                        type yang:counter64;
                                                        description "The number of out-of-profile octets offered by the packet processor to traffic manager";
                                                    }

                                                } // container offered-limited-capped-cir

                                            }
                                            case v4-v6 {

                                                container v4-v6 {
                                                    description "Enter the v4-v6 context";

                                                    leaf ipv4-offered-packets {
                                                        type yang:counter64;
                                                        description "The number of ipv4 packets offered by the packet processor to traffic manager";
                                                    }

                                                    leaf ipv4-offered-octets {
                                                        type yang:counter64;
                                                        description "The number of ipv4 octets offered by the packet processor to traffic manager";
                                                    }

                                                    leaf ipv6-offered-packets {
                                                        type yang:counter64;
                                                        description "The number of ipv6 packets offered by the packet processor to traffic manager";
                                                    }

                                                    leaf ipv6-offered-octets {
                                                        type yang:counter64;
                                                        description "The number of ipv6 octets offered by the packet processor to traffic manager";
                                                    }

                                                    leaf ipv4-dropped-packets {
                                                        type yang:counter64;
                                                        description "The number of ipv4 packets dropped by the packet processor to traffic manager";
                                                    }

                                                    leaf ipv4-dropped-octets {
                                                        type yang:counter64;
                                                        description "The number of ipv4 octets dropped by the packet processor to traffic manager";
                                                    }

                                                    leaf ipv6-dropped-packets {
                                                        type yang:counter64;
                                                        description "The number of ipv6 packets dropped by the packet processor to traffic manager";
                                                    }

                                                    leaf ipv6-dropped-octets {
                                                        type yang:counter64;
                                                        description "The number of ipv6 octets dropped by the packet processor to traffic manager";
                                                    }

                                                    leaf ipv4-forwarded-packets {
                                                        type yang:counter64;
                                                        description "The number of ipv4 packets forwarded by the packet processor to traffic manager";
                                                    }

                                                    leaf ipv4-forwarded-octets {
                                                        type yang:counter64;
                                                        description "The number of ipv4 octets forwarded by the packet processor to traffic manager";
                                                    }

                                                    leaf ipv6-forwarded-packets {
                                                        type yang:counter64;
                                                        description "The number of ipv6 packets forwarded by the packet processor to traffic manager";
                                                    }

                                                    leaf ipv6-forwarded-octets {
                                                        type yang:counter64;
                                                        description "The number of ipv6 octets forwarded by the packet processor to traffic manager";
                                                    }

                                                } // container v4-v6

                                            }
                                        }
                                    } // container statistics

                                    list hardware-policer {
                                        key "hardware-policer-string";
                                        description "Enter the hardware-policer list instance";

                                        leaf hardware-policer-string {
                                            type types-sros:named-item-255;
                                            description "Name of the policer formatted by IOM.";
                                        }

                                        leaf adapted-admin-cbs {
                                            type int64;
                                            units "bytes";
                                            description "Admin CBS.";
                                        }

                                        leaf adapted-admin-mbs {
                                            type int64;
                                            units "bytes";
                                            description "Admin MBS.";
                                        }

                                        leaf adapted-hp-only {
                                            type int64;
                                            units "bytes";
                                            description "Hi Prio Only.";
                                        }

                                        leaf depth {
                                            type int64;
                                            units "bytes";
                                            description "Depth.";
                                        }

                                        leaf operational-cir {
                                            type union {
                                                type enumeration {
                                                    enum "max"                          { value -1; }
                                                }
                                                type int64;
                                            }
                                            description "Oper CIR.";
                                        }

                                        leaf operational-fir {
                                            type union {
                                                type enumeration {
                                                    enum "max"                          { value -1; }
                                                }
                                                type int64;
                                            }
                                            description "Oper FIR.";
                                        }

                                        leaf operational-pir {
                                            type union {
                                                type enumeration {
                                                    enum "max"                          { value -1; }
                                                }
                                                type int64;
                                            }
                                            description "Oper PIR.";
                                        }

                                    } // list hardware-policer

                                } // list policer

                            } // container sap-ingress

                            container policer-control-policy {
                                description "Enter the policer-control-policy context";

                                list arbiter {
                                    key "arbiter-name";
                                    description "Enter the arbiter list instance";

                                    leaf arbiter-name {
                                        type types-sros:named-item;
                                        description "Specifies the arbiter name.";
                                    }

                                    container statistics {
                                        description "Enter the statistics context";

                                        leaf forwarded-packets {
                                            type yang:counter64;
                                            description "The number of forwarded packets.";
                                        }

                                        leaf forwarded-octets {
                                            type yang:counter64;
                                            description "The number of forwarded octets.";
                                        }

                                    } // container statistics

                                } // list arbiter

                            } // container policer-control-policy

                            container scheduler-policy {
                                description "Enter the scheduler-policy context";

                                list scheduler {
                                    key "scheduler-name";
                                    description "Enter the scheduler list instance";

                                    leaf scheduler-name {
                                        type types-sros:named-item;
                                        description "Specifies the scheduler name.";
                                    }

                                    container statistics {
                                        description "Enter the statistics context";

                                        leaf forwarded-packets {
                                            type yang:counter64;
                                            description "The number of forwarded packets.";
                                        }

                                        leaf forwarded-octets {
                                            type yang:counter64;
                                            description "The number of forwarded octets.";
                                        }

                                    } // container statistics

                                } // list scheduler

                            } // container scheduler-policy

                        } // container qos

                    } // container ingress

                    container egress {
                        description "Enter the egress context";

                        container vlan-qos {
                            description "Enter the vlan-qos context";

                            list queue {
                                key "queue-id";
                                description "Enter the queue list instance";

                                leaf queue-id {
                                    type types-qos:egress-queue-id;
                                    description "The unique identifier for the queue.";
                                }

                                container statistics {
                                    description "Enter the statistics context";

                                    choice stat-mode {
                                        case enqueued-with-discards {

                                            container enqueued-with-discards {
                                                description "Enter the enqueued-with-discards context";

                                                leaf forwarded-packets {
                                                    type yang:counter64;
                                                    description "The number of packets (rate below CIR) forwarded.";
                                                }

                                                leaf forwarded-octets {
                                                    type yang:counter64;
                                                    description "The number of octets (rate below CIR) forwarded.";
                                                }

                                                leaf dropped-packets {
                                                    type yang:counter64;
                                                    description "The number of packets discarded.";
                                                }

                                                leaf dropped-octets {
                                                    type yang:counter64;
                                                    description "The number of octets discarded.";
                                                }

                                            } // container enqueued-with-discards

                                        }
                                        case enqueued-4-profile-with-discards {

                                            container enqueued-4-profile-with-discards {
                                                description "Enter the enqueued-4-profile-with-discards context";

                                                leaf inplus-profile-forwarded-packets {
                                                    type yang:counter64;
                                                    description
                                                        "The number of in-plus-profile packets
                                                         (rate below CIR) forwarded.";
                                                }

                                                leaf inplus-profile-forwarded-octets {
                                                    type yang:counter64;
                                                    description
                                                        "The number of in-plus-profile octets
                                                         (rate below CIR) forwarded.";
                                                }

                                                leaf inplus-profile-dropped-packets {
                                                    type yang:counter64;
                                                    description
                                                        "The number of in-plus-profile packets
                                                         discarded.";
                                                }

                                                leaf inplus-profile-dropped-octets {
                                                    type yang:counter64;
                                                    description
                                                        "The number of in-plus-profile octets
                                                         discarded.";
                                                }

                                                leaf in-profile-forwarded-packets {
                                                    type yang:counter64;
                                                    description
                                                        "The number of in-profile packets
                                                         (rate below CIR) forwarded.";
                                                }

                                                leaf in-profile-forwarded-octets {
                                                    type yang:counter64;
                                                    description
                                                        "The number of in-profile octets
                                                         (rate below CIR) forwarded.";
                                                }

                                                leaf in-profile-dropped-packets {
                                                    type yang:counter64;
                                                    description
                                                        "The number of in-profile packets
                                                         discarded.";
                                                }

                                                leaf in-profile-dropped-octets {
                                                    type yang:counter64;
                                                    description
                                                        "The number of in-profile octets
                                                         discarded.";
                                                }

                                                leaf out-profile-forwarded-packets {
                                                    type yang:counter64;
                                                    description
                                                        "The number of out-profile packets
                                                         (rate below CIR) forwarded.";
                                                }

                                                leaf out-profile-forwarded-octets {
                                                    type yang:counter64;
                                                    description
                                                        "The number of out-profile octets
                                                         (rate below CIR) forwarded.";
                                                }

                                                leaf out-profile-dropped-packets {
                                                    type yang:counter64;
                                                    description
                                                        "The number of out-profile packets
                                                         discarded.";
                                                }

                                                leaf out-profile-dropped-octets {
                                                    type yang:counter64;
                                                    description
                                                        "The number of out-profile octets
                                                         discarded.";
                                                }

                                                leaf exceed-profile-forwarded-packets {
                                                    type yang:counter64;
                                                    description
                                                        "The number of exceed-profile packets
                                                         (rate above CIR) forwarded.";
                                                }

                                                leaf exceed-profile-forwarded-octets {
                                                    type yang:counter64;
                                                    description
                                                        "The number of exceed-profile octets
                                                         (rate above CIR) forwarded.";
                                                }

                                                leaf exceed-profile-dropped-packets {
                                                    type yang:counter64;
                                                    description
                                                        "The number of exceed-profile packets
                                                         discarded.";
                                                }

                                                leaf exceed-profile-dropped-octets {
                                                    type yang:counter64;
                                                    description
                                                        "The number of exceed-profile octets
                                                         discarded.";
                                                }

                                            } // container enqueued-4-profile-with-discards

                                        }
                                    }
                                } // container statistics

                            } // list queue

                        } // container vlan-qos

                        container qos {
                            description "Enter the qos context";

                            container sap-egress {
                                description "Enter the sap-egress context";

                                container traffic-manager {
                                    description "Enter the traffic-manager context";

                                    container statistics {
                                        description "Enter the statistics context";

                                        leaf in-inplus-profile-dropped-packets {
                                            type yang:counter64;
                                            description "Policy ID";
                                        }

                                        leaf in-inplus-profile-dropped-octets {
                                            type yang:counter64;
                                            description
                                                "The number of in-profile octets
                                                 discarded by the egress traffic manager due
                                                 to: MBS exceeded, buffer pool limit
                                                 exceeded, etc.";
                                        }

                                        leaf out-exceed-profile-dropped-packets {
                                            type yang:counter64;
                                            description
                                                "The number of out-of-profile packets
                                                 discarded by the egress traffic manager due
                                                 to: MBS exceeded, buffer pool limit
                                                 exceeded, etc.";
                                        }

                                        leaf out-exceed-profile-dropped-octets {
                                            type yang:counter64;
                                            description
                                                "The number of out-of-profile packets
                                                 discarded by the egress traffic manager due
                                                 to: MBS exceeded, buffer pool limit
                                                 exceeded, etc.";
                                        }

                                        leaf in-inplus-profile-forwarded-packets {
                                            type yang:counter64;
                                            description
                                                "The number of in-profile packets
                                                 (rate below CIR) forwarded by the
                                                 egress traffic manager.";
                                        }

                                        leaf in-inplus-profile-forwarded-octets {
                                            type yang:counter64;
                                            description
                                                "The number of in-profile octets
                                                 (rate below CIR) forwarded by the
                                                 egress traffic manager.";
                                        }

                                        leaf out-exceed-profile-forwarded-packets {
                                            type yang:counter64;
                                            description
                                                "The number of out-of-profile packets
                                                 (rate above CIR) forwarded by the
                                                 egress traffic manager.";
                                        }

                                        leaf out-exceed-profile-forwarded-octets {
                                            type yang:counter64;
                                            description
                                                "The number of out-of-profile octets
                                                 (rate above CIR) forwarded by the
                                                 egress traffic manager.";
                                        }

                                        leaf aggregate-forwarded-packets {
                                            type yang:counter64;
                                            description
                                                "The aggregate number of in and out-of profile
                                                 packets forwarded by the egress traffic manager.";
                                        }

                                        leaf aggregate-forwarded-octets {
                                            type yang:counter64;
                                            description
                                                "The aggregate number of in and out-of profile
                                                 octets forwarded by the egress traffic manager.";
                                        }

                                        leaf aggregate-dropped-packets {
                                            type yang:counter64;
                                            description
                                                "The aggregate number of in and out-of profile
                                                 packets discarded by the egress traffic manager due
                                                 to: MBS exceeded, buffer pool limit
                                                 exceeded, etc.";
                                        }

                                        leaf aggregate-dropped-octets {
                                            type yang:counter64;
                                            description
                                                "The aggregate number of in and out-of profile
                                                 octets discarded by the egress traffic manager due
                                                 to: MBS exceeded, buffer pool limit
                                                 exceeded, etc.";
                                        }

                                        leaf last-cleared-time {
                                            type yang:date-and-time;
                                            description "Time when the counters in this table were last cleared.";
                                        }

                                    } // container statistics

                                } // container traffic-manager

                                container qos-traffic {
                                    description "Enter the qos-traffic context";

                                    container statistics {
                                        description "Enter the statistics context";

                                        leaf egress-packets {
                                            type yang:counter64;
                                            description "The number of egress packets on this SAP.";
                                        }

                                        leaf egress-octets {
                                            type yang:counter64;
                                            description "The number of egress octets on this SAP.";
                                        }

                                    } // container statistics

                                } // container qos-traffic

                                list hardware-queue {
                                    key "hardware-queue-string";
                                    description "Enter the hardware-queue list instance";

                                    leaf hardware-queue-string {
                                        type types-sros:named-item-255;
                                        description "Name of the queue formatted by IOM.";
                                    }

                                    leaf adapted-admin-mbs {
                                        type types-qos:bytes;
                                        units "bytes";
                                        description "Admin MBS.";
                                    }

                                    leaf exceed-droptail {
                                        type union {
                                            type int64 {
                                                range "0..max";
                                            }
                                            type enumeration {
                                                enum "auto"                         { value -1; }
                                            }
                                        }
                                        description "Exceed droptail.";
                                    }

                                    leaf high-droptail {
                                        type union {
                                            type int64 {
                                                range "0..max";
                                            }
                                            type enumeration {
                                                enum "auto"                         { value -1; }
                                            }
                                        }
                                        description "High droptail.";
                                    }

                                    leaf high-plus-droptail {
                                        type union {
                                            type int64 {
                                                range "0..max";
                                            }
                                            type enumeration {
                                                enum "auto"                         { value -1; }
                                            }
                                        }
                                        description "Highplus droptail.";
                                    }

                                    leaf low-droptail {
                                        type union {
                                            type int64 {
                                                range "0..max";
                                            }
                                            type enumeration {
                                                enum "auto"                         { value -1; }
                                            }
                                        }
                                        description "Low droptail.";
                                    }

                                    leaf operational-cbs {
                                        type types-qos:bytes;
                                        units "bytes";
                                        description "Oper CBS.";
                                    }

                                    leaf operational-cir {
                                        type union {
                                            type enumeration {
                                                enum "max"                          { value -1; }
                                            }
                                            type int64;
                                        }
                                        description "Oper CIR.";
                                    }

                                    leaf operational-mbs {
                                        type types-qos:bytes;
                                        units "bytes";
                                        description "Oper MBS.";
                                    }

                                    leaf operational-pir {
                                        type union {
                                            type enumeration {
                                                enum "max"                          { value -1; }
                                            }
                                            type int64;
                                        }
                                        description "Oper PIR.";
                                    }

                                    leaf depth {
                                        type union {
                                            type enumeration {
                                                enum "max"                          { value -1; }
                                            }
                                            type int64;
                                        }
                                        description "Depth CIR.";
                                    }

                                    container exceed-slope {
                                        description "Enter the exceed-slope context";

                                        leaf current-probability {
                                            type types-sros:percent;
                                            description "Specifies the current probability in percentage";
                                        }

                                    } // container exceed-slope

                                    container high-slope {
                                        description "Enter the high-slope context";

                                        leaf current-probability {
                                            type types-sros:percent;
                                            description "Specifies the current probability in percentage";
                                        }

                                    } // container high-slope

                                    container high-plus-slope {
                                        description "Enter the high-plus-slope context";

                                        leaf current-probability {
                                            type types-sros:percent;
                                            description "Specifies the current probability in percentage";
                                        }

                                    } // container high-plus-slope

                                    container low-slope {
                                        description "Enter the low-slope context";

                                        leaf current-probability {
                                            type types-sros:percent;
                                            description "Specifies the current probability in percentage";
                                        }

                                    } // container low-slope

                                } // list hardware-queue

                                list queue {
                                    key "queue-id";
                                    description "Enter the queue list instance";

                                    leaf queue-id {
                                        type types-qos:egress-queue-id;
                                        description "The unique identifier for the queue.";
                                    }

                                    container queue-depth {
                                        description "Enter the queue-depth context";

                                        leaf elapsed-time {
                                            type types-sros:time-interval;
                                            description "Indicated the elapsed time.";
                                        }

                                        leaf depth-0-to-10-percent {
                                            type decimal64 {
                                                fraction-digits 2;
                                            }
                                            description "Indicated the depth 0 to 10 percent.";
                                        }

                                        leaf depth-11-to-20-percent {
                                            type decimal64 {
                                                fraction-digits 2;
                                            }
                                            description "Indicated the depth 0 to 20 percent.";
                                        }

                                        leaf depth-21-to-30-percent {
                                            type decimal64 {
                                                fraction-digits 2;
                                            }
                                            description "Indicated the depth 0 to 30 percent.";
                                        }

                                        leaf depth-31-to-40-percent {
                                            type decimal64 {
                                                fraction-digits 2;
                                            }
                                            description "Indicated the depth 0 to 40 percent.";
                                        }

                                        leaf depth-41-to-50-percent {
                                            type decimal64 {
                                                fraction-digits 2;
                                            }
                                            description "Indicated the depth 0 to 50 percent.";
                                        }

                                        leaf depth-51-to-60-percent {
                                            type decimal64 {
                                                fraction-digits 2;
                                            }
                                            description "Indicated the depth 0 to 60 percent.";
                                        }

                                        leaf depth-61-to-70-percent {
                                            type decimal64 {
                                                fraction-digits 2;
                                            }
                                            description "Indicated the depth 0 to 70 percent.";
                                        }

                                        leaf depth-71-to-80-percent {
                                            type decimal64 {
                                                fraction-digits 2;
                                            }
                                            description "Indicated the depth 0 to 80 percent.";
                                        }

                                        leaf depth-81-to-90-percent {
                                            type decimal64 {
                                                fraction-digits 2;
                                            }
                                            description "Indicated the depth 0 to 90 percent.";
                                        }

                                        leaf depth-91-to-100-percent {
                                            type decimal64 {
                                                fraction-digits 2;
                                            }
                                            description "Indicated the depth 0 to 100 percent.";
                                        }

                                        leaf queue-polling-interval {
                                            type types-sros:time-interval;
                                            description "Indicates the queue polling interval.";
                                        }

                                        leaf last-violation {
                                            type yang:date-and-time;
                                            description "Indicates the last violation time.";
                                        }

                                        leaf total-threshold-violations {
                                            type yang:counter32;
                                            description "Indicates the total threshold violations.";
                                        }

                                        leaf high-water-mark-polling-interval {
                                            type types-sros:time-duration;
                                            units "microseconds";
                                            description "Indicates the high water mark polling interval.";
                                        }

                                    } // container queue-depth

                                    container statistics {
                                        description "Enter the statistics context";

                                        choice stat-mode {
                                            case profile {

                                                container profile {
                                                    description "Enter the profile context";

                                                    leaf in-inplus-profile-forwarded-packets {
                                                        type yang:counter64;
                                                        description
                                                            "The number of in-profile/in-plus-profile packets
                                                             (rate below CIR) forwarded.";
                                                    }

                                                    leaf in-inplus-profile-forwarded-octets {
                                                        type yang:counter64;
                                                        description
                                                            "The number of in-profile/in-plus-profile octets
                                                             (rate below CIR) forwarded.";
                                                    }

                                                    leaf out-exceed-profile-forwarded-packets {
                                                        type yang:counter64;
                                                        description
                                                            "The number of out-profile/exceed-profile packets
                                                             (rate above CIR) forwarded.";
                                                    }

                                                    leaf out-exceed-profile-forwarded-octets {
                                                        type yang:counter64;
                                                        description
                                                            "The number of out-profile/exceed-profile octets
                                                             (rate above CIR) forwarded.";
                                                    }

                                                    leaf in-inplus-profile-dropped-packets {
                                                        type yang:counter64;
                                                        description
                                                            "The number of in-profile/in-plus-profile packets
                                                             discarded.";
                                                    }

                                                    leaf in-inplus-profile-dropped-octets {
                                                        type yang:counter64;
                                                        description
                                                            "The number of in-profile/in-plus-profile octets
                                                             discarded.";
                                                    }

                                                    leaf out-exceed-profile-dropped-packets {
                                                        type yang:counter64;
                                                        description
                                                            "The number of out-profile/exceed-profile packets
                                                             discarded.";
                                                    }

                                                    leaf out-exceed-profile-dropped-octets {
                                                        type yang:counter64;
                                                        description
                                                            "The number of out-profile/exceed-profile octets
                                                             discarded.";
                                                    }

                                                } // container profile

                                            }
                                            case v4-v6 {

                                                container v4-v6 {
                                                    description "Enter the v4-v6 context";

                                                    leaf ipv4-dropped-packets {
                                                        type yang:counter64;
                                                        description "The number of ipv4 packets discarded.";
                                                    }

                                                    leaf ipv4-dropped-octets {
                                                        type yang:counter64;
                                                        description "The number of ipv4 octets discarded.";
                                                    }

                                                    leaf ipv6-dropped-packets {
                                                        type yang:counter64;
                                                        description "The number of ipv6 packets discarded.";
                                                    }

                                                    leaf ipv6-dropped-octets {
                                                        type yang:counter64;
                                                        description "The number of ipv6 octets discarded.";
                                                    }

                                                    leaf ipv4-forwarded-packets {
                                                        type yang:counter64;
                                                        description "The number of ipv4 packets forwarded.";
                                                    }

                                                    leaf ipv4-forwarded-octets {
                                                        type yang:counter64;
                                                        description "The number of ipv4 octets forwarded.";
                                                    }

                                                    leaf ipv6-forwarded-packets {
                                                        type yang:counter64;
                                                        description "The number of ipv6 packets forwarded.";
                                                    }

                                                    leaf ipv6-forwarded-octets {
                                                        type yang:counter64;
                                                        description "The number of ipv6 octets forwarded.";
                                                    }

                                                } // container v4-v6

                                            }
                                        }
                                    } // container statistics

                                } // list queue

                                list policer {
                                    key "policer-id";
                                    description "Enter the policer list instance";

                                    leaf policer-id {
                                        type types-qos:sap-egress-policer-id;
                                        description "The unique identifier for the policer.";
                                    }

                                    container statistics {
                                        description "Enter the statistics context";

                                        choice stat-mode {
                                            case minimal {

                                                container minimal {
                                                    description "Enter the minimal context";

                                                    leaf all-offered-packets {
                                                        type yang:counter64;
                                                        description "The number of all the priority packets offered by the packet processor to traffic manager";
                                                    }

                                                    leaf all-offered-octets {
                                                        type yang:counter64;
                                                        description "The number of all the priority octets offered by the packet processor to traffic manager";
                                                    }

                                                    leaf all-dropped-packets {
                                                        type yang:counter64;
                                                        description "The number of all the priority packets dropped by the packet processor to traffic manager";
                                                    }

                                                    leaf all-dropped-octets {
                                                        type yang:counter64;
                                                        description "The number of all the priority octets dropped by the packet processor to traffic manager";
                                                    }

                                                    leaf all-forwarded-packets {
                                                        type yang:counter64;
                                                        description "The number of all the priority packets forwarded by the packet processor to traffic manager";
                                                    }

                                                    leaf all-forwarded-octets {
                                                        type yang:counter64;
                                                        description "The number of all the priority octets forwarded by the packet processor to traffic manager";
                                                    }

                                                } // container minimal

                                            }
                                            case offered-profile-no-cir {

                                                container offered-profile-no-cir {
                                                    description "Enter the offered-profile-no-cir context";

                                                    leaf in-profile-offered-packets {
                                                        type yang:counter64;
                                                        description "The number of in-profile packets offered by the packet processor to traffic manager";
                                                    }

                                                    leaf in-profile-offered-octets {
                                                        type yang:counter64;
                                                        description "The number of in-profile octets offered by the packet processor to traffic manager";
                                                    }

                                                    leaf out-profile-offered-packets {
                                                        type yang:counter64;
                                                        description "The number of out-of-profile packets offered by the packet processor to traffic manager";
                                                    }

                                                    leaf out-profile-offered-octets {
                                                        type yang:counter64;
                                                        description "The number of out-of-profile octets offered by the packet processor to traffic manager";
                                                    }

                                                    leaf in-profile-dropped-packets {
                                                        type yang:counter64;
                                                        description "The number of in-profile packets dropped by the packet processor to traffic manager";
                                                    }

                                                    leaf in-profile-dropped-octets {
                                                        type yang:counter64;
                                                        description "The number of in-profile octets dropped by the packet processor to traffic manager";
                                                    }

                                                    leaf out-profile-dropped-packets {
                                                        type yang:counter64;
                                                        description "The number of out-of-profile packets dropped by the packet processor to traffic manager";
                                                    }

                                                    leaf out-profile-dropped-octets {
                                                        type yang:counter64;
                                                        description "The number of out-of-profile octets dropped by the packet processor to traffic manager";
                                                    }

                                                    leaf in-profile-forwarded-packets {
                                                        type yang:counter64;
                                                        description "The number of in-profile packets forwarded by the packet processor to traffic manager";
                                                    }

                                                    leaf in-profile-forwarded-octets {
                                                        type yang:counter64;
                                                        description "The number of in-profile octets forwarded by the packet processor to traffic manager";
                                                    }

                                                    leaf out-profile-forwarded-packets {
                                                        type yang:counter64;
                                                        description "The number of out-of-profile packets forwarded by the packet processor to traffic manager";
                                                    }

                                                    leaf out-profile-forwarded-octets {
                                                        type yang:counter64;
                                                        description "The number of out-of-profile octets forwarded by the packet processor to traffic manager";
                                                    }

                                                } // container offered-profile-no-cir

                                            }
                                            case offered-profile-cir {

                                                container offered-profile-cir {
                                                    description "Enter the offered-profile-cir context";

                                                    leaf in-profile-offered-packets {
                                                        type yang:counter64;
                                                        description "The number of in-profile packets offered by the packet processor to traffic manager";
                                                    }

                                                    leaf in-profile-offered-octets {
                                                        type yang:counter64;
                                                        description "The number of in-profile octets offered by the packet processor to traffic manager";
                                                    }

                                                    leaf out-profile-offered-packets {
                                                        type yang:counter64;
                                                        description "The number of out-of-profile packets offered by the packet processor to traffic manager";
                                                    }

                                                    leaf out-profile-offered-octets {
                                                        type yang:counter64;
                                                        description "The number of out-of-profile octets offered by the packet processor to traffic manager";
                                                    }

                                                    leaf uncolor-offered-packets {
                                                        type yang:counter64;
                                                        description "The number of uncolor packets offered by the packet processor to traffic manager";
                                                    }

                                                    leaf uncolor-offered-octets {
                                                        type yang:counter64;
                                                        description "The number of uncolor octets offered by the packet processor to traffic manager";
                                                    }

                                                    leaf in-profile-dropped-packets {
                                                        type yang:counter64;
                                                        description "The number of in-profile packets dropped by the packet processor to traffic manager";
                                                    }

                                                    leaf in-profile-dropped-octets {
                                                        type yang:counter64;
                                                        description "The number of in-profile octets dropped by the packet processor to traffic manager";
                                                    }

                                                    leaf out-profile-dropped-packets {
                                                        type yang:counter64;
                                                        description "The number of out-of-profile packets dropped by the packet processor to traffic manager";
                                                    }

                                                    leaf out-profile-dropped-octets {
                                                        type yang:counter64;
                                                        description "The number of out-of-profile octets dropped by the packet processor to traffic manager";
                                                    }

                                                    leaf in-profile-forwarded-packets {
                                                        type yang:counter64;
                                                        description "The number of in-profile packets forwarded by the packet processor to traffic manager";
                                                    }

                                                    leaf in-profile-forwarded-octets {
                                                        type yang:counter64;
                                                        description "The number of in-profile octets forwarded by the packet processor to traffic manager";
                                                    }

                                                    leaf out-profile-forwarded-packets {
                                                        type yang:counter64;
                                                        description "The number of out-of-profile packets forwarded by the packet processor to traffic manager";
                                                    }

                                                    leaf out-profile-forwarded-octets {
                                                        type yang:counter64;
                                                        description "The number of out-of-profile octets forwarded by the packet processor to traffic manager";
                                                    }

                                                } // container offered-profile-cir

                                            }
                                            case offered-total-cir {

                                                container offered-total-cir {
                                                    description "Enter the offered-total-cir context";

                                                    leaf all-offered-packets {
                                                        type yang:counter64;
                                                        description "The number of all the priority packets offered by the packet processor to traffic manager";
                                                    }

                                                    leaf all-offered-octets {
                                                        type yang:counter64;
                                                        description "The number of all the priority octets offered by the packet processor to traffic manager";
                                                    }

                                                    leaf in-profile-dropped-packets {
                                                        type yang:counter64;
                                                        description "The number of in-profile packets dropped by the packet processor to traffic manager";
                                                    }

                                                    leaf in-profile-dropped-octets {
                                                        type yang:counter64;
                                                        description "The number of in-profile octets dropped by the packet processor to traffic manager";
                                                    }

                                                    leaf out-profile-dropped-packets {
                                                        type yang:counter64;
                                                        description "The number of out-of-profile packets dropped by the packet processor to traffic manager";
                                                    }

                                                    leaf out-profile-dropped-octets {
                                                        type yang:counter64;
                                                        description "The number of out-of-profile octets dropped by the packet processor to traffic manager";
                                                    }

                                                    leaf in-profile-forwarded-packets {
                                                        type yang:counter64;
                                                        description "The number of in-profile packets forwarded by the packet processor to traffic manager";
                                                    }

                                                    leaf in-profile-forwarded-octets {
                                                        type yang:counter64;
                                                        description "The number of in-profile octets forwarded by the packet processor to traffic manager";
                                                    }

                                                    leaf out-profile-forwarded-packets {
                                                        type yang:counter64;
                                                        description "The number of out-of-profile packets forwarded by the packet processor to traffic manager";
                                                    }

                                                    leaf out-profile-forwarded-octets {
                                                        type yang:counter64;
                                                        description "The number of out-of-profile octets forwarded by the packet processor to traffic manager";
                                                    }

                                                } // container offered-total-cir

                                            }
                                            case offered-limited-capped-cir {

                                                container offered-limited-capped-cir {
                                                    description "Enter the offered-limited-capped-cir context";

                                                    leaf in-profile-offered-packets {
                                                        type yang:counter64;
                                                        description "The number of in-profile packets offered by the packet processor to traffic manager";
                                                    }

                                                    leaf in-profile-offered-octets {
                                                        type yang:counter64;
                                                        description "The number of in-profile octets offered by the packet processor to traffic manager";
                                                    }

                                                    leaf in-profile-dropped-packets {
                                                        type yang:counter64;
                                                        description "The number of in-profile packets dropped by the packet processor to traffic manager";
                                                    }

                                                    leaf in-profile-dropped-octets {
                                                        type yang:counter64;
                                                        description "The number of in-profile octets dropped by the packet processor to traffic manager";
                                                    }

                                                    leaf out-profile-dropped-packets {
                                                        type yang:counter64;
                                                        description "The number of out-of-profile packets dropped by the packet processor to traffic manager";
                                                    }

                                                    leaf out-profile-dropped-octets {
                                                        type yang:counter64;
                                                        description "The number of out-of-profile octets dropped by the packet processor to traffic manager";
                                                    }

                                                    leaf in-profile-forwarded-packets {
                                                        type yang:counter64;
                                                        description "The number of in-profile packets forwarded by the packet processor to traffic manager";
                                                    }

                                                    leaf in-profile-forwarded-octets {
                                                        type yang:counter64;
                                                        description "The number of in-profile octets forwarded by the packet processor to traffic manager";
                                                    }

                                                    leaf out-profile-forwarded-packets {
                                                        type yang:counter64;
                                                        description "The number of out-of-profile packets forwarded by the packet processor to traffic manager";
                                                    }

                                                    leaf out-profile-forwarded-octets {
                                                        type yang:counter64;
                                                        description "The number of out-of-profile octets forwarded by the packet processor to traffic manager";
                                                    }

                                                    leaf out-profile-offered-packets {
                                                        type yang:counter64;
                                                        description "The number of out-of-rofile packets offered by the packet processor to traffic manager";
                                                    }

                                                    leaf out-profile-offered-octets {
                                                        type yang:counter64;
                                                        description "The number of out-of-profile octets offered by the packet processor to traffic manager";
                                                    }

                                                } // container offered-limited-capped-cir

                                            }
                                            case offered-profile-capped-cir {

                                                container offered-profile-capped-cir {
                                                    description "Enter the offered-profile-capped-cir context";

                                                    leaf in-profile-offered-packets {
                                                        type yang:counter64;
                                                        description "The number of in-profile packets offered by the packet processor to traffic manager";
                                                    }

                                                    leaf in-profile-offered-octets {
                                                        type yang:counter64;
                                                        description "The number of in-profile octets offered by the packet processor to traffic manager";
                                                    }

                                                    leaf out-profile-offered-packets {
                                                        type yang:counter64;
                                                        description "The number of out-of-profile packets offered by the packet processor to traffic manager";
                                                    }

                                                    leaf out-profile-offered-octets {
                                                        type yang:counter64;
                                                        description "The number of out-of-profile octets offered by the packet processor to traffic manager";
                                                    }

                                                    leaf uncolor-offered-packets {
                                                        type yang:counter64;
                                                        description "The number of uncolor packets offered by the packet processor to traffic manager";
                                                    }

                                                    leaf uncolor-offered-octets {
                                                        type yang:counter64;
                                                        description "The number of uncolor octets offered by the packet processor to traffic manager";
                                                    }

                                                    leaf in-profile-dropped-packets {
                                                        type yang:counter64;
                                                        description "The number of in-profile packets dropped by the packet processor to traffic manager";
                                                    }

                                                    leaf in-profile-dropped-octets {
                                                        type yang:counter64;
                                                        description "The number of in-profile octets dropped by the packet processor to traffic manager";
                                                    }

                                                    leaf out-profile-dropped-packets {
                                                        type yang:counter64;
                                                        description "The number of out-of-profile packets dropped by the packet processor to traffic manager";
                                                    }

                                                    leaf out-profile-dropped-octets {
                                                        type yang:counter64;
                                                        description "The number of out-of-profile octets dropped by the packet processor to traffic manager";
                                                    }

                                                    leaf in-profile-forwarded-packets {
                                                        type yang:counter64;
                                                        description "The number of in-profile packets forwarded by the packet processor to traffic manager";
                                                    }

                                                    leaf in-profile-forwarded-octets {
                                                        type yang:counter64;
                                                        description "The number of in-profile octets forwarded by the packet processor to traffic manager";
                                                    }

                                                    leaf out-profile-forwarded-packets {
                                                        type yang:counter64;
                                                        description "The number of out-of-profile packets forwarded by the packet processor to traffic manager";
                                                    }

                                                    leaf out-profile-forwarded-octets {
                                                        type yang:counter64;
                                                        description "The number of out-of-profile octets forwarded by the packet processor to traffic manager";
                                                    }

                                                } // container offered-profile-capped-cir

                                            }
                                            case offered-total-cir-exceed {

                                                container offered-total-cir-exceed {
                                                    description "Enter the offered-total-cir-exceed context";

                                                    leaf all-offered-packets {
                                                        type yang:counter64;
                                                        description "The number of all the priority packets offered by the packet processor to traffic manager";
                                                    }

                                                    leaf all-offered-octets {
                                                        type yang:counter64;
                                                        description "The number of all the priority octets offered by the packet processor to traffic manager";
                                                    }

                                                    leaf in-profile-dropped-packets {
                                                        type yang:counter64;
                                                        description "The number of in-profile packets dropped by the packet processor to traffic manager";
                                                    }

                                                    leaf in-profile-dropped-octets {
                                                        type yang:counter64;
                                                        description "The number of in-profile octets dropped by the packet processor to traffic manager";
                                                    }

                                                    leaf out-profile-dropped-packets {
                                                        type yang:counter64;
                                                        description "The number of out-of-profile packets dropped by the packet processor to traffic manager";
                                                    }

                                                    leaf out-profile-dropped-octets {
                                                        type yang:counter64;
                                                        description "The number of out-of-profile octets dropped by the packet processor to traffic manager";
                                                    }

                                                    leaf exceed-profile-dropped-packets {
                                                        type yang:counter64;
                                                        description "The number of exceed-profile packets dropped by the packet processor to traffic manager";
                                                    }

                                                    leaf exceed-profile-dropped-octets {
                                                        type yang:counter64;
                                                        description "The number of exceed-profile octets dropped by the packet processor to traffic manager";
                                                    }

                                                    leaf in-profile-forwarded-packets {
                                                        type yang:counter64;
                                                        description "The number of in-profile packets forwarded by the packet processor to traffic manager";
                                                    }

                                                    leaf in-profile-forwarded-octets {
                                                        type yang:counter64;
                                                        description "The number of in-profile octets forwarded by the packet processor to traffic manager";
                                                    }

                                                    leaf out-profile-forwarded-packets {
                                                        type yang:counter64;
                                                        description "The number of out-of-profile packets forwarded by the packet processor to traffic manager";
                                                    }

                                                    leaf out-profile-forwarded-octets {
                                                        type yang:counter64;
                                                        description "The number of out-of-profile octets forwarded by the packet processor to traffic manager";
                                                    }

                                                    leaf exceed-profile-forwarded-packets {
                                                        type yang:counter64;
                                                        description "The number of exceed-profile packets forwarded by the packet processor to traffic manager";
                                                    }

                                                    leaf exceed-profile-forwarded-octets {
                                                        type yang:counter64;
                                                        description "The number of exceed-profile octets forwarded by the packet processor to traffic manager";
                                                    }

                                                } // container offered-total-cir-exceed

                                            }
                                            case offered-four-profile-no-cir {

                                                container offered-four-profile-no-cir {
                                                    description "Enter the offered-four-profile-no-cir context";

                                                    leaf inplus-profile-offered-packets {
                                                        type yang:counter64;
                                                        description "The number of inplus-profile packets offered by the packet processor to traffic manager";
                                                    }

                                                    leaf inplus-profile-offered-octets {
                                                        type yang:counter64;
                                                        description "The number of inplus-profile octets offered by the packet processor to traffic manager";
                                                    }

                                                    leaf in-profile-offered-packets {
                                                        type yang:counter64;
                                                        description "The number of in-profile packets offered by the packet processor to traffic manager";
                                                    }

                                                    leaf in-profile-offered-octets {
                                                        type yang:counter64;
                                                        description "The number of in-profile octets offered by the packet processor to traffic manager";
                                                    }

                                                    leaf out-profile-offered-packets {
                                                        type yang:counter64;
                                                        description "The number of out-of-profile packets offered by the packet processor to traffic manager";
                                                    }

                                                    leaf out-profile-offered-octets {
                                                        type yang:counter64;
                                                        description "The number of out-of-profile octets offered by the packet processor to traffic manager";
                                                    }

                                                    leaf exceed-profile-offered-packets {
                                                        type yang:counter64;
                                                        description "The number of exceed-profile packets offered by the packet processor to traffic manager";
                                                    }

                                                    leaf exceed-profile-offered-octets {
                                                        type yang:counter64;
                                                        description "The number of exceed-profile octets offered by the packet processor to traffic manager";
                                                    }

                                                    leaf inplus-profile-dropped-packets {
                                                        type yang:counter64;
                                                        description "The number of inplus-profile packets dropped by the packet processor to traffic manager";
                                                    }

                                                    leaf inplus-profile-dropped-octets {
                                                        type yang:counter64;
                                                        description "The number of inplus-profile octets dropped by the packet processor to traffic manager";
                                                    }

                                                    leaf in-profile-dropped-packets {
                                                        type yang:counter64;
                                                        description "The number of in-profile packets dropped by the packet processor to traffic manager";
                                                    }

                                                    leaf in-profile-dropped-octets {
                                                        type yang:counter64;
                                                        description "The number of in-profile octets dropped by the packet processor to traffic manager";
                                                    }

                                                    leaf out-profile-dropped-packets {
                                                        type yang:counter64;
                                                        description "The number of out-of-profile packets dropped by the packet processor to traffic manager";
                                                    }

                                                    leaf out-profile-dropped-octets {
                                                        type yang:counter64;
                                                        description "The number of out-of-profile octets dropped by the packet processor to traffic manager";
                                                    }

                                                    leaf exceed-profile-dropped-packets {
                                                        type yang:counter64;
                                                        description "The number of exceed-profile packets dropped by the packet processor to traffic manager";
                                                    }

                                                    leaf exceed-profile-dropped-octets {
                                                        type yang:counter64;
                                                        description "The number of exceed-profile octets dropped by the packet processor to traffic manager";
                                                    }

                                                    leaf inplus-profile-forwarded-packets {
                                                        type yang:counter64;
                                                        description "The number of inplus-profile packets forwarded by the packet processor to traffic manager";
                                                    }

                                                    leaf inplus-profile-forwarded-octets {
                                                        type yang:counter64;
                                                        description "The number of inplus-profile octets forwarded by the packet processor to traffic manager";
                                                    }

                                                    leaf in-profile-forwarded-packets {
                                                        type yang:counter64;
                                                        description "The number of in-profile packets forwarded by the packet processor to traffic manager";
                                                    }

                                                    leaf in-profile-forwarded-octets {
                                                        type yang:counter64;
                                                        description "The number of in-profile octets forwarded by the packet processor to traffic manager";
                                                    }

                                                    leaf out-profile-forwarded-packets {
                                                        type yang:counter64;
                                                        description "The number of out-of-profile packets forwarded by the packet processor to traffic manager";
                                                    }

                                                    leaf out-profile-forwarded-octets {
                                                        type yang:counter64;
                                                        description "The number of out-of-profile octets forwarded by the packet processor to traffic manager";
                                                    }

                                                    leaf exceed-profile-forwarded-packets {
                                                        type yang:counter64;
                                                        description "The number of exceed-profile packets forwarded by the packet processor to traffic manager";
                                                    }

                                                    leaf exceed-profile-forwarded-octets {
                                                        type yang:counter64;
                                                        description "The number of exceed-profile octets forwarded by the packet processor to traffic manager";
                                                    }

                                                } // container offered-four-profile-no-cir

                                            }
                                            case offered-total-cir-four-profile {

                                                container offered-total-cir-four-profile {
                                                    description "Enter the offered-total-cir-four-profile context";

                                                    leaf all-offered-packets {
                                                        type yang:counter64;
                                                        description "The number of all the priority packets offered by the packet processor to traffic manager";
                                                    }

                                                    leaf all-offered-octets {
                                                        type yang:counter64;
                                                        description "The number of all the priority octets offered by the packet processor to traffic manager";
                                                    }

                                                    leaf inplus-profile-dropped-packets {
                                                        type yang:counter64;
                                                        description "The number of inplus-profile packets dropped by the packet processor to traffic manager";
                                                    }

                                                    leaf inplus-profile-dropped-octets {
                                                        type yang:counter64;
                                                        description "The number of inplus-profile octets dropped by the packet processor to traffic manager";
                                                    }

                                                    leaf in-profile-dropped-packets {
                                                        type yang:counter64;
                                                        description "The number of in-profile packets dropped by the packet processor to traffic manager";
                                                    }

                                                    leaf in-profile-dropped-octets {
                                                        type yang:counter64;
                                                        description "The number of in-profile octets dropped by the packet processor to traffic manager";
                                                    }

                                                    leaf out-profile-dropped-packets {
                                                        type yang:counter64;
                                                        description "The number of out-of-profile packets dropped by the packet processor to traffic manager";
                                                    }

                                                    leaf out-profile-dropped-octets {
                                                        type yang:counter64;
                                                        description "The number of out-of-profile octets dropped by the packet processor to traffic manager";
                                                    }

                                                    leaf exceed-profile-dropped-packets {
                                                        type yang:counter64;
                                                        description "The number of exceed-profile packets dropped by the packet processor to traffic manager";
                                                    }

                                                    leaf exceed-profile-dropped-octets {
                                                        type yang:counter64;
                                                        description "The number of exceed-profile octets dropped by the packet processor to traffic manager";
                                                    }

                                                    leaf inplus-profile-forwarded-packets {
                                                        type yang:counter64;
                                                        description "The number of inplus-profile packets forwarded by the packet processor to traffic manager";
                                                    }

                                                    leaf inplus-profile-forwarded-octets {
                                                        type yang:counter64;
                                                        description "The number of inplus-profile octets forwarded by the packet processor to traffic manager";
                                                    }

                                                    leaf in-profile-forwarded-packets {
                                                        type yang:counter64;
                                                        description "The number of in-profile packets forwarded by the packet processor to traffic manager";
                                                    }

                                                    leaf in-profile-forwarded-octets {
                                                        type yang:counter64;
                                                        description "The number of in-profile octets forwarded by the packet processor to traffic manager";
                                                    }

                                                    leaf out-profile-forwarded-packets {
                                                        type yang:counter64;
                                                        description "The number of out-of-profile packets forwarded by the packet processor to traffic manager";
                                                    }

                                                    leaf out-profile-forwarded-octets {
                                                        type yang:counter64;
                                                        description "The number of out-of-profile octets forwarded by the packet processor to traffic manager";
                                                    }

                                                    leaf exceed-profile-forwarded-packets {
                                                        type yang:counter64;
                                                        description "The number of exceed-profile packets forwarded by the packet processor to traffic manager";
                                                    }

                                                    leaf exceed-profile-forwarded-octets {
                                                        type yang:counter64;
                                                        description "The number of exceed-profile octets forwarded by the packet processor to traffic manager";
                                                    }

                                                } // container offered-total-cir-four-profile

                                            }
                                            case v4-v6 {

                                                container v4-v6 {
                                                    description "Enter the v4-v6 context";

                                                    leaf ipv4-offered-packets {
                                                        type yang:counter64;
                                                        description "The number of ipv4 packets offered by the packet processor to traffic manager";
                                                    }

                                                    leaf ipv4-offered-octets {
                                                        type yang:counter64;
                                                        description "The number of ipv4 octets offered by the packet processor to traffic manager";
                                                    }

                                                    leaf ipv6-offered-packets {
                                                        type yang:counter64;
                                                        description "The number of ipv6 packets offered by the packet processor to traffic manager";
                                                    }

                                                    leaf ipv6-offered-octets {
                                                        type yang:counter64;
                                                        description "The number of ipv6 octets offered by the packet processor to traffic manager";
                                                    }

                                                    leaf ipv4-dropped-packets {
                                                        type yang:counter64;
                                                        description "The number of ipv4 packets dropped by the packet processor to traffic manager";
                                                    }

                                                    leaf ipv4-dropped-octets {
                                                        type yang:counter64;
                                                        description "The number of ipv4 octets dropped by the packet processor to traffic manager";
                                                    }

                                                    leaf ipv6-dropped-packets {
                                                        type yang:counter64;
                                                        description "The number of ipv6 packets dropped by the packet processor to traffic manager";
                                                    }

                                                    leaf ipv6-dropped-octets {
                                                        type yang:counter64;
                                                        description "The number of ipv6 octets dropped by the packet processor to traffic manager";
                                                    }

                                                    leaf ipv4-forwarded-packets {
                                                        type yang:counter64;
                                                        description "The number of ipv4 packets forwarded by the packet processor to traffic manager";
                                                    }

                                                    leaf ipv4-forwarded-octets {
                                                        type yang:counter64;
                                                        description "The number of ipv4 octets forwarded by the packet processor to traffic manager";
                                                    }

                                                    leaf ipv6-forwarded-packets {
                                                        type yang:counter64;
                                                        description "The number of ipv6 packets forwarded by the packet processor to traffic manager";
                                                    }

                                                    leaf ipv6-forwarded-octets {
                                                        type yang:counter64;
                                                        description "The number of ipv6 octets forwarded by the packet processor to traffic manager";
                                                    }

                                                } // container v4-v6

                                            }
                                            case bonding {

                                                container bonding {
                                                    description "Enter the bonding context";

                                                    leaf connection-1-offered-packets {
                                                        type yang:counter64;
                                                        description "The number of connection-1 packets offered by the packet processor to traffic manager";
                                                    }

                                                    leaf connection-1-offered-octets {
                                                        type yang:counter64;
                                                        description "The number of connection-1 octets offered by the packet processor to traffic manager";
                                                    }

                                                    leaf connection-2-offered-packets {
                                                        type yang:counter64;
                                                        description "The number of connection-2 packets offered by the packet processor to traffic manager";
                                                    }

                                                    leaf connection-2-offered-octets {
                                                        type yang:counter64;
                                                        description "The number of connection-2 octets offered by the packet processor to traffic manager";
                                                    }

                                                    leaf connection-1-dropped-packets {
                                                        type yang:counter64;
                                                        description "The number of connection-1 packets dropped by the packet processor to traffic manager";
                                                    }

                                                    leaf connection-1-dropped-octets {
                                                        type yang:counter64;
                                                        description "The number of connection-1 octets dropped by the packet processor to traffic manager";
                                                    }

                                                    leaf connection-2-dropped-packets {
                                                        type yang:counter64;
                                                        description "The number of connection-2 packets dropped by the packet processor to traffic manager";
                                                    }

                                                    leaf connection-2-dropped-octets {
                                                        type yang:counter64;
                                                        description "The number of connection-2 octets dropped by the packet processor to traffic manager";
                                                    }

                                                    leaf connection-1-forwarded-packets {
                                                        type yang:counter64;
                                                        description "The number of connection-1 packets forwarded by the packet processor to traffic manager";
                                                    }

                                                    leaf connection-1-forwarded-octets {
                                                        type yang:counter64;
                                                        description "The number of connection-1 octets forwarded by the packet processor to traffic manager";
                                                    }

                                                    leaf connection-2-forwarded-packets {
                                                        type yang:counter64;
                                                        description "The number of connection-2 packets forwarded by the packet processor to traffic manager";
                                                    }

                                                    leaf connection-2-forwarded-octets {
                                                        type yang:counter64;
                                                        description "The number of connection-2 octets forwarded by the packet processor to traffic manager";
                                                    }

                                                } // container bonding

                                            }
                                        }
                                    } // container statistics

                                    list hardware-policer {
                                        key "hardware-policer-string";
                                        description "Enter the hardware-policer list instance";

                                        leaf hardware-policer-string {
                                            type types-sros:named-item-255;
                                            description "Name of the policer formatted by IOM.";
                                        }

                                        leaf adapted-admin-cbs {
                                            type int64;
                                            units "bytes";
                                            description "Admin CBS.";
                                        }

                                        leaf adapted-admin-mbs {
                                            type int64;
                                            units "bytes";
                                            description "Admin MBS.";
                                        }

                                        leaf adapted-hp-only {
                                            type int64;
                                            units "bytes";
                                            description "Hi Prio Only.";
                                        }

                                        leaf depth {
                                            type int64;
                                            units "bytes";
                                            description "Depth.";
                                        }

                                        leaf operational-cir {
                                            type union {
                                                type enumeration {
                                                    enum "max"                          { value -1; }
                                                }
                                                type int64;
                                            }
                                            description "Oper CIR.";
                                        }

                                        leaf operational-fir {
                                            type union {
                                                type enumeration {
                                                    enum "max"                          { value -1; }
                                                }
                                                type int64;
                                            }
                                            description "Oper FIR.";
                                        }

                                        leaf operational-pir {
                                            type union {
                                                type enumeration {
                                                    enum "max"                          { value -1; }
                                                }
                                                type int64;
                                            }
                                            description "Oper PIR.";
                                        }

                                    } // list hardware-policer

                                } // list policer

                            } // container sap-egress

                            container policer-control-policy {
                                description "Enter the policer-control-policy context";

                                list arbiter {
                                    key "arbiter-name";
                                    description "Enter the arbiter list instance";

                                    leaf arbiter-name {
                                        type types-sros:named-item;
                                        description "Specifies the arbiter name.";
                                    }

                                    container statistics {
                                        description "Enter the statistics context";

                                        leaf forwarded-packets {
                                            type yang:counter64;
                                            description "The number of forwarded packets.";
                                        }

                                        leaf forwarded-octets {
                                            type yang:counter64;
                                            description "The number of forwarded octets.";
                                        }

                                    } // container statistics

                                } // list arbiter

                            } // container policer-control-policy

                            container scheduler-policy {
                                description "Enter the scheduler-policy context";

                                list scheduler {
                                    key "scheduler-name";
                                    description "Enter the scheduler list instance";

                                    leaf scheduler-name {
                                        type types-sros:named-item;
                                        description "Specifies the scheduler name.";
                                    }

                                    container statistics {
                                        description "Enter the statistics context";

                                        leaf forwarded-packets {
                                            type yang:counter64;
                                            description "The number of forwarded packets.";
                                        }

                                        leaf forwarded-octets {
                                            type yang:counter64;
                                            description "The number of forwarded octets.";
                                        }

                                    } // container statistics

                                } // list scheduler

                            } // container scheduler-policy

                        } // container qos

                    } // container egress

                    container lag {
                        description "Enter the lag context";

                        leaf active-port {
                            type types-sros:port;
                            description
                                "Port on the lag associated with this SAP, that is used when
                                 lag-per-link-hash is enabled on the lag or when lag-link-map-profile
                                 is configured on this SAP.";
                        }

                        container per-link-hash-oper {
                            description "Enter the per-link-hash-oper context";

                            leaf class {
                                type int32;
                                description "Operational value for class associated with this SAP.";
                            }

                            leaf weight {
                                type int32;
                                description "Operational value used for weight associated with this SAP.";
                            }

                            leaf is-overriden {
                                type boolean;
                                description
                                    "Whether administrative values, subscriber management determined
                                     operational weight and class are used for this SAP.";
                            }

                        } // container per-link-hash-oper

                    } // container lag

                    container distributed-cpu-protection {
                        description "Enter the distributed-cpu-protection context";

                        list static-policer {
                            key "name card fp-number";
                            description "Enter the static-policer list instance";

                            leaf name {
                                type types-sros:named-item;
                                description "Name of static policer.";
                            }

                            leaf card {
                                type types-card:iom-card-slot;
                                description "IOM card within a chassis in the system.";
                            }

                            leaf fp-number {
                                type uint32 {
                                    range "1..12";
                                }
                                description "Forwarding plane within a specific IOM card in the system.";
                            }

                            leaf state {
                                type types-services:dist-cpu-prot-policer-state;
                                description "State of the policer configured on Distributed CPU Protection Policy.";
                            }

                            leaf exceed-count {
                                type uint64;
                                description
                                    "Number of packets exceeding the policing parameters since the given
                                     policer was previously declared as conformant or newly instantiated.";
                            }

                            leaf hold-down-remain {
                                type types-services:dist-cpu-prot-action-duration;
                                units "seconds";
                                description "Remaining hold-down period for a given policer.";
                            }

                            leaf detection-time-remain {
                                type uint32;
                                units "seconds";
                                description "Detection time remaining for a given policer.";
                            }

                        } // list static-policer

                        list local-monitor-policer {
                            key "name card fp-number";
                            description "Enter the local-monitor-policer list instance";

                            leaf name {
                                type types-sros:named-item;
                                description "Name of local-monitor policer.";
                            }

                            leaf card {
                                type types-card:iom-card-slot;
                                description "IOM card within a chassis in the system.";
                            }

                            leaf fp-number {
                                type uint32 {
                                    range "1..12";
                                }
                                description "Forwarding plane within a specific IOM card in the system.";
                            }

                            leaf state {
                                type types-services:dist-cpu-prot-policer-state;
                                description "State of the policer configured on Distributed CPU Protection Policy.";
                            }

                            leaf exceed-count {
                                type uint64;
                                description
                                    "Number of packets exceeding the policing parameters since the given
                                     policer was previously declared as conformant or newly instantiated.";
                            }

                            leaf all-dynamic-policer-allocation {
                                type boolean;
                                description "All dynamic-policers allocation status";
                            }

                        } // list local-monitor-policer

                        list dynamic-policer {
                            key "protocol card fp-number";
                            description "Enter the dynamic-policer list instance";

                            leaf protocol {
                                type types-sros:dist-cpu-protection-protocol;
                                description "Dynamic policer protocol.";
                            }

                            leaf card {
                                type types-card:iom-card-slot;
                                description "IOM card within a chassis in the system.";
                            }

                            leaf fp-number {
                                type uint32 {
                                    range "1..12";
                                }
                                description "Forwarding plane within a specific IOM card in the system.";
                            }

                            leaf state {
                                type types-services:dist-cpu-prot-policer-state;
                                description "State of the policer configured on Distributed CPU Protection Policy.";
                            }

                            leaf exceed-count {
                                type uint64;
                                description
                                    "Number of packets exceeding the policing parameters since the given
                                     policer was previously declared as conformant or newly instantiated.";
                            }

                            leaf hold-down-remain {
                                type types-services:dist-cpu-prot-action-duration;
                                units "seconds";
                                description "Remaining hold-down period for a given policer.";
                            }

                            leaf detection-time-remain {
                                type uint32;
                                units "seconds";
                                description "Detection time remaining for a given policer.";
                            }

                            leaf dynamic-policer-allocation {
                                type boolean;
                                description "Dynamic-policer allocation status";
                            }

                        } // list dynamic-policer

                    } // container distributed-cpu-protection

                    container eth-cfm {
                        description "Enter the eth-cfm context";

                        list mep {
                            key "md-admin-name ma-admin-name mep-id";
                            description "Enter the mep list instance";

                            leaf md-admin-name {
                                type leafref {
                                    path "../../../../../../../eth-cfm/domain/md-admin-name";
                                }
                                description "Admin-assigned maintenance domain index value";
                            }

                            leaf ma-admin-name {
                                type leafref {
                                    path "../../../../../../../eth-cfm/domain[md-admin-name=current()/../md-admin-name]/association/ma-admin-name";
                                }
                                description "Maintenance association name";
                            }

                            leaf mep-id {
                                type types-eth-cfm:mep-id-type;
                                description "Maintenance endpoint ID";
                            }

                            leaf if-index {
                                type uint32;
                                description "Port ID of the MEP.";
                            }

                            leaf oper-mac-address {
                                type yang:mac-address;
                                description "Operational MAC address of the MEP.";
                            }

                            container csf {
                                description "Enter the csf context";

                                container received {
                                    description "Enter the received context";

                                    leaf state {
                                        type enumeration {
                                            enum "los"                          { value 0; }
                                            enum "ais"                          { value 1; }
                                            enum "rdi"                          { value 2; }
                                            enum "dci"                          { value 3; }
                                        }
                                        description
                                            "Indicates the state of the received CSF frames for the MEP.
                                                los (0) - Client Loss of Signal
                                                ais (1) - Client Forward Defect Indication
                                                rdi (2) - Client Reverse Defect Indication
                                                dci (3) - Client Defect Clear Indication.";
                                    }

                                    leaf interval {
                                        type uint32 {
                                            range "1|60";
                                        }
                                        units "seconds";
                                        description "Indicates the CSF Interval received in the most recent CSF frame.";
                                    }

                                } // container received

                            } // container csf

                            container grace {
                                description "Enter the grace context";

                                container transmitted {
                                    description "Enter the transmitted context";

                                    leaf grace-notification {
                                        type enumeration {
                                            enum "no-transmit"                  { value 0; }
                                            enum "grace"                        { value 1; }
                                            enum "eth-ed"                       { value 2; }
                                        }
                                        description "Indicates the state of the MEP grace period PDU transmission.";
                                    }

                                } // container transmitted

                                container received {
                                    description "Enter the received context";

                                    leaf process-grace-notification {
                                        type boolean;
                                        description
                                            "Indicates whether the local MEP is receiving and processing grace notifications
                                             from one or more peer MEPs. A value of 'true ' indicates the local MEP is
                                             receiving and processing grace from at least one peer MEP. A value
                                             of 'false' indicates that no peer grace notifications are being
                                             received and processed.";
                                    }

                                } // container received

                            } // container grace

                            container ccm-states {
                                description "Enter the ccm-states context";

                                leaf transmit-status {
                                    type enumeration {
                                        enum "no-transmit"                  { value 0; }
                                        enum "transmit"                     { value 1; }
                                        enum "suppressed"                   { value 2; }
                                    }
                                    description
                                        "Indicates the state of the MEP CCM PDU transmission.

                                         Values:
                                            noTransmit (0) - no CCM PDUs are being transmitted by the MEP
                                            transmit   (1) - MEP is currently transmitting CCM PDUs
                                            suppressed (2) - MEP should be transmitting CCM PDUs but is suppressing
                                                            them due to an internal condition";
                                }

                                leaf sequence-error {
                                    type yang:counter32;
                                    description "The total number of out-of-sequence CCMs received from all remote MEPs.";
                                }

                                leaf fng-state {
                                    type types-eth-cfm:fng-state-type;
                                    description "Current state of the MEP Fault Notification Generator State Machine.";
                                }

                                container transmitted {
                                    description "Enter the transmitted context";

                                    leaf count {
                                        type yang:counter32;
                                        description "Total number of CCMs transmitted.";
                                    }

                                    leaf interface-status {
                                        type types-eth-cfm:interface-status;
                                        description
                                            "Indicates the interface status TLV information included in the most
                                             recent Connectivity Check Message (CCM) transmission from the local MEP.
                                             If the local MEP CCM transmissions are not enabled, or if no interface
                                             status TLV was included in the most recent transmission, then
                                             ccm-tx-if-status will return a value of is-no-interface-status-tlv (0).";
                                    }

                                    leaf port-status {
                                        type types-eth-cfm:port-status;
                                        description
                                            "Indicates the port status TLV information included in the most recent
                                             Connectivity Check Message (CCM) transmission from the local MEP.

                                             If the local MEP CCM transmissions are not enabled, or if no port
                                             status TLV was included in the most recent transmission, then
                                             ccm-tx-port-status will return a value of ps-no-port-state-tlv (0).";
                                    }

                                    leaf remote-defect-indicator {
                                        type boolean;
                                        description
                                            "Indicates whether or not the Remote Defect Indication (RDI) bit was set
                                             on the most recent Connectivity Check Message (CCM) transmission from the
                                             local MEP.

                                             If the local MEP CCM transmissions are not eanbled, or if the RDI bit
                                             was not set in the most recent transmission, then ccm-tx-rdi will return
                                             a value of 'false (2)'.";
                                    }

                                } // container transmitted

                                container received {
                                    description "Enter the received context";

                                    leaf highest-priority-defect {
                                        type types-eth-cfm:highest-priority-defect-type;
                                        description
                                            "The highest priority defect that has been present since the
                                             MEPs Fault Notification Generator State Machine was last in
                                             the reset state.";
                                    }

                                    leaf defect-flags {
                                        type types-eth-cfm:mep-defect-flags;
                                        description "A vector of boolean error conditions, any of which may be true.";
                                    }

                                    list remote-mep-peer {
                                        key "remote-mep-id";
                                        description "Enter the remote-mep-peer list instance";

                                        leaf remote-mep-id {
                                            type types-eth-cfm:mep-id-type;
                                            description "The Remote MEP ID within the same Maintenance Association.";
                                        }

                                        leaf auto-discovered {
                                            type boolean;
                                            description
                                                "Specifies whether or not the remote peer was automatically discovered
                                                 ('true') or not. Auto-discovered remote peers are created by the system
                                                 only, and are of a 'volatile' storage type. Specifying the value of
                                                 'false' will mark an auto-discovered remote peer as permanently configured.";
                                        }

                                        leaf receiving-ccm {
                                            type types-eth-cfm:remote-mep-state-type;
                                            description "The operational CCM receiving state of the remote MEP.";
                                        }

                                        leaf ccm-status-since {
                                            type yang:date-and-time;
                                            description
                                                "The time at which the Remote MEP
                                                 last entered either the mep-failed or mep-ok state. ";
                                        }

                                        leaf peer-mac-address {
                                            type yang:mac-address;
                                            description "The MAC address of the remote MEP.";
                                        }

                                        leaf receiving-remote-defect-indicator {
                                            type boolean;
                                            description
                                                "State of the RDI bit in the last received CCM (true for rdi=1), or false
                                                 if none has been received.";
                                        }

                                        leaf port-status-tlv {
                                            type types-eth-cfm:port-status;
                                            description
                                                "An enumerated value of the Port status TLV received in the
                                                 last CCM from the remote MEP or the default value
                                                 ps-no-port-state-tlv indicating either no CCM has been received,
                                                 or that no port status TLV was received in the last CCM. ";
                                        }

                                        leaf interface-status-tlv {
                                            type types-eth-cfm:interface-status;
                                            description
                                                "An enumerated value of the Interface status TLV received
                                                 in the last CCM from the remote MEP or the default value
                                                 is-no-interface-status-tlv indicating either no CCM has been
                                                 received, or that no interface status TLV was received in
                                                 the last CCM.";
                                        }

                                    } // list remote-mep-peer

                                } // container received

                            } // container ccm-states

                            container mc-lag {
                                description "Enter the mc-lag context";

                                leaf inactive-state {
                                    type enumeration {
                                        enum "not-applicable"               { value 0; }
                                        enum "standby"                      { value 1; }
                                        enum "active"                       { value 2; }
                                    }
                                    description
                                        "Indicates the MC-LAG inactive state of the mep.  The value of
                                         system/eth-cfm/redundancy/mc-lag/standby-mep must be 'true (1)' 
                                         on the node for this leaf to have meaning.";
                                }

                            } // container mc-lag

                            container statistics {
                                description "Enter the statistics context";

                                list opcode {
                                    key "opcode-name";
                                    description "Enter the opcode list instance";

                                    leaf opcode-name {
                                        type types-eth-cfm:statistics-opcode-name;
                                        description "Integer that defines which CFM PDU Opcode the statictics refer to.";
                                    }

                                    leaf transmitted {
                                        type yang:counter32;
                                        description "The total number of PDUs transmitted from the node with the specified Opcode.";
                                    }

                                    leaf received {
                                        type yang:counter32;
                                        description "The total number of PDUs received on the node with the specified Opcode.";
                                    }

                                } // list opcode

                            } // container statistics

                        } // list mep

                    } // container eth-cfm

                    list ip-tunnel {
                        key "tunnel-name";
                        description "Enter the ip-tunnel list instance";

                        leaf tunnel-name {
                            type types-sros:interface-name;
                            description "IP tunnel name";
                        }

                        leaf host-mda {
                            type types-isa:slot-mda;
                            description "Active ISA that is being used to host this tunnel.";
                        }

                        leaf last-oper-changed {
                            type types-sros:date-time;
                            description "Last operational status change time.";
                        }

                        leaf oper-state {
                            type types-services:ip-tunnel-oper-state;
                            description "Operational state of the tunnel.";
                        }

                        leaf oper-flags {
                            type bits {
                                bit unresolved-local-ip            { position 0; }
                                bit tunnel-admin-down              { position 1; }
                                bit sap-down                       { position 2; }
                                bit unresolved-delivery-svc        { position 3; }
                                bit unregistered-local-ip          { position 4; }
                                bit remote-ip-unreachable          { position 5; }
                                bit unresolved-dst-ip              { position 6; }
                                bit trust-anchors-down             { position 7; }
                                bit cert-profile-down              { position 8; }
                            }
                            description "Reason why the tunnel is operationally down";
                        }

                        leaf oper-remote-ip-address {
                            type types-sros:ip-address;
                            description "Operational remote IP address.";
                        }

                        leaf matched-trust-anchor {
                            type types-sros:named-item;
                            description
                                "The name for matched Certificate-Authority Profile name associated
                                 with this SAP IPSec SA certificate.";
                        }

                        container key-exchange {
                            description "Enter the key-exchange context";

                            container dynamic {
                                description "Enter the dynamic context";

                                container ike-sa {
                                    description "Enter the ike-sa context";

                                    leaf state {
                                        type enumeration {
                                            enum "up"                           { value 1; }
                                            enum "down"                         { value 2; }
                                        }
                                        description "The state of IKE SA";
                                    }

                                    leaf established-time {
                                        type yang:date-and-time;
                                        description "The time the IKE SA completed";
                                    }

                                    leaf negotiated-lifetime {
                                        type types-sros:time-duration;
                                        description "The lifetime negotiated for the IKE SA";
                                    }

                                    leaf expiration-time {
                                        type yang:date-and-time;
                                        description "The time when the IKE SA will expire";
                                    }

                                    leaf path-mtu {
                                        type uint32;
                                        units "bytes";
                                        description "The path MTU used between the local and remote endpoints for this IPsec tunnel";
                                    }

                                    leaf authentication-algorithm {
                                        type types-ipsec:auth-algorithms;
                                        description "The authentication algorithm of the IKE SA for this IPsec tunnel";
                                    }

                                    leaf encryption-algorithm {
                                        type types-ipsec:encryption-algorithms;
                                        description "The encryption algorithm of the IKE SA for this IPsec tunnel";
                                    }

                                    leaf prf-algorithm {
                                        type types-ipsec:prf-algorithms;
                                        description "The pseudo-random function (PRF)";
                                    }

                                    leaf dh-group {
                                        type types-ipsec:dh-group;
                                        description "The Diffie-Hellman (DH) group of the IKE SA for this IPsec tunnel.";
                                    }

                                    leaf cert-profile-entry-id {
                                        type uint32;
                                        description "The matching certificate profile entry id used for this tunnel";
                                    }

                                    leaf cert-profile-name {
                                        type types-sros:named-item;
                                        description "The IPsec tunnel certificate profile name used for this tunnel";
                                    }

                                    container statistics {
                                        description "Enter the statistics context";

                                        leaf ctrl-packets-sent {
                                            type yang:counter32;
                                            description "The number of control packets this IPsec Tunnel has sent";
                                        }

                                        leaf ctrl-packets-received {
                                            type yang:counter32;
                                            description "The number of control packets this IPsec Tunnel has received";
                                        }

                                        leaf ctrl-packets-sent-errors {
                                            type yang:counter32;
                                            description "The number of control packet transmit errors";
                                        }

                                        leaf ctrl-packets-received-errors {
                                            type yang:counter32;
                                            description "The number of control packet receive errors";
                                        }

                                        leaf dpd-packets-sent {
                                            type yang:counter32;
                                            description "The number of Dead-Peer-Detection packets transmitted";
                                        }

                                        leaf dpd-packets-received {
                                            type yang:counter32;
                                            description "The number of Dead-Peer-Detection packets received";
                                        }

                                        leaf dpd-ack-packets-sent {
                                            type yang:counter32;
                                            description "The number of Dead-Peer-Detection acknowledgement packets transmitted";
                                        }

                                        leaf dpd-ack-packets-received {
                                            type yang:counter32;
                                            description "The number of Dead-Peer-Detection acknowledgement packets received";
                                        }

                                        leaf dpd-timeout-packets {
                                            type yang:counter32;
                                            description "The number of DPD R-U-THERE packets that have not been acknowledged";
                                        }

                                        leaf dpd-ack-packets-received-errors {
                                            type yang:counter32;
                                            description "The number of malformed DPD R-U-THERE acknowledgement packets received";
                                        }

                                    } // container statistics

                                } // container ike-sa

                            } // container dynamic

                        } // container key-exchange

                        list ipsec-sa {
                            key "security-association direction index";
                            description "Enter the ipsec-sa list instance";

                            leaf security-association {
                                type uint32 {
                                    range "1..16";
                                }
                                description "The unique identifier of an security association (SA).";
                            }

                            leaf direction {
                                type enumeration {
                                    enum "inbound"                      { value 1; }
                                    enum "outbound"                     { value 2; }
                                }
                                description "The direction on the IPsec tunnel to which this SA can be applied.";
                            }

                            leaf index {
                                type uint32 {
                                    range "1..2";
                                }
                                description "The unique identifier of an security association (SA).";
                            }

                            leaf spi {
                                type uint32;
                                description
                                    "The SPI (Security Parameter Index) used to lookup the instruction to verify and decrypt
                                     the incoming IPsec packets when the value of direction is 'inbound'.";
                            }

                            leaf authentication-algorithm {
                                type types-ipsec:auth-algorithms;
                                description "The authentication algorithm used with this SA.";
                            }

                            leaf encryption-algorithm {
                                type types-ipsec:encryption-algorithms;
                                description "The encryption algorithm used with this SA.";
                            }

                            leaf established-time {
                                type yang:date-and-time;
                                description "The time when the IPsec SA negotiation completed.";
                            }

                            leaf negotiated-lifetime {
                                type types-sros:time-duration;
                                description "The lifetime negotiated for the IPsec SA.";
                            }

                            leaf security-association-type {
                                type types-ipsec:keying-type;
                                description
                                    "Whether this SA entry is created manually by the user or
                                     dynamically by the IPsec subsystem.";
                            }

                            container isa {
                                description "Enter the isa context";

                                leaf pfs-dh-group {
                                    type types-ipsec:dh-group;
                                    description "The Diffie-Hellman (DH) group used with this SA";
                                }

                                leaf extended-sequence-number {
                                    type boolean;
                                    description "The value 'true' indicates ESN is enabled for this SA";
                                }

                                container fragmentation {
                                    description "Enter the fragmentation context";

                                    leaf encapsulation-overhead {
                                        type uint32;
                                        description "The encapsulation overhead for this outbound SA.";
                                    }

                                } // container fragmentation

                                container statistics {
                                    description "Enter the statistics context";

                                    leaf bytes-processed {
                                        type yang:counter64;
                                        description "The number of bytes successfully processed for this SA";
                                    }

                                    leaf packets-processed {
                                        type yang:counter64;
                                        description "The the number of packets successfully processed for this SA";
                                    }

                                    container errors {
                                        description "Enter the errors context";

                                        leaf crypto {
                                            type yang:counter32;
                                            description
                                                "The number of crypto errors encountered on this SA.
                                                     
                                                 When the value of direction is 'inbound', the crypto-errors will be set for the following errors:
                                                     MAC miscompare
                                                     Pad errors
                                                     Illegal configure algorithm
                                                     Illegal authentication algorithm
                                                     Inner IP checksum errors
                                                     Payload alignment errors
                                                     Sequence number errors
                                                     Protocol errors
                                                      
                                                 When the value of direction is 'outbound', the crypto-errors will be set for the following errors:
                                                     Sequence wrap errors
                                                     Illegal configure algorithm
                                                     Illegal authentication algorithm
                                                     Expanded packet too big
                                                     TTL decrement errors.";
                                        }

                                        leaf replay {
                                            type yang:counter32;
                                            description "The number of replay errors encountered on this SA";
                                        }

                                        leaf security-association {
                                            type yang:counter32;
                                            description
                                                "The number of SA errors encountered on this SA.
                                                 The SA errors means ISA tried to use a CHILD SA that is marked for deletion.";
                                        }

                                        leaf policy {
                                            type yang:counter32;
                                            description
                                                "The number of policy errors encountered on this SA.
                                                 The policy errors include bundled SA, selector check and policy direction error.";
                                        }

                                    } // container errors

                                } // container statistics

                            } // container isa

                        } // list ipsec-sa

                        list dest-ip {
                            key "dest-ip-address";
                            description "Enter the dest-ip list instance";

                            leaf dest-ip-address {
                                type types-sros:ip-address;
                                description "IP address of the remote IP tunnel endpoint";
                            }

                            leaf dest-ip-address-resolved {
                                type boolean;
                                description
                                    "IP tunnel destination address has been resolved
                                     as reachable by the virtual router";
                            }

                        } // list dest-ip

                    } // list ip-tunnel

                    list ipsec-gateway {
                        key "name";
                        description "Enter the ipsec-gateway list instance";

                        leaf name {
                            type types-sros:named-item;
                            description "IPsec gateway name";
                        }

                        leaf oper-flags {
                            type bits {
                                bit local-ip-unreachable           { position 0; }
                                bit gateway-admin-down             { position 1; }
                                bit x509-cert-unavailable          { position 2; }
                                bit private-key-unavailable        { position 3; }
                                bit ca-cert-unavailable            { position 4; }
                                bit ca-crl-unavailable             { position 5; }
                                bit trust-anchors-down             { position 6; }
                                bit cert-profile-down              { position 7; }
                                bit invalid-cert-key-combo         { position 8; }
                                bit ike-not-ready                  { position 9; }
                            }
                            description "The reason why the IPsec gateway is operationally down.";
                        }

                        leaf oper-state {
                            type types-ipsec:oper-state;
                            description "The operational status of this IPsec gateway.";
                        }

                        container statistics {
                            description "Enter the statistics context";

                            leaf dynamic-lan-to-lan-tunnels {
                                type yang:gauge32;
                                description
                                    "The number of dynamic LAN-to-LAN (SL2L) tunnels associated
                                     with this IPsec gateway.";
                            }

                            leaf remote-access-tunnels {
                                type yang:gauge32;
                                description
                                    "The number of remote access (RA) tunnels associated
                                     to this IPsec gateway";
                            }

                            container number-of-tunnels {
                                description "Enter the number-of-tunnels context";

                                container current {
                                    description "Enter the current context";

                                    leaf dynamic-lan-to-lan {
                                        type yang:counter64;
                                        description "Number of IPsec dynamic LAN-to-LAN (DL2L) tunnels.";
                                    }

                                    leaf remote-access {
                                        type yang:counter64;
                                        description "Number of IPsec remote access (RA) tunnels.";
                                    }

                                    leaf total {
                                        type yang:counter64;
                                        description "Total number of IPsec tunnels.";
                                    }

                                    leaf start-time {
                                        type yang:date-and-time;
                                        description "The time when the sampling interval started.";
                                    }

                                } // container current

                                list historical {
                                    key "index";
                                    description "Enter the historical list instance";

                                    leaf index {
                                        type uint32 {
                                            range "2..max";
                                        }
                                        description
                                            "The index of the finished sampling interval period for this statistic.
                                             It starts with '2' and is ordered by start time of intervals so that
                                             smaller index indicate more recent intervals.";
                                    }

                                    leaf dynamic-lan-to-lan {
                                        type yang:counter64;
                                        description "Number of IPsec dynamic LAN-to-LAN (DL2L) tunnels.";
                                    }

                                    leaf remote-access {
                                        type yang:counter64;
                                        description "Number of IPsec remote access (RA) tunnels.";
                                    }

                                    leaf total {
                                        type yang:counter64;
                                        description "Total number of IPsec tunnels.";
                                    }

                                    leaf start-time {
                                        type yang:date-and-time;
                                        description "The time when the sampling interval started.";
                                    }

                                } // list historical

                            } // container number-of-tunnels

                            container throughput {
                                description "Enter the throughput context";

                                container current {
                                    description "Enter the current context";

                                    leaf start-time {
                                        type yang:date-and-time;
                                        description "The time when the sampling interval started.";
                                    }

                                    leaf sampling-duration {
                                        type types-sros:time-duration;
                                        description "The duration of the corresponding sampling interval.";
                                    }

                                    container packets {
                                        description "Enter the packets context";

                                        leaf encrypted {
                                            type yang:counter64;
                                            units "packets per second";
                                            description "Encrypted IPsec traffic throughput.";
                                        }

                                        leaf decrypted {
                                            type yang:counter64;
                                            units "packets per second";
                                            description "Decrypted IPsec traffic throughput.";
                                        }

                                        leaf total {
                                            type yang:counter64;
                                            units "packets per second";
                                            description "Encrypted and decrypted IPsec traffic throughput.";
                                        }

                                    } // container packets

                                    container bytes {
                                        description "Enter the bytes context";

                                        leaf encrypted {
                                            type yang:counter64;
                                            units "megabps";
                                            description "Encrypted IPsec traffic throughput.";
                                        }

                                        leaf decrypted {
                                            type yang:counter64;
                                            units "megabps";
                                            description "Decrypted IPsec traffic throughput.";
                                        }

                                        leaf total {
                                            type yang:counter64;
                                            units "megabps";
                                            description "Encrypted and decrypted IPsec traffic throughput.";
                                        }

                                    } // container bytes

                                } // container current

                                list historical {
                                    key "index";
                                    description "Enter the historical list instance";

                                    leaf index {
                                        type uint32 {
                                            range "2..max";
                                        }
                                        description
                                            "The index of the finished sampling interval period for this statistic.
                                             It starts with '2' and is ordered by start time of intervals so that
                                             smaller index indicate more recent intervals.";
                                    }

                                    leaf start-time {
                                        type yang:date-and-time;
                                        description "The time when the sampling interval started.";
                                    }

                                    leaf sampling-duration {
                                        type types-sros:time-duration;
                                        description "The duration of the corresponding sampling interval.";
                                    }

                                    container packets {
                                        description "Enter the packets context";

                                        leaf encrypted {
                                            type yang:counter64;
                                            units "packets per second";
                                            description "Encrypted IPsec traffic throughput.";
                                        }

                                        leaf decrypted {
                                            type yang:counter64;
                                            units "packets per second";
                                            description "Decrypted IPsec traffic throughput.";
                                        }

                                        leaf total {
                                            type yang:counter64;
                                            units "packets per second";
                                            description "Encrypted and decrypted IPsec traffic throughput.";
                                        }

                                    } // container packets

                                    container bytes {
                                        description "Enter the bytes context";

                                        leaf encrypted {
                                            type yang:counter64;
                                            units "megabps";
                                            description "Encrypted IPsec traffic throughput.";
                                        }

                                        leaf decrypted {
                                            type yang:counter64;
                                            units "megabps";
                                            description "Decrypted IPsec traffic throughput.";
                                        }

                                        leaf total {
                                            type yang:counter64;
                                            units "megabps";
                                            description "Encrypted and decrypted IPsec traffic throughput.";
                                        }

                                    } // container bytes

                                } // list historical

                            } // container throughput

                            container tunnel-setup-rate {
                                description "Enter the tunnel-setup-rate context";

                                container current {
                                    description "Enter the current context";

                                    leaf total {
                                        type decimal64 {
                                            fraction-digits 2;
                                        }
                                        units "tunnels per second";
                                        description "Total IPsec tunnel setup rate.";
                                    }

                                    leaf dynamic-lan-to-lan {
                                        type decimal64 {
                                            fraction-digits 2;
                                        }
                                        units "tunnels per second";
                                        description "Dynamic LAN-to-LAN (DL2L) tunnel setup rate.";
                                    }

                                    leaf remote-access {
                                        type decimal64 {
                                            fraction-digits 2;
                                        }
                                        units "tunnels per second";
                                        description "Remote access (RA) tunnel setup rate.";
                                    }

                                    leaf start-time {
                                        type yang:date-and-time;
                                        description "The time when the sampling interval started.";
                                    }

                                    leaf sampling-duration {
                                        type types-sros:time-duration;
                                        description "The duration of the corresponding sampling interval.";
                                    }

                                } // container current

                                list historical {
                                    key "index";
                                    description "Enter the historical list instance";

                                    leaf index {
                                        type uint32 {
                                            range "2..max";
                                        }
                                        description
                                            "The index of the finished sampling interval period for this statistic.
                                             It starts with '2' and is ordered by start time of intervals so that
                                             smaller index indicate more recent intervals.";
                                    }

                                    leaf total {
                                        type decimal64 {
                                            fraction-digits 2;
                                        }
                                        units "tunnels per second";
                                        description "Total IPsec tunnel setup rate.";
                                    }

                                    leaf dynamic-lan-to-lan {
                                        type decimal64 {
                                            fraction-digits 2;
                                        }
                                        units "tunnels per second";
                                        description "Dynamic LAN-to-LAN (DL2L) tunnel setup rate.";
                                    }

                                    leaf remote-access {
                                        type decimal64 {
                                            fraction-digits 2;
                                        }
                                        units "tunnels per second";
                                        description "Remote access (RA) tunnel setup rate.";
                                    }

                                    leaf start-time {
                                        type yang:date-and-time;
                                        description "The time when the sampling interval started.";
                                    }

                                    leaf sampling-duration {
                                        type types-sros:time-duration;
                                        description "The duration of the corresponding sampling interval.";
                                    }

                                } // list historical

                            } // container tunnel-setup-rate

                            container traffic-forward {
                                description "Enter the traffic-forward context";

                                container current {
                                    description "Enter the current context";

                                    leaf start-time {
                                        type yang:date-and-time;
                                        description "The time when the sampling interval started.";
                                    }

                                    leaf sampling-duration {
                                        type types-sros:time-duration;
                                        description "The duration of the corresponding sampling interval.";
                                    }

                                    container packets {
                                        description "Enter the packets context";

                                        leaf encrypted {
                                            type yang:counter64;
                                            units "packets";
                                            description "Number of encrypted IPsec packets.";
                                        }

                                        leaf decrypted {
                                            type yang:counter64;
                                            units "packets";
                                            description "Number of decrypted IPsec packets.";
                                        }

                                        leaf total {
                                            type yang:counter64;
                                            units "packets";
                                            description "Number of encrypted and decrypted IPsec packets.";
                                        }

                                    } // container packets

                                    container bytes {
                                        description "Enter the bytes context";

                                        leaf encrypted {
                                            type yang:counter64;
                                            units "kilobytes";
                                            description "Number of kilobytes in the encrypted IPsec packets.";
                                        }

                                        leaf decrypted {
                                            type yang:counter64;
                                            units "kilobytes";
                                            description "Number of kilobytes in the decrypted IPsec packets.";
                                        }

                                        leaf total {
                                            type yang:counter64;
                                            units "kilobytes";
                                            description "Number of kilobytes in the encrypted and decrypted IPsec packets.";
                                        }

                                    } // container bytes

                                } // container current

                            } // container traffic-forward

                            container ike-exchange-failure-rate {
                                description "Enter the ike-exchange-failure-rate context";

                                container current {
                                    description "Enter the current context";

                                    leaf start-time {
                                        type yang:date-and-time;
                                        description "The time when the sampling interval started.";
                                    }

                                    leaf sampling-duration {
                                        type types-sros:time-duration;
                                        description "The duration of the corresponding sampling interval.";
                                    }

                                    container auth-failure {
                                        description "Enter the auth-failure context";

                                        leaf count {
                                            type decimal64 {
                                                fraction-digits 2;
                                            }
                                            units "failures per second";
                                            description "IKE exchange failure rate - authentication.";
                                        }

                                        leaf first-failure {
                                            type yang:date-and-time;
                                            description
                                                "The time when the first IKE exchange failure happened
                                                 in the corresponding sampling interval.";
                                        }

                                        leaf first-failure-description {
                                            type types-sros:long-description;
                                            description "The description of the place where the first IKE exchange failure happened.";
                                        }

                                        leaf last-failure {
                                            type yang:date-and-time;
                                            description
                                                "The time when the last IKE exchange failure happened
                                                 in the corresponding sampling interval.";
                                        }

                                        leaf last-failure-description {
                                            type types-sros:long-description;
                                            description "The description of the place where the last IKE exchange failure happened.";
                                        }

                                    } // container auth-failure

                                    container non-proposal-chosen {
                                        description "Enter the non-proposal-chosen context";

                                        leaf count {
                                            type decimal64 {
                                                fraction-digits 2;
                                            }
                                            units "failures per second";
                                            description "IKE exchange failure rate - non-proposal chosen.";
                                        }

                                        leaf first-failure {
                                            type yang:date-and-time;
                                            description
                                                "The time when the first IKE exchange failure happened
                                                 in the corresponding sampling interval.";
                                        }

                                        leaf first-failure-description {
                                            type types-sros:long-description;
                                            description "The description of the place where the first IKE exchange failure happened.";
                                        }

                                        leaf last-failure {
                                            type yang:date-and-time;
                                            description
                                                "The time when the last IKE exchange failure happened
                                                 in the corresponding sampling interval.";
                                        }

                                        leaf last-failure-description {
                                            type types-sros:long-description;
                                            description "The description of the place where the last IKE exchange failure happened.";
                                        }

                                    } // container non-proposal-chosen

                                    container internal-address-assignment {
                                        description "Enter the internal-address-assignment context";

                                        leaf count {
                                            type decimal64 {
                                                fraction-digits 2;
                                            }
                                            units "failures per second";
                                            description "IKE exchange failure rate - address assignment.";
                                        }

                                        leaf first-failure {
                                            type yang:date-and-time;
                                            description
                                                "The time when the first IKE exchange failure happened
                                                 in the corresponding sampling interval.";
                                        }

                                        leaf first-failure-description {
                                            type types-sros:long-description;
                                            description "The description of the place where the first IKE exchange failure happened.";
                                        }

                                        leaf last-failure {
                                            type yang:date-and-time;
                                            description
                                                "The time when the last IKE exchange failure happened
                                                 in the corresponding sampling interval.";
                                        }

                                        leaf last-failure-description {
                                            type types-sros:long-description;
                                            description "The description of the place where the last IKE exchange failure happened.";
                                        }

                                    } // container internal-address-assignment

                                    container invalid-ts {
                                        description "Enter the invalid-ts context";

                                        leaf count {
                                            type decimal64 {
                                                fraction-digits 2;
                                            }
                                            units "failures per second";
                                            description "IKE exchange failure rate - invalid traffic selector.";
                                        }

                                        leaf first-failure {
                                            type yang:date-and-time;
                                            description
                                                "The time when the first IKE exchange failure happened
                                                 in the corresponding sampling interval.";
                                        }

                                        leaf first-failure-description {
                                            type types-sros:long-description;
                                            description "The description of the place where the first IKE exchange failure happened.";
                                        }

                                        leaf last-failure {
                                            type yang:date-and-time;
                                            description
                                                "The time when the last IKE exchange failure happened
                                                 in the corresponding sampling interval.";
                                        }

                                        leaf last-failure-description {
                                            type types-sros:long-description;
                                            description "The description of the place where the last IKE exchange failure happened.";
                                        }

                                    } // container invalid-ts

                                    container invalid-ke {
                                        description "Enter the invalid-ke context";

                                        leaf count {
                                            type decimal64 {
                                                fraction-digits 2;
                                            }
                                            units "failures per second";
                                            description "IKE exchange failure rate - invalid key exchange.";
                                        }

                                        leaf first-failure {
                                            type yang:date-and-time;
                                            description
                                                "The time when the first IKE exchange failure happened
                                                 in the corresponding sampling interval.";
                                        }

                                        leaf first-failure-description {
                                            type types-sros:long-description;
                                            description "The description of the place where the first IKE exchange failure happened.";
                                        }

                                        leaf last-failure {
                                            type yang:date-and-time;
                                            description
                                                "The time when the last IKE exchange failure happened
                                                 in the corresponding sampling interval.";
                                        }

                                        leaf last-failure-description {
                                            type types-sros:long-description;
                                            description "The description of the place where the last IKE exchange failure happened.";
                                        }

                                    } // container invalid-ke

                                    container dpd-timeout {
                                        description "Enter the dpd-timeout context";

                                        leaf count {
                                            type decimal64 {
                                                fraction-digits 2;
                                            }
                                            units "failures per second";
                                            description "IKE exchange failure rate - DPD timeout.";
                                        }

                                        leaf first-failure {
                                            type yang:date-and-time;
                                            description
                                                "The time when the first IKE exchange failure happened
                                                 in the corresponding sampling interval.";
                                        }

                                        leaf first-failure-description {
                                            type types-sros:long-description;
                                            description "The description of the place where the first IKE exchange failure happened.";
                                        }

                                        leaf last-failure {
                                            type yang:date-and-time;
                                            description
                                                "The time when the last IKE exchange failure happened
                                                 in the corresponding sampling interval.";
                                        }

                                        leaf last-failure-description {
                                            type types-sros:long-description;
                                            description "The description of the place where the last IKE exchange failure happened.";
                                        }

                                    } // container dpd-timeout

                                    container other {
                                        description "Enter the other context";

                                        leaf count {
                                            type decimal64 {
                                                fraction-digits 2;
                                            }
                                            units "failures per second";
                                            description "IKE exchange failure rate - other failure reasons.";
                                        }

                                        leaf first-failure {
                                            type yang:date-and-time;
                                            description
                                                "The time when the first IKE exchange failure happened
                                                 in the corresponding sampling interval.";
                                        }

                                        leaf first-failure-description {
                                            type types-sros:long-description;
                                            description "The description of the place where the first IKE exchange failure happened.";
                                        }

                                        leaf last-failure {
                                            type yang:date-and-time;
                                            description
                                                "The time when the last IKE exchange failure happened
                                                 in the corresponding sampling interval.";
                                        }

                                        leaf last-failure-description {
                                            type types-sros:long-description;
                                            description "The description of the place where the last IKE exchange failure happened.";
                                        }

                                    } // container other

                                } // container current

                                list historical {
                                    key "index";
                                    description "Enter the historical list instance";

                                    leaf index {
                                        type uint32 {
                                            range "2..max";
                                        }
                                        description
                                            "The index of the finished sampling interval period for this statistic.
                                             It starts with '2' and is ordered by start time of intervals so that
                                             smaller index indicate more recent intervals.";
                                    }

                                    leaf start-time {
                                        type yang:date-and-time;
                                        description "The time when the sampling interval started.";
                                    }

                                    leaf sampling-duration {
                                        type types-sros:time-duration;
                                        description "The duration of the corresponding sampling interval.";
                                    }

                                    container auth-failure {
                                        description "Enter the auth-failure context";

                                        leaf count {
                                            type decimal64 {
                                                fraction-digits 2;
                                            }
                                            units "failures per second";
                                            description "IKE exchange failure rate - authentication.";
                                        }

                                        leaf first-failure {
                                            type yang:date-and-time;
                                            description
                                                "The time when the first IKE exchange failure happened
                                                 in the corresponding sampling interval.";
                                        }

                                        leaf first-failure-description {
                                            type types-sros:long-description;
                                            description "The description of the place where the first IKE exchange failure happened.";
                                        }

                                        leaf last-failure {
                                            type yang:date-and-time;
                                            description
                                                "The time when the last IKE exchange failure happened
                                                 in the corresponding sampling interval.";
                                        }

                                        leaf last-failure-description {
                                            type types-sros:long-description;
                                            description "The description of the place where the last IKE exchange failure happened.";
                                        }

                                    } // container auth-failure

                                    container non-proposal-chosen {
                                        description "Enter the non-proposal-chosen context";

                                        leaf count {
                                            type decimal64 {
                                                fraction-digits 2;
                                            }
                                            units "failures per second";
                                            description "IKE exchange failure rate - non-proposal chosen.";
                                        }

                                        leaf first-failure {
                                            type yang:date-and-time;
                                            description
                                                "The time when the first IKE exchange failure happened
                                                 in the corresponding sampling interval.";
                                        }

                                        leaf first-failure-description {
                                            type types-sros:long-description;
                                            description "The description of the place where the first IKE exchange failure happened.";
                                        }

                                        leaf last-failure {
                                            type yang:date-and-time;
                                            description
                                                "The time when the last IKE exchange failure happened
                                                 in the corresponding sampling interval.";
                                        }

                                        leaf last-failure-description {
                                            type types-sros:long-description;
                                            description "The description of the place where the last IKE exchange failure happened.";
                                        }

                                    } // container non-proposal-chosen

                                    container internal-address-assignment {
                                        description "Enter the internal-address-assignment context";

                                        leaf count {
                                            type decimal64 {
                                                fraction-digits 2;
                                            }
                                            units "failures per second";
                                            description "IKE exchange failure rate - address assignment.";
                                        }

                                        leaf first-failure {
                                            type yang:date-and-time;
                                            description
                                                "The time when the first IKE exchange failure happened
                                                 in the corresponding sampling interval.";
                                        }

                                        leaf first-failure-description {
                                            type types-sros:long-description;
                                            description "The description of the place where the first IKE exchange failure happened.";
                                        }

                                        leaf last-failure {
                                            type yang:date-and-time;
                                            description
                                                "The time when the last IKE exchange failure happened
                                                 in the corresponding sampling interval.";
                                        }

                                        leaf last-failure-description {
                                            type types-sros:long-description;
                                            description "The description of the place where the last IKE exchange failure happened.";
                                        }

                                    } // container internal-address-assignment

                                    container invalid-ts {
                                        description "Enter the invalid-ts context";

                                        leaf count {
                                            type decimal64 {
                                                fraction-digits 2;
                                            }
                                            units "failures per second";
                                            description "IKE exchange failure rate - invalid traffic selector.";
                                        }

                                        leaf first-failure {
                                            type yang:date-and-time;
                                            description
                                                "The time when the first IKE exchange failure happened
                                                 in the corresponding sampling interval.";
                                        }

                                        leaf first-failure-description {
                                            type types-sros:long-description;
                                            description "The description of the place where the first IKE exchange failure happened.";
                                        }

                                        leaf last-failure {
                                            type yang:date-and-time;
                                            description
                                                "The time when the last IKE exchange failure happened
                                                 in the corresponding sampling interval.";
                                        }

                                        leaf last-failure-description {
                                            type types-sros:long-description;
                                            description "The description of the place where the last IKE exchange failure happened.";
                                        }

                                    } // container invalid-ts

                                    container invalid-ke {
                                        description "Enter the invalid-ke context";

                                        leaf count {
                                            type decimal64 {
                                                fraction-digits 2;
                                            }
                                            units "failures per second";
                                            description "IKE exchange failure rate - invalid key exchange.";
                                        }

                                        leaf first-failure {
                                            type yang:date-and-time;
                                            description
                                                "The time when the first IKE exchange failure happened
                                                 in the corresponding sampling interval.";
                                        }

                                        leaf first-failure-description {
                                            type types-sros:long-description;
                                            description "The description of the place where the first IKE exchange failure happened.";
                                        }

                                        leaf last-failure {
                                            type yang:date-and-time;
                                            description
                                                "The time when the last IKE exchange failure happened
                                                 in the corresponding sampling interval.";
                                        }

                                        leaf last-failure-description {
                                            type types-sros:long-description;
                                            description "The description of the place where the last IKE exchange failure happened.";
                                        }

                                    } // container invalid-ke

                                    container dpd-timeout {
                                        description "Enter the dpd-timeout context";

                                        leaf count {
                                            type decimal64 {
                                                fraction-digits 2;
                                            }
                                            units "failures per second";
                                            description "IKE exchange failure rate - DPD timeout.";
                                        }

                                        leaf first-failure {
                                            type yang:date-and-time;
                                            description
                                                "The time when the first IKE exchange failure happened
                                                 in the corresponding sampling interval.";
                                        }

                                        leaf first-failure-description {
                                            type types-sros:long-description;
                                            description "The description of the place where the first IKE exchange failure happened.";
                                        }

                                        leaf last-failure {
                                            type yang:date-and-time;
                                            description
                                                "The time when the last IKE exchange failure happened
                                                 in the corresponding sampling interval.";
                                        }

                                        leaf last-failure-description {
                                            type types-sros:long-description;
                                            description "The description of the place where the last IKE exchange failure happened.";
                                        }

                                    } // container dpd-timeout

                                    container other {
                                        description "Enter the other context";

                                        leaf count {
                                            type decimal64 {
                                                fraction-digits 2;
                                            }
                                            units "failures per second";
                                            description "IKE exchange failure rate - other failure reasons.";
                                        }

                                        leaf first-failure {
                                            type yang:date-and-time;
                                            description
                                                "The time when the first IKE exchange failure happened
                                                 in the corresponding sampling interval.";
                                        }

                                        leaf first-failure-description {
                                            type types-sros:long-description;
                                            description "The description of the place where the first IKE exchange failure happened.";
                                        }

                                        leaf last-failure {
                                            type yang:date-and-time;
                                            description
                                                "The time when the last IKE exchange failure happened
                                                 in the corresponding sampling interval.";
                                        }

                                        leaf last-failure-description {
                                            type types-sros:long-description;
                                            description "The description of the place where the last IKE exchange failure happened.";
                                        }

                                    } // container other

                                } // list historical

                            } // container ike-exchange-failure-rate

                        } // container statistics

                        list dynamic-tunnel {
                            key "address port";
                            description "Enter the dynamic-tunnel list instance";

                            leaf address {
                                type types-sros:ip-address;
                                description "The address of the SAP IPsec gateway to the tunnel";
                            }

                            leaf port {
                                type types-sros:tcp-udp-port;
                                description "The UDP port of the SAP IPsec gateway to the tunnel";
                            }

                            leaf private-service-name {
                                type types-services:service-name;
                                description "The name of the Tunnel delivery service.";
                            }

                            leaf private-interface-name {
                                type types-sros:interface-name;
                                description "The private interface name used by the tunnel";
                            }

                            leaf private-address {
                                type types-sros:ip-address;
                                description "The private IP address on the IPsec gateway tunnel";
                            }

                            leaf second-private-address {
                                type types-sros:ip-address;
                                description "The second private IP address on the IPsec gateway tunnel";
                            }

                            leaf tunnel-template {
                                type types-ipsec:tunnel-template-id;
                                description "The id of a tunnel template entry used for the tunnel";
                            }

                            leaf replay-window {
                                type uint32 {
                                    range "32|64|128|256|512";
                                }
                                description "The size of the anti-replay window";
                            }

                            leaf bi-direction-sa {
                                type boolean;
                                description "Indicates whether this tunnel has bi-directional Security-Association entries.";
                            }

                            leaf host-mda {
                                type types-isa:slot-mda;
                                description "Active ISA that is being used to host this tunnel";
                            }

                            leaf matched-trust-anchor {
                                type types-sros:named-item;
                                description
                                    "The name for matched Certificate-Authority Profile name associated
                                     with this SAP IPSec tunnel certificate.";
                            }

                            leaf last-oper-changed {
                                type yang:date-and-time;
                                description "Uptime at the time of the last operational status change of this IPsec gateway tunnel";
                            }

                            leaf ike-idi-type {
                                type enumeration {
                                    enum "ipv4-addr"                    { value 1; }
                                    enum "fqdn"                         { value 2; }
                                    enum "rfc-822-addr"                 { value 3; }
                                    enum "ipv6-addr"                    { value 5; }
                                    enum "der-asn1-dn"                  { value 9; }
                                    enum "der-asn1-gn"                  { value 10; }
                                    enum "key-id"                       { value 11; }
                                }
                                description "The direction on the IPsec tunnel to which this SA can be applied.";
                            }

                            leaf ike-idi-value {
                                type types-sros:display-string;
                                description "The ID type for the IKE header used in the tunnel associated with this entry.";
                            }

                            leaf ts-list {
                                type types-sros:named-item;
                                description "The traffic selector (TS) list used by this tunnel.";
                            }

                            leaf ike-policy {
                                type types-ipsec:ike-policy-id;
                                description "The IKE policy identifier used by this tunnel.";
                            }

                            container tcp-mss {
                                description "Enter the tcp-mss context";

                                leaf public {
                                    type uint32;
                                    units "bytes";
                                    description
                                        "The Maximum Segment Size (MSS) for the TCP traffic in an IPsec tunnel
                                         which is sent from the public network to the private network.";
                                }

                                leaf private {
                                    type uint32;
                                    units "bytes";
                                    description
                                        "The Maximum Segment Size (MSS) for the TCP traffic in an IPsec tunnel
                                         which is sent from the private network to the public network.";
                                }

                            } // container tcp-mss

                            container ike-sa {
                                description "Enter the ike-sa context";

                                leaf oper-state {
                                    type enumeration {
                                        enum "up"                           { value 1; }
                                        enum "down"                         { value 2; }
                                    }
                                    description "The state of IKE SA";
                                }

                                leaf established-time {
                                    type yang:date-and-time;
                                    description "The time the IKE SA completed";
                                }

                                leaf negotiated-lifetime {
                                    type types-sros:time-duration;
                                    description "The lifetime negotiated for the IKE SA";
                                }

                                leaf expiration-time {
                                    type yang:date-and-time;
                                    description "The time when the IKE SA will expire";
                                }

                                leaf authentication-algorithm {
                                    type types-ipsec:auth-algorithms;
                                    description "The authentication algorithm of the IKE SA for this IPsec tunnel";
                                }

                                leaf encryption-algorithm {
                                    type types-ipsec:encryption-algorithms;
                                    description "The encryption algorithm of the IKE SA for this IPsec tunnel";
                                }

                                leaf prf-algorithm {
                                    type types-ipsec:prf-algorithms;
                                    description "The pseudo-random function (PRF)";
                                }

                                leaf dh-group {
                                    type types-ipsec:dh-group;
                                    description "The Diffie-Hellman (DH) group of the IKE SA for this IPsec tunnel";
                                }

                                leaf cert-profile-entry-id {
                                    type uint32;
                                    description "The matching certificate profile entry id used for this tunnel";
                                }

                                leaf cert-profile-name {
                                    type types-sros:named-item;
                                    description "The IPsec tunnel certificate profile name used for this tunnel";
                                }

                                leaf client-database {
                                    type uint32 {
                                        range "1..8000";
                                    }
                                    description "The client ID that was matched for this tunnel in the IPsec client database";
                                }

                                container statistics {
                                    description "Enter the statistics context";

                                    leaf ctrl-packets-sent {
                                        type yang:counter32;
                                        description "The number of control packets this IPsec Tunnel has sent";
                                    }

                                    leaf ctrl-packets-received {
                                        type yang:counter32;
                                        description "The number of control packets this IPsec Tunnel has received";
                                    }

                                    leaf ctrl-packets-sent-errors {
                                        type yang:counter32;
                                        description "The number of control packet transmit errors";
                                    }

                                    leaf ctrl-packets-received-errors {
                                        type yang:counter32;
                                        description "The number of control packet receive errors";
                                    }

                                    leaf dpd-packets-sent {
                                        type yang:counter32;
                                        description "The number of number of Dead-Peer-Detection packets transmitted";
                                    }

                                    leaf dpd-packets-received {
                                        type yang:counter32;
                                        description "The number of Dead-Peer-Detection packets received";
                                    }

                                    leaf dpd-ack-packets-sent {
                                        type yang:counter32;
                                        description "The number of Dead-Peer-Detection acknowledgement packets transmitted";
                                    }

                                    leaf dpd-ack-packets-received {
                                        type yang:counter32;
                                        description "The number of Dead-Peer-Detection acknowledgement packets received";
                                    }

                                    leaf dpd-timeout-packets {
                                        type yang:counter32;
                                        description "The number of DPD R-U-THERE packets that have not been acknowledged";
                                    }

                                    leaf dpd-ack-packets-received-errors {
                                        type yang:counter32;
                                        description "The number of malformed DPD R-U-THERE acknowledgement packets received";
                                    }

                                } // container statistics

                            } // container ike-sa

                            list ipsec-sa {
                                key "security-association direction index";
                                description "Enter the ipsec-sa list instance";

                                leaf security-association {
                                    type uint32 {
                                        range "1..16";
                                    }
                                    description "The unique identifier of an security association (SA).";
                                }

                                leaf direction {
                                    type types-ipsec:direction;
                                    description "The direction on the IPsec tunnel to which this SA can be applied.";
                                }

                                leaf index {
                                    type uint32 {
                                        range "1..2";
                                    }
                                    description "The unique identifier of an security association (SA).";
                                }

                                leaf spi {
                                    type uint32;
                                    description
                                        "The SPI (Security Parameter Index) used to lookup the instruction to verify and decrypt
                                         the incoming IPsec packets when the value of direction is 'inbound'.";
                                }

                                leaf authentication-algorithm {
                                    type types-ipsec:auth-algorithms;
                                    description "The authentication algorithm used with this SA.";
                                }

                                leaf encryption-algorithm {
                                    type types-ipsec:encryption-algorithms;
                                    description "The encryption algorithm used with this SA.";
                                }

                                leaf established-time {
                                    type yang:date-and-time;
                                    description "The time when the IPsec SA negotiation completed.";
                                }

                                leaf negotiated-lifetime {
                                    type types-sros:time-duration;
                                    description "The lifetime negotiated for the IPsec SA.";
                                }

                                list ts {
                                    key "side from-address to-address min-port max-port protocol-id";
                                    description "Enter the ts list instance";

                                    leaf side {
                                        type types-ipsec:ts-side;
                                        description
                                            "Whether this SA entry is created manually by the user or
                                             dynamically by the IPsec subsystem.";
                                    }

                                    leaf from-address {
                                        type types-sros:ip-address;
                                        description "The beginning address of the range for this traffic selector entry.";
                                    }

                                    leaf to-address {
                                        type types-sros:ip-address;
                                        description "The end address of the range for this traffic selector entry.";
                                    }

                                    leaf min-port {
                                        type types-sros:tcp-udp-port;
                                        description
                                            "The minimum port number of the range for this IPsec traffic selector entry.

                                             When the value of min-port is 0 and the value of max-port is 65535,
                                             it means that the IPsec traffic selector accepts any port number.

                                             When the value of protocol-id is 1 (ICMP) or 58 (ICMPv6), the bits from 0 to 7 of min-port
                                             represent the minimum ICMP/ICMPv6 code and the bits from 8 to 15
                                             represent the minimum ICMP/ICMPv6 type.";
                                    }

                                    leaf max-port {
                                        type types-sros:tcp-udp-port;
                                        description
                                            "The maximum port number of the range for this IPsec traffic selector entry.

                                             When the value of max-port is 0 and the value of min-port is 65535,
                                             it means that the IPsec traffic selector accepts the packet only when the
                                             corresponding port field is unavailable.

                                             When the value of protocol-id is 1 (ICMP) or 58 (ICMPv6), the bits from 0 to 7 of max-port
                                             represent the maximum ICMP/ICMPv6 code and the bits from 8 to 15
                                             represent the maximum ICMP/ICMPv6 type.";
                                    }

                                    leaf protocol-id {
                                        type uint32 {
                                            range "0..255";
                                        }
                                        description
                                            "The IP protocol number for this IPsec traffic selector entry.

                                             A value of zero specifies that the IPsec traffic selector will accept
                                             packets for any protocol.";
                                    }

                                } // list ts

                                container isa {
                                    description "Enter the isa context";

                                    leaf multicast-interface-name {
                                        type types-sros:named-item;
                                        description "The multicast interface name associated with this SA";
                                    }

                                    leaf multicast-protocol {
                                        type types-ipsec:multicast-protocol;
                                        description "The supported protocol types of the multicast interface associated to this SA";
                                    }

                                    leaf pfs-dh-group {
                                        type types-ipsec:dh-group;
                                        description "The Diffie-Hellman (DH) group used with this SA";
                                    }

                                    leaf extended-sequence-number {
                                        type boolean;
                                        description "The value 'true' indicates ESN is enabled for this SA";
                                    }

                                    container fragmentation {
                                        description "Enter the fragmentation context";

                                        leaf encapsulation-overhead {
                                            type uint32;
                                            description "The encapsulation overhead for this outbound SA.";
                                        }

                                        leaf temporary-private-mtu {
                                            type uint32;
                                            units "bytes";
                                            description "The size of temporary private MTU for this SA.";
                                        }

                                        container pre-encapsulation {
                                            description "Enter the pre-encapsulation context";

                                            leaf last-packet-size {
                                                type uint32;
                                                units "bytes";
                                                description
                                                    "The size of the last packet which caused a pre-encapsulation fragmentation
                                                     to occur for this SA.";
                                            }

                                        } // container pre-encapsulation

                                        container post-encapsulation {
                                            description "Enter the post-encapsulation context";

                                            leaf last-packet-size {
                                                type uint32;
                                                units "bytes";
                                                description
                                                    "The size of the last encapsulated packet which caused a post-encapsulation
                                                     fragmentation to occur for this SA.";
                                            }

                                        } // container post-encapsulation

                                    } // container fragmentation

                                    container statistics {
                                        description "Enter the statistics context";

                                        leaf bytes-processed {
                                            type yang:counter64;
                                            description "The number of bytes successfully processed for this SA";
                                        }

                                        leaf packets-processed {
                                            type yang:counter64;
                                            description "The the number of packets successfully processed for this SA";
                                        }

                                        container errors {
                                            description "Enter the errors context";

                                            leaf crypto {
                                                type yang:counter32;
                                                description
                                                    "The number of crypto errors encountered on this SA.
                                                         
                                                     When the value of direction is 'inbound', the crypto-errors will be set for the following errors:
                                                         MAC miscompare
                                                         Pad errors
                                                         Illegal configure algorithm
                                                         Illegal authentication algorithm
                                                         Inner IP checksum errors
                                                         Payload alignment errors
                                                         Sequence number errors
                                                         Protocol errors
                                                          
                                                     When the value of direction is 'outbound', the crypto-errors will be set for the following errors:
                                                         Sequence wrap errors
                                                         Illegal configure algorithm
                                                         Illegal authentication algorithm
                                                         Expanded packet too big
                                                         TTL decrement errors.";
                                            }

                                            leaf replay {
                                                type yang:counter32;
                                                description "The number of replay errors encountered on this SA";
                                            }

                                            leaf security-association {
                                                type yang:counter32;
                                                description
                                                    "The number of SA errors encountered on this SA.
                                                     The SA errors means ISA tried to use a CHILD SA that is marked for deletion.";
                                            }

                                            leaf policy {
                                                type yang:counter32;
                                                description
                                                    "The number of policy errors encountered on this SA.
                                                     The policy errors include bundled SA, selector check and policy direction error.";
                                            }

                                        } // container errors

                                        container fragmentation {
                                            description "Enter the fragmentation context";

                                            container pre-encapsulation {
                                                description "Enter the pre-encapsulation context";

                                                leaf count {
                                                    type yang:counter64;
                                                    description
                                                        "The number of fragmentations that occurred prior to encapsulation for this outbound SA.
                                                         Pre-encapsulation fragmentation occurs for IPv4 packets whose size exceeds tIPsecTnlTempIpMtu.";
                                                }

                                            } // container pre-encapsulation

                                            container post-encapsulation {
                                                description "Enter the post-encapsulation context";

                                                leaf count {
                                                    type yang:counter64;
                                                    description
                                                        "The number of fragmentations that occurred after encapsulation for this SA.
                                                         Post-encapsulation fragmentation occurs when the encapsulated packet size exceeds tIPsecTnlTempEncapIpMtu.";
                                                }

                                            } // container post-encapsulation

                                        } // container fragmentation

                                    } // container statistics

                                } // container isa

                            } // list ipsec-sa

                            list dhcp-lease {
                                key "private-address";
                                description "Enter the dhcp-lease list instance";

                                leaf private-address {
                                    type types-sros:ip-address;
                                    description
                                        "The private IP address of the dynamic IPsec remote user tunnel.
                                         It can be equal to either private-address or second-private-address.";
                                }

                                leaf acquired {
                                    type yang:date-and-time;
                                    description
                                        "The time when the latest DHCP lease was acquired from the server.
                                         The address of the server is indicated by server-address.

                                         The value can be the time when the private IP address for the dynamic IPsec user remote tunnel
                                         first obtained the DHCP lease, or the time when the lease was renewed or rebound.";
                                }

                                leaf renew {
                                    type yang:date-and-time;
                                    description "The time when the current DHCP lease needs to be renewed";
                                }

                                leaf rebind {
                                    type yang:date-and-time;
                                    description "The time when the current DHCP lease needs to be rebound";
                                }

                                leaf valid-lifetime {
                                    type yang:date-and-time;
                                    description
                                        "The time when the valid lifetime of the private IP address for the dynamic IPsec user remote
                                         tunnel will expire. Once the valid lifetime expires, the private IP address must be renewed or rebound.";
                                }

                                leaf preferred-lifetime {
                                    type yang:date-and-time;
                                    description
                                        "The time when the preferred lifetime of the private IP address for the dynamic IPsec user remote
                                         tunnel will expire. In the preferred state, the private IP address can be used without any restriction.
                                         Once the lifetime expires, the private IP address is still valid, but needs to be renewed or rebound.";
                                }

                                leaf server-address {
                                    type types-sros:ip-address;
                                    description "The DHCP server address";
                                }

                            } // list dhcp-lease

                            container statistics {
                                description "Enter the statistics context";

                                container traffic-forward {
                                    description "Enter the traffic-forward context";

                                    container current {
                                        description "Enter the current context";

                                        leaf start-time {
                                            type yang:date-and-time;
                                            description "The time when the sampling interval started.";
                                        }

                                        leaf sampling-duration {
                                            type types-sros:time-duration;
                                            description "The duration of the corresponding sampling interval.";
                                        }

                                        container packets {
                                            description "Enter the packets context";

                                            leaf encrypted {
                                                type yang:counter64;
                                                units "packets";
                                                description "Number of encrypted IPsec packets.";
                                            }

                                            leaf decrypted {
                                                type yang:counter64;
                                                units "packets";
                                                description "Number of decrypted IPsec packets.";
                                            }

                                            leaf total {
                                                type yang:counter64;
                                                units "packets";
                                                description "Number of encrypted and decrypted IPsec packets.";
                                            }

                                        } // container packets

                                        container bytes {
                                            description "Enter the bytes context";

                                            leaf encrypted {
                                                type yang:counter64;
                                                units "kilobytes";
                                                description "Number of kilobytes in the encrypted IPsec packets.";
                                            }

                                            leaf decrypted {
                                                type yang:counter64;
                                                units "kilobytes";
                                                description "Number of kilobytes in the decrypted IPsec packets.";
                                            }

                                            leaf total {
                                                type yang:counter64;
                                                units "kilobytes";
                                                description "Number of kilobytes in the encrypted and decrypted IPsec packets.";
                                            }

                                        } // container bytes

                                    } // container current

                                } // container traffic-forward

                            } // container statistics

                        } // list dynamic-tunnel

                    } // list ipsec-gateway

                } // list sap

                list vpls {
                    key "vpls-name";
                    description "Enter the vpls list instance";

                    leaf vpls-name {
                        type types-sros:named-item-64;
                        description "VPLS service";
                    }

                    leaf status {
                        type types-sros:oper-state;
                        description "The value of this object indicates the operational status of the VPLS service on this interface";
                    }

                    leaf failed-reason {
                        type types-sros:display-string-or-empty;
                        description "The reason when the Vpls is operationally down";
                    }

                } // list vpls

                container hold-time {
                    description "Enter the hold-time context";

                    container ipv4 {
                        description "Enter the ipv4 context";

                        leaf hold-timer {
                            type uint32;
                            units "seconds";
                            description
                                "The hold-timer indicates the time left before
                                 the interface comes up or goes down, depending on the ongoing
                                 transition state of the interface.";
                        }

                    } // container ipv4

                    container ipv6 {
                        description "Enter the ipv6 context";

                        leaf hold-timer {
                            type uint32;
                            units "seconds";
                            description
                                "The hold-timer indicates the time left before
                                 the interface comes up or goes down, depending on the ongoing
                                 transition state of the interface.";
                        }

                    } // container ipv6

                } // container hold-time

                container ipv4 {
                    description "Enter the ipv4 context";

                    leaf oper-state {
                        type types-sros:oper-state;
                        description "The current IPv4 operational status of this router interface.";
                    }

                    leaf down-reason {
                        type bits {
                            bit admin-disabled                 { position 0; }
                            bit service-admin-disabled         { position 1; }
                            bit port-down                      { position 2; }
                            bit address-or-parent-not-ready    { position 3; }
                            bit associated-object-not-ready    { position 4; }
                            bit rvpls-down                     { position 5; }
                            bit operational-group-down         { position 6; }
                            bit admin-destroy                  { position 7; }
                            bit no-address                     { position 8; }
                            bit no-info                        { position 9; }
                            bit hold-down-timer-running        { position 10; }
                            bit protocol-down                  { position 11; }
                            bit invalid-port-configuration     { position 12; }
                            bit unknown                        { position 13; }
                            bit no-route-distinguisher         { position 14; }
                            bit wlan-gateway-redundancy-standby { position 15; }
                            bit wlan-gateway-group-degraded    { position 16; }
                            bit ip-control-tunnel-down         { position 17; }
                            bit pdn-address-mismatch           { position 18; }
                            bit ping-check-failure             { position 19; }
                            bit port-internal-loopback         { position 20; }
                        }
                        description
                            "Indicates the reason for why the interface is operationally down.
                                             
                             Values:
                                 admin-disabled                  - Administratively disabled.
                                 service-admin-disabled          - Assiocated service is administratively disabled.
                                 port-down                       - Associated SAP/port is operationally down.
                                 address-or-parent-not-ready     - Associated address or parent interface is not ready.
                                 associated-object-not-ready     - Associated object is not ready.
                                 rvpls-down                      - Associated R-VPLS service is operationally down.
                                 operational-group-down          - Associated operational group is operationally down.
                                 admin-destroy                   - The interface is being destroyed.
                                 no-address                      - There is no address configured.
                                 no-info                         - The interface info is not present.
                                 hold-down-timer-running         - The hold down timer is running.
                                 protocol-down                   - The protocols are operationally down.
                                 invalid-port-configuration      - Invalid port configuration.
                                 unknown                         - The interface is operationally down due to some unknown reason.
                                 no-route-distinguisher          - No route-distinguisher configured in the VRF.
                                 wlan-gateway-redundancy-standby - The interface is in standby state for WLAN-GW redundancy.
                                 wlan-gateway-group-degraded     - The interface associated WLAN-GW group is in a degraded state.
                                 ip-control-tunnel-down          - The IP tunnel associated to a control-tunnel interface is operationally down.
                                 pdn-address-mismatch            - The IP address learned from the packet data network does not match the configured primary IP address.
                                 ping-check-failure              - The IP interface is or went down because of a ping-template failure.
                                 port-internal-loopback          - The IP interface is bound to a port that has an internal loopback configured.";
                    }

                    container icmp {
                        description "Enter the icmp context";

                        container statistics {
                            description "Enter the statistics context";

                            leaf icmp-in-msgs {
                                type yang:counter32;
                                description
                                    "Total Number of ICMPv4 messages received by this interface.
                                                     
                                     This includes all those counted by icmp-in-errors. Note that this
                                     interface is the interface to which the ICMPv4 messages were
                                     addressed which may not be necessarily the input interface
                                     for the messages.";
                            }

                            leaf icmp-in-errors {
                                type yang:counter32;
                                description
                                    "Number of ICMPv4 errored messages received by this interface.
                                                     
                                     This implies ICMPv4 messages determined as having specific
                                     ICMPv4 errors (bad ICMPv4 checksums, bad length, etc.).";
                            }

                            leaf icmp-in-dest-unreachables {
                                type yang:counter32;
                                description "Number of ICMPv4 destination unreachable messages received by this interface.";
                            }

                            leaf icmp-in-redirects {
                                type yang:counter32;
                                description "Number of ICMPv4 redirect messages received by this interface.";
                            }

                            leaf icmp-in-echos {
                                type yang:counter32;
                                description "Number of ICMPv4 echo (request) messages received by this interface.";
                            }

                            leaf icmp-in-echo-replies {
                                type yang:counter32;
                                description "Number of ICMPv4 echo reply messages received by this interface.";
                            }

                            leaf icmp-in-time-exceeds {
                                type yang:counter32;
                                description "Number of ICMPv4 time exceeded messages received by this interface.";
                            }

                            leaf icmp-in-src-quenches {
                                type yang:counter32;
                                description "Number of ICMPv4 source quench messages received by this interface.";
                            }

                            leaf icmp-in-timestamps {
                                type yang:counter32;
                                description "Number of ICMPv4 timestamp (request) messages received by this interface.";
                            }

                            leaf icmp-in-timestamp-replies {
                                type yang:counter32;
                                description "Number of ICMPv4 timestamp reply messages received by this interface.";
                            }

                            leaf icmp-in-address-masks {
                                type yang:counter32;
                                description "Number of ICMPv4 address mask request messages received by this interface.";
                            }

                            leaf icmp-in-address-mask-replies {
                                type yang:counter32;
                                description "Number of ICMPv4 address mask reply messages received by this interface.";
                            }

                            leaf icmp-in-parm-problems {
                                type yang:counter32;
                                description "Number of ICMPv4 parameter problem messages received by this interface.";
                            }

                            leaf icmp-out-msgs {
                                type yang:counter32;
                                description
                                    "Total number of ICMPv4 messages this interface attempted to send.
                                                     
                                     This includes all those counted by icmp-out-errors.";
                            }

                            leaf icmp-out-errors {
                                type yang:counter32;
                                description
                                    "Number of ICMPv4 messages this interface could not be send due to problems
                                     discovered within ICMPv4 such as lack of buffers.
                                                     
                                     This value should not include errors discovered outside the ICMPv4 layer such as
                                     the inability of VRtr IPv4 to route the resultant datagram. In some implementations
                                     there may be no types of error which contribute to this counter's value.";
                            }

                            leaf icmp-out-dest-unreachables {
                                type yang:counter32;
                                description "Number of ICMPv4 destination unreachable messages sent by this interface.";
                            }

                            leaf icmp-out-redirects {
                                type yang:counter32;
                                description "Number of ICMPv4 redirect messages sent by this interface.";
                            }

                            leaf icmp-out-echos {
                                type yang:counter32;
                                description "Number of ICMPv4 echo request messages sent by this interface.";
                            }

                            leaf icmp-out-echo-replies {
                                type yang:counter32;
                                description "Number of ICMPv4 echo reply messages sent by this interface.";
                            }

                            leaf icmp-out-time-exceeds {
                                type yang:counter32;
                                description "Number of ICMPv4 time exceeded messages sent by this interface.";
                            }

                            leaf icmp-out-src-quenches {
                                type yang:counter32;
                                description "Number of ICMPv4 source quench messages sent by this interface.";
                            }

                            leaf icmp-out-timestamps {
                                type yang:counter32;
                                description "Number of ICMPv4 timestamp (request) messages sent by this interface.";
                            }

                            leaf icmp-out-timestamp-replies {
                                type yang:counter32;
                                description "Number of ICMPv4 timestamp reply messages sent by this interface.";
                            }

                            leaf icmp-out-address-masks {
                                type yang:counter32;
                                description "Number of ICMPv4 address mask request messages sent by this interface.";
                            }

                            leaf icmp-out-address-mask-replies {
                                type yang:counter32;
                                description "Number of ICMPv4 address mask reply messages sent by this interface.";
                            }

                            leaf icmp-out-parm-problems {
                                type yang:counter32;
                                description "Number of ICMPv4 parameter problem messages sent by this interface.";
                            }

                            leaf icmp-out-discards {
                                type yang:counter32;
                                description "Number of discarded ICMPv4 messages on this interface.";
                            }

                        } // container statistics

                    } // container icmp

                    container primary {
                        description "Enter the primary context";

                        leaf oper-address {
                            type types-sros:ip-address;
                            description "Indicates the operational address of this entry.";
                        }

                        leaf creation-origin {
                            type types-sros:creation-origin;
                            description "Indicates the mechanism used to create this entry.";
                        }

                    } // container primary

                    list secondary {
                        key "address";
                        description "Enter the secondary list instance";

                        leaf address {
                            type types-sros:ipv4-unicast-address;
                            description "Secondary IPv4 address assigned to the interface";
                        }

                        leaf oper-address {
                            type types-sros:ip-address;
                            description "Indicates the operational address of this entry.";
                        }

                        leaf creation-origin {
                            type types-sros:creation-origin;
                            description "Indicates the mechanism used to create this entry.";
                        }

                    } // list secondary

                    container addresses {
                        description "Enter the addresses context";

                        list address {
                            key "ipv4-address";
                            description "Enter the address list instance";

                            leaf ipv4-address {
                                type types-sros:ipv4-unicast-address;
                                description "IPv4 address for the interface";
                            }

                            leaf oper-address {
                                type types-sros:ip-address;
                                description "Indicates the operational address of this entry.";
                            }

                            leaf creation-origin {
                                type types-sros:creation-origin;
                                description "Indicates the mechanism used to create this entry.";
                            }

                        } // list address

                    } // container addresses

                    container neighbor-discovery {
                        description "Enter the neighbor-discovery context";

                        container neighbor-unnumbered {
                            description "Enter the neighbor-unnumbered context";

                            leaf oper-state {
                                type types-sros:oper-state;
                                description "Indicates if the ARP entry is being used actively in the ARP table.";
                            }

                            leaf mac-address {
                                type yang:mac-address;
                                description "The media-dependent physical address.";
                            }

                            leaf type {
                                type enumeration {
                                    enum "other"                        { value 0; }
                                    enum "static"                       { value 1; }
                                    enum "dynamic"                      { value 2; }
                                    enum "managed"                      { value 100; }
                                    enum "evpn"                         { value 101; }
                                }
                                description "The type of mapping.";
                            }

                            leaf timer {
                                type uint32 {
                                    range "0..65535";
                                }
                                units "seconds";
                                description
                                    "Indicates how much longer an ARP entry remains in the ARP cache.

                                     When timer has a value of zero, the entry is cleared from the cache.";
                            }

                        } // container neighbor-unnumbered

                        list neighbor {
                            key "ipv4-address";
                            description "Enter the neighbor list instance";

                            leaf ipv4-address {
                                type types-sros:ipv4-address;
                                description "IPv4 address corresponding to the physical address";
                            }

                            leaf oper-state {
                                type types-sros:oper-state;
                                description "Indicates if the ARP entry is being used actively in the ARP table.";
                            }

                            leaf mac-address {
                                type yang:mac-address;
                                description "The media-dependent physical address.";
                            }

                            leaf type {
                                type enumeration {
                                    enum "other"                        { value 0; }
                                    enum "static"                       { value 1; }
                                    enum "dynamic"                      { value 2; }
                                    enum "managed"                      { value 100; }
                                    enum "evpn"                         { value 101; }
                                }
                                description "The type of mapping.";
                            }

                            leaf timer {
                                type uint32 {
                                    range "0..65535";
                                }
                                units "seconds";
                                description
                                    "Indicates how much longer an ARP entry remains in the ARP cache.

                                     When timer has a value of zero, the entry is cleared from the cache.";
                            }

                        } // list neighbor

                    } // container neighbor-discovery

                    container dhcp {
                        description "Enter the dhcp context";

                        container lease-populate {
                            description "Enter the lease-populate context";

                            leaf current-lease-states {
                                type uint32 {
                                    range "0..511999";
                                }
                                description "The number of DHCP lease states currently allocated on this interface.";
                            }

                        } // container lease-populate

                        container statistics {
                            description "Enter the statistics context";

                            container total-rx-packets {
                                description "Enter the total-rx-packets context";

                                leaf received {
                                    type yang:counter32;
                                    description "The total number of packets received by the DHCP relay agent.";
                                }

                                leaf malformed {
                                    type yang:counter32;
                                    description "The total number of malformed packets received by the DHCP relay agent.";
                                }

                                leaf untrusted {
                                    type yang:counter32;
                                    description "The total number of untrusted packets received by the DHCP relay agent.";
                                }

                            } // container total-rx-packets

                            container total-tx-packets {
                                description "Enter the total-tx-packets context";

                                leaf transmitted {
                                    type yang:counter32;
                                    description "The total number of packets transmitted by the DHCP relay agent.";
                                }

                            } // container total-tx-packets

                            container client-packets {
                                description "Enter the client-packets context";

                                leaf dropped {
                                    type yang:counter32;
                                    description "The total number of client packets dropped by the DHCP relay agent.";
                                }

                                leaf relayed {
                                    type yang:counter32;
                                    description "The total number of client packets relayed by the DHCP relay agent.";
                                }

                                leaf snooped {
                                    type yang:counter32;
                                    description "The total number of client packets snooped by the DHCP relay agent.";
                                }

                                container proxied {
                                    description "Enter the proxied context";

                                    leaf radius {
                                        type yang:counter32;
                                        description
                                            "The total number of client packets proxied by the DHCP relay agent based
                                             on data received from a RADIUS server.";
                                    }

                                    leaf lease-split {
                                        type yang:counter32;
                                        description
                                            "The total number of DHCP lease-split. Lease-split allows the DHCP relay agent to assigning a shorter lease time
                                             than the actual lease time assigned by the DHCP server. This allows the system to remove disconnected client quickly
                                             but ensure that client's shorter DHCP renewal are process by the relay agent and not the DHCP server.";
                                    }

                                } // container proxied

                            } // container client-packets

                            container server-packets {
                                description "Enter the server-packets context";

                                leaf dropped {
                                    type yang:counter32;
                                    description "The total number of server packets dropped by the DHCP relay agent.";
                                }

                                leaf relayed {
                                    type yang:counter32;
                                    description "The total number of server packets relayed by the DHCP relay agent.";
                                }

                                leaf snooped {
                                    type yang:counter32;
                                    description "The total number of server packets snooped by the DHCP relay agent.";
                                }

                            } // container server-packets

                            container spoofed-packets {
                                description "Enter the spoofed-packets context";

                                leaf release {
                                    type yang:counter32;
                                    description "The total number of DHCP RELEASE messages spoofed by the DHCP relay agent to the DHCP server.";
                                }

                                leaf force-renews {
                                    type yang:counter32;
                                    description
                                        "The total number of DHCP FORCERENEW messages spoofed by the DHCP relay agent
                                         to the DHCP clients.";
                                }

                            } // container spoofed-packets

                        } // container statistics

                    } // container dhcp

                    list vrrp {
                        key "virtual-router-id";
                        description "Enter the vrrp list instance";

                        leaf virtual-router-id {
                            type int32 {
                                range "1..255";
                            }
                            description "Virtual Router Identifier (VRID) for the VRRP virtual router instance";
                        }

                        leaf authentication-type {
                            type enumeration {
                                enum "no-authentication"            { value 1; }
                                enum "simple-text-password"         { value 2; }
                                enum "ip-authentication-header"     { value 3; }
                            }
                            description
                                "Authentication type used for VRRP protocol exchanges between
                                 virtual routers. This value of this object is the same for a
                                 given ifIndex.

                                 New enumerations to this list can only be added via a new
                                 RFC on the standards track.";
                        }

                        leaf oper-state {
                            type types-sros:oper-state;
                            description "Operational state.";
                        }

                        leaf router-state {
                            type enumeration {
                                enum "initialize"                   { value 1; }
                                enum "backup"                       { value 2; }
                                enum "master"                       { value 3; }
                            }
                            description
                                "The current state of the virtual router. This object has
                                 three defined values:
                                  - `initialize', which indicates that all the
                                     virtual router is waiting for a startup event.

                                  - `backup', which indicates the virtual router is
                                     monitoring the availability of the master router.

                                  - `master', which indicates that the virtual router
                                     is forwarding packets for IP addresses that are
                                     associated with this router.

                                 Setting the `admin-state' object initiates
                                 transitions in the value of this object.";
                        }

                        leaf virtual-mac {
                            type yang:mac-address;
                            description
                                "The virtual MAC address of the virtual router. Although this
                                 object can be derived from the 'virtual-router-id' object, it is
                                 defined so that it is easily obtainable by a management
                                 application and can be included in VRRP-related SNMP traps.";
                        }

                        leaf master-ip-address {
                            type types-sros:ip-address;
                            description
                                "The master router's real (primary) IP address. This is
                                 the IP address listed as the source in VRRP advertisement
                                 last received by this virtual router.";
                        }

                        leaf primary-ip-address {
                            type types-sros:ip-address;
                            description
                                "In the case where there is more than one IP address for
                                 a given `interface', this object is used to specify the IP
                                 address that will become the `master-ip-addr', should
                                 the virtual router transition from backup to master. If
                                 this object is set to 0.0.0.0, the IP address which is
                                 numerically lowest will be selected.";
                        }

                        leaf up-time {
                            type yang:date-and-time;
                            description
                                "This is the value of the `system up time' object when this
                                 virtual router (i.e., the `oper-state') transitioned
                                 out of `initialized'.";
                        }

                        leaf in-use-priority {
                            type uint32 {
                                range "0..255";
                            }
                            description
                                "Indicates the current in-use priority
                                 associated with the VRRP VRRP.";
                        }

                        leaf master-since {
                            type yang:date-and-time;
                            description
                                "In case of a virtual router which
                                 is the current master, is the sysUpTime when operational state
                                 (oper-state) of the virtual router changed to master(3).
                                 In case of a backup virtual router, this value specifies the
                                 sysUpTime when it received the first VRRP advertisement message
                                 from the virtual router which is the current master.";
                        }

                        leaf master-priority {
                            type uint32 {
                                range "0..255";
                            }
                            description
                                "The value indicates the priority of
                                 the VRRP which is the current master";
                        }

                        leaf master-down-interval {
                            type types-sros:time-duration;
                            units "milliseconds";
                            description
                                "The value indicates the time
                                 interval for the backup router to declare the master as down.
                                 It is calculated as
                                        (3 * Advertisement_Interval) + Skew_time
                                 where Skew_Time is calculated as
                                        (256 - Priority) / 256";
                        }

                        leaf master-down-timer {
                            type types-sros:time-duration;
                            units "milliseconds";
                            description
                                "The value indicates the current
                                 value of the Master Down Timer.

                                 When a backup router receives a VRRP advertisement from a master,
                                 it resets this timer to the value of the Master Down Interval
                                 and begins to count down. If the backup router does not receive
                                 an advertisement till this timer times out, it will assume that
                                 the master is down and will declare itself to be the master.";
                        }

                        leaf in-use-advertisement-interval {
                            type int64;
                            units "milliseconds";
                            description "Indicates the operational value for the advertisement interval.";
                        }

                        leaf init-timer {
                            type types-sros:time-duration;
                            units "milliseconds";
                            description
                                "The value indicates the current value of
                                 initialization delay timer for VRRP, in milliseconds.";
                        }

                        leaf down-reason {
                            type enumeration {
                                enum "unknown"                      { value 0; }
                                enum "not-active"                   { value 1; }
                                enum "admin-down"                   { value 2; }
                                enum "if-down"                      { value 3; }
                                enum "no-link-lcl-addr-cfg"         { value 4; }
                                enum "rtr-adv-no-proper-cfg"        { value 5; }
                                enum "invalid-mac"                  { value 6; }
                            }
                            description
                                "The value indicates the reason for the
                                 operational state to be 'down'.";
                        }

                        container bfd-liveness {
                            description "Enter the bfd-liveness context";

                            leaf src-ip {
                                type types-sros:ip-address;
                                description
                                    "The value indicates the source
                                     IP address on the interface running BFD.";
                            }

                            leaf session-state {
                                type enumeration {
                                    enum "unknown"                      { value 1; }
                                    enum "connected"                    { value 2; }
                                    enum "broken"                       { value 3; }
                                    enum "peer-detects-down"            { value 4; }
                                    enum "not-configured"               { value 5; }
                                    enum "no-resources"                 { value 6; }
                                }
                                description
                                    "The value indicates the operational
                                     state of the BFD session the VRRP is relying
                                     upon for its fast triggering mechanism.";
                            }

                        } // container bfd-liveness

                        list master {
                            key "primary-ip-address";
                            description "Enter the master list instance";

                            leaf primary-ip-address {
                                type types-sros:ipv4-address;
                                description
                                    "This Object is set as read-only in mib. We use it to pass values to the sia-check
                                     function where it should fail.";
                            }

                            leaf last-seen {
                                type yang:date-and-time;
                                description
                                    "The value indicates the sysUpTime
                                     when the master was last seen by this VRRP. In
                                     other words it is the timestamp of the last advertisement message
                                     that was received from that master.";
                            }

                            leaf auth-sequence {
                                type int32;
                                description
                                    "The value indicates the last
                                     sequence number seen in the IP Authentication header of the
                                     advertisement messages received from the master.
                                     A negative value implies that the master was not being
                                     authenticated via IP authentication header.";
                            }

                            leaf ip-list-match {
                                type boolean;
                                description
                                    "The value indicates whether or not
                                     the IP address list in the advertisement messages received from
                                     the master matched the configured virtual router IP address list.";
                            }

                            container statistics {
                                description "Enter the statistics context";

                                leaf messages-received {
                                    type yang:counter32;
                                    description
                                        "The value indicates the total
                                         number of VRRP advertisement messages that have been received
                                         from the master.";
                                }

                            } // container statistics

                        } // list master

                        container statistics {
                            description "Enter the statistics context";

                            leaf authentication-failure-packets-received {
                                type yang:counter32;
                                description
                                    "The total number of VRRP packets received that do not pass
                                     the authentication check.";
                            }

                            leaf authentication-type-mismatch-packets-received {
                                type yang:counter32;
                                description
                                    "The total number of packets received with 'Auth Type' not
                                     equal to the locally configured authentication method
                                     (`vrrpOperAuthType').";
                            }

                            leaf address-list-discards {
                                type yang:counter32;
                                description
                                    "The total number of VRRP advertisement packets discarded
                                     because the address list did not match the locally configured
                                     list for the virtual router.";
                            }

                            leaf become-master {
                                type yang:counter32;
                                description
                                    "The total number of times that this virtual router's state
                                     has transitioned to MASTER.";
                            }

                            leaf advertisements-received {
                                type yang:counter32;
                                description
                                    "The total number of VRRP advertisements received by this
                                     virtual router.";
                            }

                            leaf advertisements-sent {
                                type yang:counter32;
                                description
                                    "The total number of VRRP advertisements sent by this virtual
                                     router.";
                            }

                            leaf advertisement-interval-errors {
                                type yang:counter32;
                                description
                                    "The total number of VRRP advertisement packets received
                                     for which the advertisement interval is different than the
                                     one configured for the local virtual router.";
                            }

                            leaf ttl-error-packets-received {
                                type yang:counter32;
                                description
                                    "The total number of VRRP packets received by the virtual
                                     router with IP TTL (Time-To-Live) not equal to 255.";
                            }

                            leaf zero-priority-packets-received {
                                type yang:counter32;
                                description
                                    "The total number of VRRP packets received by the virtual
                                     router with a priority of '0'.";
                            }

                            leaf zero-priority-packets-sent {
                                type yang:counter32;
                                description
                                    "The total number of VRRP packets sent by the virtual router
                                     with a priority of '0'.";
                            }

                            leaf invalid-type-packets-received {
                                type yang:counter32;
                                description
                                    "The number of VRRP packets received by the virtual router
                                     with an invalid value in the 'type' field.";
                            }

                            leaf address-list-error-packets-received {
                                type yang:counter32;
                                description
                                    "The total number of packets received for which the address
                                     list does not match the locally configured list for the
                                     virtual router.";
                            }

                            leaf error-length-packets-received {
                                type yang:counter32;
                                description
                                    "The total number of packets received with a packet length
                                     less than the length of the VRRP header.";
                            }

                            leaf invalid-authentication-type-packets-received {
                                type yang:counter32;
                                description
                                    "The total number of packets received with an unknown
                                     authentication type.";
                            }

                            leaf preempt-events {
                                type yang:counter32;
                                description
                                    "The value indicates the total
                                     number of times the virtual router has preempted another
                                     non-owner master with lower priority.";
                            }

                            leaf preempted-events {
                                type yang:counter32;
                                description
                                    "The value indicates the total
                                     number of times the virtual router has been preempted by another
                                     non-owner master with higher priority.";
                            }

                            leaf master-changes {
                                type yang:counter32;
                                description
                                    "The value indicates the total
                                     number of times the virtual router has seen the master virtual
                                     router change.";
                            }

                            leaf advertise-interval-discards {
                                type yang:counter32;
                                description
                                    "The total number of VRRP advertisement packets discarded
                                     because the advertisement interval in the received packet
                                     was different than the one configured for the local virtual
                                     router.";
                            }

                            leaf total-discards {
                                type yang:counter32;
                                description
                                    "The total number of VRRP advertisement packets discarded
                                     for any reason. This includes the packets discarded due to
                                     advertise interval mismatch and address list mismatch.";
                            }

                        } // container statistics

                    } // list vrrp

                    container statistics {
                        description "Enter the statistics context";

                        leaf out-packets {
                            type yang:counter64;
                            description "The number of packets transmitted by this interface.";
                        }

                        leaf out-octets {
                            type yang:counter64;
                            description "The number of octets transmitted by this interface.";
                        }

                        leaf out-discard-packets {
                            type yang:counter64;
                            description "The number of transmit packets discarded.";
                        }

                        leaf out-discard-octets {
                            type yang:counter64;
                            description "The number of transmit octets discarded.";
                        }

                        leaf in-packets {
                            type yang:counter64;
                            description "The number of packets received.";
                        }

                        leaf in-octets {
                            type yang:counter64;
                            description "The number of octets received.";
                        }

                        leaf urpf-check-fail-packets {
                            type yang:counter64;
                            description "The number of packets that fail uRPF check on this interface.";
                        }

                        leaf urpf-check-fail-octets {
                            type yang:counter64;
                            description "The number of octets in the packets that fail uRPF check.";
                        }

                        leaf out-discard-dbcast-packets {
                            type yang:counter64;
                            description "The number of directed-broadcast packets dropped.";
                        }

                        leaf out-discard-dbcast-octets {
                            type yang:counter64;
                            description "The number of directed-broadcast octets dropped.";
                        }

                        leaf in-ip-helper-redirects-packets {
                            type yang:counter64;
                            description "The number of packets redirected to the ip-helper gateway.";
                        }

                        leaf in-ip-helper-redirects-octets {
                            type yang:counter64;
                            description "The number of bytes redirected to the ip-helper gateway.";
                        }

                    } // container statistics

                } // container ipv4

                container ipv6 {
                    description "Enter the ipv6 context";

                    leaf oper-state {
                        type types-sros:oper-state;
                        description "The current IPv6 operational status of this router interface.";
                    }

                    leaf down-reason {
                        type bits {
                            bit admin-disabled                 { position 0; }
                            bit service-admin-disabled         { position 1; }
                            bit port-down                      { position 2; }
                            bit address-or-parent-not-ready    { position 3; }
                            bit associated-object-not-ready    { position 4; }
                            bit rvpls-down                     { position 5; }
                            bit operational-group-down         { position 6; }
                            bit admin-destroy                  { position 7; }
                            bit no-address                     { position 8; }
                            bit no-info                        { position 9; }
                            bit hold-down-timer-running        { position 10; }
                            bit protocol-down                  { position 11; }
                            bit invalid-port-configuration     { position 12; }
                            bit unknown                        { position 13; }
                            bit no-route-distinguisher         { position 14; }
                            bit wlan-gateway-redundancy-standby { position 15; }
                            bit wlan-gateway-group-degraded    { position 16; }
                            bit ip-control-tunnel-down         { position 17; }
                            bit pdn-address-mismatch           { position 18; }
                            bit ping-check-failure             { position 19; }
                            bit port-internal-loopback         { position 20; }
                        }
                        description
                            "Indicates the reason for why the interface is operationally down.
                                             
                             Values:
                                 admin-disabled                  - Administratively disabled.
                                 service-admin-disabled          - Assiocated service is administratively disabled.
                                 port-down                       - Associated SAP/port is operationally down.
                                 address-or-parent-not-ready     - Associated address or parent interface is not ready.
                                 associated-object-not-ready     - Associated object is not ready.
                                 rvpls-down                      - Associated R-VPLS service is operationally down.
                                 operational-group-down          - Associated operational group is operationally down.
                                 admin-destroy                   - The interface is being destroyed.
                                 no-address                      - There is no address configured.
                                 no-info                         - The interface info is not present.
                                 hold-down-timer-running         - The hold down timer is running.
                                 protocol-down                   - The protocols are operationally down.
                                 invalid-port-configuration      - Invalid port configuration.
                                 unknown                         - The interface is operationally down due to some unknown reason.
                                 no-route-distinguisher          - No route-distinguisher configured in the VRF.
                                 wlan-gateway-redundancy-standby - The interface is in standby state for WLAN-GW redundancy.
                                 wlan-gateway-group-degraded     - The interface associated WLAN-GW group is in a degraded state.
                                 ip-control-tunnel-down          - The IP tunnel associated to a control-tunnel interface is operationally down.
                                 pdn-address-mismatch            - The IP address learned from the packet data network does not match the configured primary IP address.
                                 ping-check-failure              - The IP interface is or went down because of a ping-template failure.
                                 port-internal-loopback          - The IP interface is bound to a port that has an internal loopback configured.";
                    }

                    container icmp6 {
                        description "Enter the icmp6 context";

                        container statistics {
                            description "Enter the statistics context";

                            leaf icmp6-in-msgs {
                                type yang:counter32;
                                description
                                    "Total number of ICMPv6 messages received by this interface.
                                                     
                                     This includes all those counted by icmp6-in-errors. Note that this
                                     interface is the interface to which the ICMPv6 messages were
                                     addressed which may not be necessarily the input interface
                                     for the messages.";
                            }

                            leaf icmp6-in-errors {
                                type yang:counter32;
                                description
                                    "Number of ICMPv6 errored messages received by this interface.
                                                     
                                     This implies ICMPv6 messages determined as having specific
                                     ICMPv6 errors (bad ICMP checksums, bad length, etc.).";
                            }

                            leaf icmp6-in-dest-unreachables {
                                type yang:counter32;
                                description "Nmber of ICMPv6 destination unreachable messages received by this interface.";
                            }

                            leaf icmp6-in-admin-prohibs {
                                type yang:counter32;
                                description
                                    "Number of ICMPv6 destination unreachable/communication administratively
                                     prohibited messages received by this interface.";
                            }

                            leaf icmp6-in-time-exceeds {
                                type yang:counter32;
                                description "Number of ICMPv6 time exceeded messages received by this interface.";
                            }

                            leaf icmp6-in-parm-problems {
                                type yang:counter32;
                                description "Number of ICMPv6 parameter problem messages received by this interface.";
                            }

                            leaf icmp6-in-pkt-too-bigs {
                                type yang:counter32;
                                description "Number of ICMPv6 packet too big messages received by this interface.";
                            }

                            leaf icmp6-in-echos {
                                type yang:counter32;
                                description "Number of ICMPv6 echo (request) messages received by this interface.";
                            }

                            leaf icmp6-in-echo-replies {
                                type yang:counter32;
                                description "Number of ICMPv6 echo reply messages received by this interface.";
                            }

                            leaf icmp6-in-rtr-solicits {
                                type yang:counter32;
                                description "Number of ICMPv6 router solicitation messages received by this interface.";
                            }

                            leaf icmp6-in-rtr-advertisements {
                                type yang:counter32;
                                description "Number of ICMPv6 router advertisement messages received by this interface.";
                            }

                            leaf icmp6-in-nbr-solicits {
                                type yang:counter32;
                                description "Number of ICMPv6 neighbor solicitation messages received by this interface.";
                            }

                            leaf icmp6-in-nbr-advertisements {
                                type yang:counter32;
                                description "Number of ICMPv6 neighbor advertisement messages received by this interface.";
                            }

                            leaf icmp6-in-redirects {
                                type yang:counter32;
                                description "Number of ICMPv6 redirect messages received by this interface.";
                            }

                            leaf icmp6-in-grp-memb-queries {
                                type yang:counter32;
                                description "Number of ICMPv6 group membership query messages received by this interface.";
                            }

                            leaf icmp6-in-grp-memb-repsonses {
                                type yang:counter32;
                                description "Number of ICMPv6 group membership response messages received by this interface.";
                            }

                            leaf icmp6-in-grp-memb-reductions {
                                type yang:counter32;
                                description "Number of ICMPv6 group membership reduction messages received by this interface.";
                            }

                            leaf icmp6-out-msgs {
                                type yang:counter32;
                                description
                                    "Total number of ICMPv6 messages this interface attempted to send.
                                                     
                                     This includes all those counted by icmp6-out-errors.";
                            }

                            leaf icmp6-out-errors {
                                type yang:counter32;
                                description
                                    "Number of ICMPv6 messages this interface could not be send due to problems
                                     discovered within ICMPv6 such as lack of buffers.
                                                     
                                     This value should not include errors discovered outside the ICMPv6 layer such as
                                     the inability of VRtr IPv6 to route the resultant datagram. In some implementations
                                     there may be no types of error which contribute to this counter's value.";
                            }

                            leaf icmp6-out-dest-unreachables {
                                type yang:counter32;
                                description "Number of ICMPv6 destination unreachable messages sent by this interface.";
                            }

                            leaf icmp6-out-admin-prohibs {
                                type yang:counter32;
                                description
                                    "Number of ICMPv6 destination unreachable/communication administratively prohibited
                                     messages sent by this interface.";
                            }

                            leaf icmp6-out-time-exceeds {
                                type yang:counter32;
                                description "Number of ICMPv6 time exceeded messages sent by this interface.";
                            }

                            leaf icmp6-out-parm-problems {
                                type yang:counter32;
                                description "Number of ICMPv6 parameter problem messages sent by this interface.";
                            }

                            leaf icmp6-out-pkt-too-bigs {
                                type yang:counter32;
                                description "Number of ICMPv6 packet too big messages sent by this interface.";
                            }

                            leaf icmp6-out-echos {
                                type yang:counter32;
                                description "Number of ICMPv6 echo request messages sent by this interface.";
                            }

                            leaf icmp6-out-echo-replies {
                                type yang:counter32;
                                description "Number of ICMPv6 echo reply messages sent by this interface.";
                            }

                            leaf icmp6-out-rtr-solicits {
                                type yang:counter32;
                                description "Number of ICMPv6 router solicitation messages sent by this interface.";
                            }

                            leaf icmp6-out-rtr-advertisements {
                                type yang:counter32;
                                description "Number of ICMPv6 router advertisement messages sent by this interface.";
                            }

                            leaf icmp6-out-nbr-solicits {
                                type yang:counter32;
                                description "Number of ICMPv6 neighbor solicitation messages sent by this interface.";
                            }

                            leaf icmp6-out-nbr-advertisements {
                                type yang:counter32;
                                description "Number of ICMPv6 neighbor advertisement messages sent by this interface.";
                            }

                            leaf icmp6-out-redirects {
                                type yang:counter32;
                                description "Number of ICMPv6 redirect messages sent by this interface.";
                            }

                            leaf icmp6-out-grp-memb-queries {
                                type yang:counter32;
                                description "Number of ICMPv6 group membership query messages sent by this interface.";
                            }

                            leaf icmp6-out-grp-memb-responses {
                                type yang:counter32;
                                description "Number of ICMPv6 group membership response messages sent by this interface.";
                            }

                            leaf icmp6-out-grp-memb-reductions {
                                type yang:counter32;
                                description "Number of ICMPv6 group membership reduction messages sent by this interface.";
                            }

                            leaf icmp6-out-discards {
                                type yang:counter32;
                                description "Number of discarded ICMPv6 messages on this interface.";
                            }

                        } // container statistics

                    } // container icmp6

                    container link-local-address {
                        description "Enter the link-local-address context";

                        leaf oper-address {
                            type types-sros:ipv6-address;
                            description "Indicates the link-local IPv6 address of this router interface.";
                        }

                        leaf address-state {
                            type types-sros:address-state;
                            description "Indicates the address state of the IPv6 address of the interface.";
                        }

                    } // container link-local-address

                    list address {
                        key "ipv6-address";
                        description "Enter the address list instance";

                        leaf ipv6-address {
                            type types-sros:ipv6-address;
                            description "IPv6 address assigned to the interface";
                        }

                        leaf address-state {
                            type types-sros:address-state;
                            description "Indicates the address state of the IPv6 address of the interface.";
                        }

                        leaf oper-address {
                            type types-sros:ip-address;
                            description "Indicates the operational address of this entry.";
                        }

                        leaf creation-origin {
                            type types-sros:creation-origin;
                            description "Indicates the mechanism used to create this entry.";
                        }

                        leaf primary-preferred {
                            type boolean;
                            description "Indicates whether this IP address is selected as the preferred primary address.";
                        }

                    } // list address

                    container dhcp6 {
                        description "Enter the dhcp6 context";

                        container relay {
                            description "Enter the relay context";

                            leaf oper-state {
                                type enumeration {
                                    enum "up"                           { value 1; }
                                    enum "down"                         { value 2; }
                                    enum "no-ipv6-prefix"               { value 3; }
                                    enum "no-server-configured"         { value 4; }
                                    enum "no-valid-source-address"      { value 5; }
                                }
                                description "The current operational state of the DHCP6 relay agent on this interface.";
                            }

                            leaf current-lease-states {
                                type uint32;
                                description
                                    "The number of lease states currently allocated on this interface
                                     by the DHCP6 relay function.";
                            }

                            leaf server-lease-states {
                                type uint32;
                                description
                                    "The number of lease states currently allocated on this interface
                                     by the DHCP6 server function.";
                            }

                        } // container relay

                        container server {
                            description "Enter the server context";

                            leaf current-server-lease-states {
                                type uint32 {
                                    range "0..8000";
                                }
                                description
                                    "Indicates the number of lease states currently allocated on this interface
                                     by the DHCP6 server function.";
                            }

                        } // container server

                    } // container dhcp6

                    container neighbor-discovery {
                        description "Enter the neighbor-discovery context";

                        list neighbor {
                            key "ipv6-address";
                            description "Enter the neighbor list instance";

                            leaf ipv6-address {
                                type types-sros:ipv6-address;
                                description "IPv6 address corresponding to the physical address";
                            }

                            leaf state {
                                type enumeration {
                                    enum "incomplete"                   { value 0; }
                                    enum "reachable"                    { value 1; }
                                    enum "stale"                        { value 2; }
                                    enum "delay"                        { value 3; }
                                    enum "probe"                        { value 4; }
                                }
                                description
                                    "The Neighbor Unreachability Detection state for the interface
                                     when the address mapping is used.";
                            }

                            leaf is-router {
                                type boolean;
                                description "Indicates whether this entry is a router.";
                            }

                            leaf secure-nd {
                                type enumeration {
                                    enum "not-applicable"               { value 0; }
                                    enum "secure"                       { value 1; }
                                    enum "unsecure"                     { value 2; }
                                }
                                description
                                    "Indicates whether the physical address is received
                                     via Secured Neighbor Discovery messages.";
                            }

                            leaf mtu {
                                type uint32;
                                description "The MTU of the link attached to this entry.";
                            }

                            leaf mac-address {
                                type yang:mac-address;
                                description "The media-dependent physical address.";
                            }

                            leaf type {
                                type enumeration {
                                    enum "other"                        { value 0; }
                                    enum "static"                       { value 1; }
                                    enum "dynamic"                      { value 2; }
                                    enum "managed"                      { value 100; }
                                    enum "evpn"                         { value 101; }
                                }
                                description "The type of mapping.";
                            }

                            leaf timer {
                                type uint32 {
                                    range "0..65535";
                                }
                                units "seconds";
                                description
                                    "Indicates how much longer an ARP entry remains in the ARP cache.

                                     When timer has a value of zero, the entry is cleared from the cache.";
                            }

                        } // list neighbor

                    } // container neighbor-discovery

                    list vrrp {
                        key "virtual-router-id";
                        description "Enter the vrrp list instance";

                        leaf virtual-router-id {
                            type int32 {
                                range "1..255";
                            }
                            description "Virtual Router Identifier (VRID) for the VRRP virtual router instance";
                        }

                        leaf oper-state {
                            type types-sros:oper-state;
                            description "Operational state.";
                        }

                        leaf router-state {
                            type enumeration {
                                enum "initialize"                   { value 1; }
                                enum "backup"                       { value 2; }
                                enum "master"                       { value 3; }
                            }
                            description
                                "The current state of the virtual router. This object has
                                 three defined values:
                                  - `initialize', which indicates that all the
                                     virtual router is waiting for a startup event.

                                  - `backup', which indicates the virtual router is
                                     monitoring the availability of the master router.

                                  - `master', which indicates that the virtual router
                                     is forwarding packets for IP addresses that are
                                     associated with this router.

                                 Setting the `admin-state' object initiates
                                 transitions in the value of this object.";
                        }

                        leaf virtual-mac {
                            type yang:mac-address;
                            description
                                "The virtual MAC address of the virtual router. Although this
                                 object can be derived from the 'virtual-router-id' object, it is
                                 defined so that it is easily obtainable by a management
                                 application and can be included in VRRP-related SNMP traps.";
                        }

                        leaf master-ip-address {
                            type types-sros:ip-address;
                            description
                                "The master router's real (primary) IP address. This is
                                 the IP address listed as the source in VRRP advertisement
                                 last received by this virtual router.";
                        }

                        leaf primary-ip-address {
                            type types-sros:ip-address;
                            description
                                "In the case where there is more than one IP address for
                                 a given `interface', this object is used to specify the IP
                                 address that will become the `master-ip-addr', should
                                 the virtual router transition from backup to master. If
                                 this object is set to 0.0.0.0, the IP address which is
                                 numerically lowest will be selected.";
                        }

                        leaf up-time {
                            type yang:date-and-time;
                            description
                                "This is the value of the `system up time' object when this
                                 virtual router (i.e., the `oper-state') transitioned
                                 out of `initialized'.";
                        }

                        leaf in-use-priority {
                            type uint32 {
                                range "0..255";
                            }
                            description
                                "Indicates the current in-use priority
                                 associated with the VRRP VRRP.";
                        }

                        leaf master-since {
                            type yang:date-and-time;
                            description
                                "In case of a virtual router which
                                 is the current master, is the sysUpTime when operational state
                                 (oper-state) of the virtual router changed to master(3).
                                 In case of a backup virtual router, this value specifies the
                                 sysUpTime when it received the first VRRP advertisement message
                                 from the virtual router which is the current master.";
                        }

                        leaf master-priority {
                            type uint32 {
                                range "0..255";
                            }
                            description
                                "The value indicates the priority of
                                 the VRRP which is the current master";
                        }

                        leaf master-down-interval {
                            type types-sros:time-duration;
                            units "milliseconds";
                            description
                                "The value indicates the time
                                 interval for the backup router to declare the master as down.
                                 It is calculated as
                                        (3 * Advertisement_Interval) + Skew_time
                                 where Skew_Time is calculated as
                                        (256 - Priority) / 256";
                        }

                        leaf master-down-timer {
                            type types-sros:time-duration;
                            units "milliseconds";
                            description
                                "The value indicates the current
                                 value of the Master Down Timer.

                                 When a backup router receives a VRRP advertisement from a master,
                                 it resets this timer to the value of the Master Down Interval
                                 and begins to count down. If the backup router does not receive
                                 an advertisement till this timer times out, it will assume that
                                 the master is down and will declare itself to be the master.";
                        }

                        leaf in-use-advertisement-interval {
                            type int64;
                            units "milliseconds";
                            description "Indicates the operational value for the advertisement interval.";
                        }

                        leaf init-timer {
                            type types-sros:time-duration;
                            units "milliseconds";
                            description
                                "The value indicates the current value of
                                 initialization delay timer for VRRP, in milliseconds.";
                        }

                        leaf down-reason {
                            type enumeration {
                                enum "unknown"                      { value 0; }
                                enum "not-active"                   { value 1; }
                                enum "admin-down"                   { value 2; }
                                enum "if-down"                      { value 3; }
                                enum "no-link-lcl-addr-cfg"         { value 4; }
                                enum "rtr-adv-no-proper-cfg"        { value 5; }
                                enum "invalid-mac"                  { value 6; }
                            }
                            description
                                "The value indicates the reason for the
                                 operational state to be 'down'.";
                        }

                        container bfd-liveness {
                            description "Enter the bfd-liveness context";

                            leaf src-ip {
                                type types-sros:ip-address;
                                description
                                    "The value indicates the source
                                     IP address on the interface running BFD.";
                            }

                            leaf session-state {
                                type enumeration {
                                    enum "unknown"                      { value 1; }
                                    enum "connected"                    { value 2; }
                                    enum "broken"                       { value 3; }
                                    enum "peer-detects-down"            { value 4; }
                                    enum "not-configured"               { value 5; }
                                    enum "no-resources"                 { value 6; }
                                }
                                description
                                    "The value indicates the operational
                                     state of the BFD session the VRRP is relying
                                     upon for its fast triggering mechanism.";
                            }

                        } // container bfd-liveness

                        list master {
                            key "primary-ip-address";
                            description "Enter the master list instance";

                            leaf primary-ip-address {
                                type types-sros:ipv6-address;
                                description
                                    "This Object is set as read-only in mib. We use it to pass values to the sia-check
                                     function where it should fail.";
                            }

                            leaf last-seen {
                                type yang:date-and-time;
                                description
                                    "The value indicates the sysUpTime
                                     when the master was last seen by this VRRP. In
                                     other words it is the timestamp of the last advertisement message
                                     that was received from that master.";
                            }

                            leaf auth-sequence {
                                type int32;
                                description
                                    "The value indicates the last
                                     sequence number seen in the IP Authentication header of the
                                     advertisement messages received from the master.
                                     A negative value implies that the master was not being
                                     authenticated via IP authentication header.";
                            }

                            leaf ip-list-match {
                                type boolean;
                                description
                                    "The value indicates whether or not
                                     the IP address list in the advertisement messages received from
                                     the master matched the configured virtual router IP address list.";
                            }

                            container statistics {
                                description "Enter the statistics context";

                                leaf messages-received {
                                    type yang:counter32;
                                    description
                                        "The value indicates the total
                                         number of VRRP advertisement messages that have been received
                                         from the master.";
                                }

                            } // container statistics

                        } // list master

                        container statistics {
                            description "Enter the statistics context";

                            leaf discontinuity-time {
                                type yang:date-and-time;
                                description
                                    "The value of sysUpTime on the most recent occasion at
                                     which any one or more of this entry's counters suffered
                                     a discontinuity.

                                     If no such discontinuities have occurred since the last
                                     re-initialization of the local management subsystem,
                                     then this object contains a zero value.";
                            }

                            leaf refresh-rate {
                                type uint32;
                                units "milliseconds";
                                description
                                    "The minimum reasonable polling interval for this entry.
                                     This object provides an indication of the minimum
                                     Amount of time required to update the counters in this
                                     entry.";
                            }

                            leaf become-master {
                                type yang:counter32;
                                description
                                    "The total number of times that this virtual router's state
                                     has transitioned to MASTER.";
                            }

                            leaf advertisements-received {
                                type yang:counter32;
                                description
                                    "The total number of VRRP advertisements received by this
                                     virtual router.";
                            }

                            leaf advertisements-sent {
                                type yang:counter32;
                                description
                                    "The total number of VRRP advertisements sent by this virtual
                                     router.";
                            }

                            leaf advertisement-interval-errors {
                                type yang:counter32;
                                description
                                    "The total number of VRRP advertisement packets received
                                     for which the advertisement interval is different than the
                                     one configured for the local virtual router.";
                            }

                            leaf ttl-error-packets-received {
                                type yang:counter32;
                                description
                                    "The total number of VRRP packets received by the virtual
                                     router with IP TTL (Time-To-Live) not equal to 255.";
                            }

                            leaf zero-priority-packets-received {
                                type yang:counter32;
                                description
                                    "The total number of VRRP packets received by the virtual
                                     router with a priority of '0'.";
                            }

                            leaf zero-priority-packets-sent {
                                type yang:counter32;
                                description
                                    "The total number of VRRP packets sent by the virtual router
                                     with a priority of '0'.";
                            }

                            leaf invalid-type-packets-received {
                                type yang:counter32;
                                description
                                    "The number of VRRP packets received by the virtual router
                                     with an invalid value in the 'type' field.";
                            }

                            leaf address-list-error-packets-received {
                                type yang:counter32;
                                description
                                    "The total number of packets received for which the address
                                     list does not match the locally configured list for the
                                     virtual router.";
                            }

                            leaf error-length-packets-received {
                                type yang:counter32;
                                description
                                    "The total number of packets received with a packet length
                                     less than the length of the VRRP header.";
                            }

                            leaf invalid-authentication-type-packets-received {
                                type yang:counter32;
                                description
                                    "The total number of packets received with an unknown
                                     authentication type.";
                            }

                            leaf preempt-events {
                                type yang:counter32;
                                description
                                    "The value indicates the total
                                     number of times the virtual router has preempted another
                                     non-owner master with lower priority.";
                            }

                            leaf preempted-events {
                                type yang:counter32;
                                description
                                    "The value indicates the total
                                     number of times the virtual router has been preempted by another
                                     non-owner master with higher priority.";
                            }

                            leaf master-changes {
                                type yang:counter32;
                                description
                                    "The value indicates the total
                                     number of times the virtual router has seen the master virtual
                                     router change.";
                            }

                            leaf advertise-interval-discards {
                                type yang:counter32;
                                description
                                    "The total number of VRRP advertisement packets discarded
                                     because the advertisement interval in the received packet
                                     was different than the one configured for the local virtual
                                     router.";
                            }

                            leaf total-discards {
                                type yang:counter32;
                                description
                                    "The total number of VRRP advertisement packets discarded
                                     for any reason. This includes the packets discarded due to
                                     advertise interval mismatch and address list mismatch.";
                            }

                        } // container statistics

                    } // list vrrp

                    container statistics {
                        description "Enter the statistics context";

                        leaf out-packets {
                            type yang:counter64;
                            description "The number of packets transmitted by this interface.";
                        }

                        leaf out-octets {
                            type yang:counter64;
                            description "The number of octets transmitted by this interface.";
                        }

                        leaf out-discard-packets {
                            type yang:counter64;
                            description "The number of transmit packets discarded.";
                        }

                        leaf out-discard-octets {
                            type yang:counter64;
                            description "The number of transmit octets discarded.";
                        }

                        leaf in-packets {
                            type yang:counter64;
                            description "The number of packets received.";
                        }

                        leaf in-octets {
                            type yang:counter64;
                            description "The number of octets received.";
                        }

                        leaf urpf-check-fail-packets {
                            type yang:counter64;
                            description "The number of packets that fail uRPF check on this interface.";
                        }

                        leaf urpf-check-fail-octets {
                            type yang:counter64;
                            description "The number of octets in the packets that fail uRPF check.";
                        }

                    } // container statistics

                } // container ipv6

                container statistics {
                    description "Enter the statistics context";

                    container ip {
                        description "Enter the ip context";

                        leaf out-packets {
                            type yang:counter64;
                            description "The number of packets transmitted by this interface.";
                        }

                        leaf out-octets {
                            type yang:counter64;
                            description "The number of octets transmitted by this interface.";
                        }

                        leaf out-discard-packets {
                            type yang:counter64;
                            description "The number of transmit packets discarded.";
                        }

                        leaf out-discard-octets {
                            type yang:counter64;
                            description "The number of transmit octets discarded.";
                        }

                        leaf in-packets {
                            type yang:counter64;
                            description "The number of packets received.";
                        }

                        leaf in-octets {
                            type yang:counter64;
                            description "The number of octets received.";
                        }

                        leaf urpf-check-fail-packets {
                            type yang:counter64;
                            description "The number of packets that fail uRPF check on this interface.";
                        }

                        leaf urpf-check-fail-octets {
                            type yang:counter64;
                            description "The number of octets in the packets that fail uRPF check.";
                        }

                    } // container ip

                    list mac {
                        key "mac-address";
                        description "Enter the mac list instance";

                        leaf mac-address {
                            type yang:mac-address;
                            description "Mac-address";
                        }

                        leaf out-packets {
                            type yang:counter64;
                            description "The number of packets sent to the mac address";
                        }

                        leaf out-octets {
                            type yang:counter64;
                            description "The number of bytes sent to the mac address";
                        }

                        leaf in-packets {
                            type yang:counter64;
                            description "The number of packets received from the mac address";
                        }

                        leaf in-octets {
                            type yang:counter64;
                            description "The number of bytes received from the mac address";
                        }

                    } // list mac

                } // container statistics

            } // list interface

            list redundant-interface {
                key "interface-name";
                description "Enter the redundant-interface list instance";

                leaf interface-name {
                    type types-sros:interface-name;
                    description "Interface name";
                }

                leaf if-index {
                    type int32;
                    description "The interface index.";
                }

                leaf system-if-index {
                    type int32;
                    description "The interface system index.";
                }

                leaf oper-state {
                    type enumeration {
                        enum "up"                           { value 1; }
                        enum "down"                         { value 2; }
                        enum "testing"                      { value 3; }
                        enum "unknown"                      { value 4; }
                        enum "dormant"                      { value 5; }
                        enum "not-present"                  { value 6; }
                        enum "lower-layer-down"             { value 7; }
                    }
                    description
                        "The current operational state of the interface.
                         This leaf has the same semantics as ifOperStatus. 
                         in RFC 2863: The Interfaces Group MIB";
                }

                leaf oper-ip-mtu {
                    type uint32;
                    units "bytes";
                    description "Indicates the interface operational IP MTU.";
                }

                leaf creation-origin {
                    type types-sros:creation-origin;
                    description "Indicates the mechanism used to create this entry.";
                }

                leaf last-oper-change {
                    type yang:date-and-time;
                    description "The sysUpTime when the operational state of this interface last changed.";
                }

                container hold-time {
                    description "Enter the hold-time context";

                    container ipv4 {
                        description "Enter the ipv4 context";

                        leaf hold-timer {
                            type uint32;
                            units "seconds";
                            description
                                "The hold-timer indicates the time left before
                                 the interface comes up or goes down, depending on the ongoing
                                 transition state of the interface.";
                        }

                    } // container ipv4

                } // container hold-time

                list spoke-sdp {
                    key "sdp-bind-id";
                    description "Enter the spoke-sdp list instance";

                    leaf sdp-bind-id {
                        type types-services:sdp-bind-id;
                        description "SDP binding ID";
                    }

                    leaf oper-state {
                        type enumeration {
                            enum "up"                           { value 1; }
                            enum "down"                         { value 5; }
                        }
                        description "Indicates the operating status of this Service-SDP binding.";
                    }

                    leaf oper-flags {
                        type bits {
                            bit sdp-bind-admin-down            { position 0; }
                            bit svc-admin-down                 { position 1; }
                            bit stitching-svc-txdown           { position 2; }
                            bit sdp-oper-down                  { position 3; }
                            bit sdp-path-mtu-too-small         { position 4; }
                            bit no-ingress-vc-label            { position 5; }
                            bit no-egress-vc-label             { position 6; }
                            bit svc-mtu-mismatch               { position 7; }
                            bit vc-type-mismatch               { position 8; }
                            bit relearn-limit-exceeded         { position 9; }
                            bit ies-if-admin-down              { position 10; }
                            bit released-ingress-vc-label      { position 11; }
                            bit labels-exhausted               { position 12; }
                            bit svc-param-mismatch             { position 13; }
                            bit insufficient-bandwidth         { position 14; }
                            bit pw-peer-fault-status-bits      { position 15; }
                            bit mesh-sdp-down                  { position 16; }
                            bit not-managed-by-mcring          { position 17; }
                            bit out-of-resource                { position 18; }
                            bit mh-standby                     { position 19; }
                            bit oam-down-mep-fault             { position 20; }
                            bit oam-up-mep-fault               { position 21; }
                            bit standby-sig-slave-tx-down      { position 22; }
                            bit oper-grp-down                  { position 23; }
                            bit withdrawn-ingress-vc-label     { position 24; }
                            bit vpls-pmsi-down                 { position 25; }
                            bit rec-prot-src-mac               { position 26; }
                            bit peer-fault-status-tx-down      { position 27; }
                            bit evpn-route-conflict            { position 28; }
                            bit admin-locked                   { position 29; }
                            bit evpn-p2mp-conflict             { position 30; }
                            bit label-stack-limit-exceeded     { position 31; }
                            bit vccv-bfd-down                  { position 32; }
                            bit stitching-svc-pw-fault         { position 33; }
                        }
                        description
                            "This object indicates all the conditions that affect the
                             operating status of this SDP Bind.";
                    }

                    leaf pw-peer-status-bits {
                        type bits {
                            bit pw-not-forwarding              { position 0; }
                            bit lac-ingress-fault              { position 1; }
                            bit lac-egress-fault               { position 2; }
                            bit psn-ingress-fault              { position 3; }
                            bit psn-egress-fault               { position 4; }
                            bit pw-fwding-standby              { position 5; }
                        }
                        description
                            "Indicates bits set by the LDP peer when there is a fault on its
                             side of the pseudowire";
                    }

                    leaf peer-vccv-cv-bits {
                        type bits {
                            bit icmp-ping                      { position 0; }
                            bit lsp-ping                       { position 1; }
                            bit bfd-fault-detection            { position 2; }
                            bit bfd-fault-detection-and-signalling { position 3; }
                        }
                        description "Indicates CV type bits set by the LDP peer if it supports VCCV.";
                    }

                    leaf peer-vccv-cc-bits {
                        type bits {
                            bit pwe3-control-word              { position 0; }
                            bit mpls-router-alert-label        { position 1; }
                            bit mpls-pw-demultiplex-or-label   { position 2; }
                        }
                        description "Indicates CC type bits set by the LDP peer if it supports VCCV.";
                    }

                    leaf oper-control-word {
                        type boolean;
                        description "Status of control word.";
                    }

                    leaf pw-fault-ip-address {
                        type types-sros:ip-address;
                        description "Faulty IP address sent by peer.";
                    }

                    leaf class-forwarding-oper-state {
                        type types-sros:oper-state;
                        description "Operational state of forwarding-class based forwarding on this SDP bind.";
                    }

                    leaf creation-origin {
                        type types-sros:creation-origin;
                        description "Creation origin of the service.";
                    }

                    leaf oper-hash-label {
                        type boolean;
                        description "Indicates the negotiated value of hash lavel that is used on this SDP binding.";
                    }

                    leaf pw-local-status-bits {
                        type bits {
                            bit pw-not-forwarding              { position 0; }
                            bit lac-ingress-fault              { position 1; }
                            bit lac-egress-fault               { position 2; }
                            bit psn-ingress-fault              { position 3; }
                            bit psn-egress-fault               { position 4; }
                            bit pw-fwding-standby              { position 5; }
                        }
                        description "Indicates locally set bits when there is a fault.";
                    }

                    leaf min-required-sdp-oper-mtu {
                        type int32;
                        description "Minimum required SDP MTU size used with this SDP binding.";
                    }

                    container ingress {
                        description "Enter the ingress context";

                        leaf oper-label {
                            type uint32;
                            description "MPLS service label used by the far-end device to send packets to the local PEs sdp-bind.";
                        }

                        container statistics {
                            description "Enter the statistics context";

                            leaf forwarded-packets {
                                type yang:counter64;
                                description "Forwarded packets";
                            }

                            leaf forwarded-octets {
                                type yang:counter64;
                                description "Forwarded octets";
                            }

                            leaf dropped-packets {
                                type yang:counter64;
                                description "Dropped packets";
                            }

                            leaf dropped-octets {
                                type yang:counter64;
                                description "Dropped octets";
                            }

                        } // container statistics

                    } // container ingress

                    container egress {
                        description "Enter the egress context";

                        leaf oper-label {
                            type uint32;
                            description "MPLS service label used to send packets to the far-end device via this sdp-bind.";
                        }

                        container statistics {
                            description "Enter the statistics context";

                            leaf forwarded-packets {
                                type yang:counter64;
                                description "Forwarded packets";
                            }

                            leaf forwarded-octets {
                                type yang:counter64;
                                description "Forwarded octets";
                            }

                        } // container statistics

                    } // container egress

                } // list spoke-sdp

                container ipv4 {
                    description "Enter the ipv4 context";

                    leaf oper-state {
                        type types-sros:oper-state;
                        description "The current IPv4 operational status of this router interface.";
                    }

                    leaf down-reason {
                        type bits {
                            bit admin-disabled                 { position 0; }
                            bit service-admin-disabled         { position 1; }
                            bit port-down                      { position 2; }
                            bit address-or-parent-not-ready    { position 3; }
                            bit associated-object-not-ready    { position 4; }
                            bit rvpls-down                     { position 5; }
                            bit operational-group-down         { position 6; }
                            bit admin-destroy                  { position 7; }
                            bit no-address                     { position 8; }
                            bit no-info                        { position 9; }
                            bit hold-down-timer-running        { position 10; }
                            bit protocol-down                  { position 11; }
                            bit invalid-port-configuration     { position 12; }
                            bit unknown                        { position 13; }
                            bit no-route-distinguisher         { position 14; }
                            bit wlan-gateway-redundancy-standby { position 15; }
                            bit wlan-gateway-group-degraded    { position 16; }
                            bit ip-control-tunnel-down         { position 17; }
                            bit pdn-address-mismatch           { position 18; }
                            bit ping-check-failure             { position 19; }
                            bit port-internal-loopback         { position 20; }
                        }
                        description
                            "Indicates the reason for why the interface is operationally down.
                                             
                             Values:
                                 admin-disabled                  - Administratively disabled.
                                 service-admin-disabled          - Assiocated service is administratively disabled.
                                 port-down                       - Associated SAP/port is operationally down.
                                 address-or-parent-not-ready     - Associated address or parent interface is not ready.
                                 associated-object-not-ready     - Associated object is not ready.
                                 rvpls-down                      - Associated R-VPLS service is operationally down.
                                 operational-group-down          - Associated operational group is operationally down.
                                 admin-destroy                   - The interface is being destroyed.
                                 no-address                      - There is no address configured.
                                 no-info                         - The interface info is not present.
                                 hold-down-timer-running         - The hold down timer is running.
                                 protocol-down                   - The protocols are operationally down.
                                 invalid-port-configuration      - Invalid port configuration.
                                 unknown                         - The interface is operationally down due to some unknown reason.
                                 no-route-distinguisher          - No route-distinguisher configured in the VRF.
                                 wlan-gateway-redundancy-standby - The interface is in standby state for WLAN-GW redundancy.
                                 wlan-gateway-group-degraded     - The interface associated WLAN-GW group is in a degraded state.
                                 ip-control-tunnel-down          - The IP tunnel associated to a control-tunnel interface is operationally down.
                                 pdn-address-mismatch            - The IP address learned from the packet data network does not match the configured primary IP address.
                                 ping-check-failure              - The IP interface is or went down because of a ping-template failure.
                                 port-internal-loopback          - The IP interface is bound to a port that has an internal loopback configured.";
                    }

                    container statistics {
                        description "Enter the statistics context";

                        leaf out-packets {
                            type yang:counter64;
                            description "The number of packets transmitted by this interface.";
                        }

                        leaf out-octets {
                            type yang:counter64;
                            description "The number of octets transmitted by this interface.";
                        }

                        leaf out-discard-packets {
                            type yang:counter64;
                            description "The number of transmit packets discarded.";
                        }

                        leaf out-discard-octets {
                            type yang:counter64;
                            description "The number of transmit octets discarded.";
                        }

                        leaf in-packets {
                            type yang:counter64;
                            description "The number of packets received.";
                        }

                        leaf in-octets {
                            type yang:counter64;
                            description "The number of octets received.";
                        }

                        leaf urpf-check-fail-packets {
                            type yang:counter64;
                            description "The number of packets that fail uRPF check on this interface.";
                        }

                        leaf urpf-check-fail-octets {
                            type yang:counter64;
                            description "The number of octets in the packets that fail uRPF check.";
                        }

                        leaf out-discard-dbcast-packets {
                            type yang:counter64;
                            description "The number of directed-broadcast packets dropped.";
                        }

                        leaf out-discard-dbcast-octets {
                            type yang:counter64;
                            description "The number of directed-broadcast octets dropped.";
                        }

                        leaf in-ip-helper-redirects-packets {
                            type yang:counter64;
                            description "The number of packets redirected to the ip-helper gateway.";
                        }

                        leaf in-ip-helper-redirects-octets {
                            type yang:counter64;
                            description "The number of bytes redirected to the ip-helper gateway.";
                        }

                    } // container statistics

                    container primary {
                        description "Enter the primary context";

                        leaf oper-address {
                            type types-sros:ip-address;
                            description "Indicates the operational address of this entry.";
                        }

                        leaf creation-origin {
                            type types-sros:creation-origin;
                            description "Indicates the mechanism used to create this entry.";
                        }

                    } // container primary

                } // container ipv4

                container ipv6 {
                    description "Enter the ipv6 context";

                    container statistics {
                        description "Enter the statistics context";

                        leaf out-packets {
                            type yang:counter64;
                            description "The number of packets transmitted by this interface.";
                        }

                        leaf out-octets {
                            type yang:counter64;
                            description "The number of octets transmitted by this interface.";
                        }

                        leaf out-discard-packets {
                            type yang:counter64;
                            description "The number of transmit packets discarded.";
                        }

                        leaf out-discard-octets {
                            type yang:counter64;
                            description "The number of transmit octets discarded.";
                        }

                        leaf in-packets {
                            type yang:counter64;
                            description "The number of packets received.";
                        }

                        leaf in-octets {
                            type yang:counter64;
                            description "The number of octets received.";
                        }

                        leaf urpf-check-fail-packets {
                            type yang:counter64;
                            description "The number of packets that fail uRPF check on this interface.";
                        }

                        leaf urpf-check-fail-octets {
                            type yang:counter64;
                            description "The number of octets in the packets that fail uRPF check.";
                        }

                    } // container statistics

                } // container ipv6

                container statistics {
                    description "Enter the statistics context";

                    container ip {
                        description "Enter the ip context";

                        leaf out-packets {
                            type yang:counter64;
                            description "The number of packets transmitted by this interface.";
                        }

                        leaf out-octets {
                            type yang:counter64;
                            description "The number of octets transmitted by this interface.";
                        }

                        leaf out-discard-packets {
                            type yang:counter64;
                            description "The number of transmit packets discarded.";
                        }

                        leaf out-discard-octets {
                            type yang:counter64;
                            description "The number of transmit octets discarded.";
                        }

                        leaf in-packets {
                            type yang:counter64;
                            description "The number of packets received.";
                        }

                        leaf in-octets {
                            type yang:counter64;
                            description "The number of octets received.";
                        }

                        leaf urpf-check-fail-packets {
                            type yang:counter64;
                            description "The number of packets that fail uRPF check on this interface.";
                        }

                        leaf urpf-check-fail-octets {
                            type yang:counter64;
                            description "The number of octets in the packets that fail uRPF check.";
                        }

                    } // container ip

                    list mac {
                        key "mac-address";
                        description "Enter the mac list instance";

                        leaf mac-address {
                            type yang:mac-address;
                            description "Mac-address";
                        }

                        leaf out-packets {
                            type yang:counter64;
                            description "The number of packets sent to the mac address";
                        }

                        leaf out-octets {
                            type yang:counter64;
                            description "The number of bytes sent to the mac address";
                        }

                        leaf in-packets {
                            type yang:counter64;
                            description "The number of packets received from the mac address";
                        }

                        leaf in-octets {
                            type yang:counter64;
                            description "The number of bytes received from the mac address";
                        }

                    } // list mac

                } // container statistics

            } // list redundant-interface

            list aarp-interface {
                key "interface-name";
                description "Enter the aarp-interface list instance";

                leaf interface-name {
                    type types-sros:interface-name;
                    description "Interface name";
                }

                leaf if-index {
                    type int32;
                    description "The interface index.";
                }

                leaf system-if-index {
                    type int32;
                    description "The interface system index.";
                }

                leaf oper-state {
                    type enumeration {
                        enum "up"                           { value 1; }
                        enum "down"                         { value 2; }
                        enum "testing"                      { value 3; }
                        enum "unknown"                      { value 4; }
                        enum "dormant"                      { value 5; }
                        enum "not-present"                  { value 6; }
                        enum "lower-layer-down"             { value 7; }
                    }
                    description
                        "The current operational state of the interface.
                         This leaf has the same semantics as ifOperStatus. 
                         in RFC 2863: The Interfaces Group MIB";
                }

                leaf oper-ip-mtu {
                    type uint32;
                    units "bytes";
                    description "Indicates the interface operational IP MTU.";
                }

                leaf creation-origin {
                    type types-sros:creation-origin;
                    description "Indicates the mechanism used to create this entry.";
                }

                leaf last-oper-change {
                    type yang:date-and-time;
                    description "The sysUpTime when the operational state of this interface last changed.";
                }

                container ipv4 {
                    description "Enter the ipv4 context";

                    container statistics {
                        description "Enter the statistics context";

                        leaf out-packets {
                            type yang:counter64;
                            description "The number of packets transmitted by this interface.";
                        }

                        leaf out-octets {
                            type yang:counter64;
                            description "The number of octets transmitted by this interface.";
                        }

                        leaf out-discard-packets {
                            type yang:counter64;
                            description "The number of transmit packets discarded.";
                        }

                        leaf out-discard-octets {
                            type yang:counter64;
                            description "The number of transmit octets discarded.";
                        }

                        leaf in-packets {
                            type yang:counter64;
                            description "The number of packets received.";
                        }

                        leaf in-octets {
                            type yang:counter64;
                            description "The number of octets received.";
                        }

                        leaf urpf-check-fail-packets {
                            type yang:counter64;
                            description "The number of packets that fail uRPF check on this interface.";
                        }

                        leaf urpf-check-fail-octets {
                            type yang:counter64;
                            description "The number of octets in the packets that fail uRPF check.";
                        }

                        leaf out-discard-dbcast-packets {
                            type yang:counter64;
                            description "The number of directed-broadcast packets dropped.";
                        }

                        leaf out-discard-dbcast-octets {
                            type yang:counter64;
                            description "The number of directed-broadcast octets dropped.";
                        }

                        leaf in-ip-helper-redirects-packets {
                            type yang:counter64;
                            description "The number of packets redirected to the ip-helper gateway.";
                        }

                        leaf in-ip-helper-redirects-octets {
                            type yang:counter64;
                            description "The number of bytes redirected to the ip-helper gateway.";
                        }

                    } // container statistics

                } // container ipv4

                container ipv6 {
                    description "Enter the ipv6 context";

                    container statistics {
                        description "Enter the statistics context";

                        leaf out-packets {
                            type yang:counter64;
                            description "The number of packets transmitted by this interface.";
                        }

                        leaf out-octets {
                            type yang:counter64;
                            description "The number of octets transmitted by this interface.";
                        }

                        leaf out-discard-packets {
                            type yang:counter64;
                            description "The number of transmit packets discarded.";
                        }

                        leaf out-discard-octets {
                            type yang:counter64;
                            description "The number of transmit octets discarded.";
                        }

                        leaf in-packets {
                            type yang:counter64;
                            description "The number of packets received.";
                        }

                        leaf in-octets {
                            type yang:counter64;
                            description "The number of octets received.";
                        }

                        leaf urpf-check-fail-packets {
                            type yang:counter64;
                            description "The number of packets that fail uRPF check on this interface.";
                        }

                        leaf urpf-check-fail-octets {
                            type yang:counter64;
                            description "The number of octets in the packets that fail uRPF check.";
                        }

                    } // container statistics

                } // container ipv6

                container statistics {
                    description "Enter the statistics context";

                    container ip {
                        description "Enter the ip context";

                        leaf out-packets {
                            type yang:counter64;
                            description "The number of packets transmitted by this interface.";
                        }

                        leaf out-octets {
                            type yang:counter64;
                            description "The number of octets transmitted by this interface.";
                        }

                        leaf out-discard-packets {
                            type yang:counter64;
                            description "The number of transmit packets discarded.";
                        }

                        leaf out-discard-octets {
                            type yang:counter64;
                            description "The number of transmit octets discarded.";
                        }

                        leaf in-packets {
                            type yang:counter64;
                            description "The number of packets received.";
                        }

                        leaf in-octets {
                            type yang:counter64;
                            description "The number of octets received.";
                        }

                        leaf urpf-check-fail-packets {
                            type yang:counter64;
                            description "The number of packets that fail uRPF check on this interface.";
                        }

                        leaf urpf-check-fail-octets {
                            type yang:counter64;
                            description "The number of octets in the packets that fail uRPF check.";
                        }

                    } // container ip

                    list mac {
                        key "mac-address";
                        description "Enter the mac list instance";

                        leaf mac-address {
                            type yang:mac-address;
                            description "Mac-address";
                        }

                        leaf out-packets {
                            type yang:counter64;
                            description "The number of packets sent to the mac address";
                        }

                        leaf out-octets {
                            type yang:counter64;
                            description "The number of bytes sent to the mac address";
                        }

                        leaf in-packets {
                            type yang:counter64;
                            description "The number of packets received from the mac address";
                        }

                        leaf in-octets {
                            type yang:counter64;
                            description "The number of bytes received from the mac address";
                        }

                    } // list mac

                } // container statistics

            } // list aarp-interface

            container subscriber-management {
                description "Enter the subscriber-management context";

                container statistics {
                    description "Enter the statistics context";

                    leaf last-reset-peak-values {
                        type yang:date-and-time;
                        description "Timestamp of the last reset of the peak values";
                    }

                    list ipv4-hosts {
                        key "counter";
                        description "Enter the ipv4-hosts list instance";

                        leaf counter {
                            type types-submgt:submgt-statistics-ipv4-type;
                            description "Type of submgt ipv4 hosts counter";
                        }

                        leaf current-value {
                            type uint32;
                            description "Current value of submgt counter";
                        }

                        leaf peak-value {
                            type uint32;
                            description "Peak value of submgt counter";
                        }

                        leaf peak-timestamp {
                            type yang:date-and-time;
                            description "Peak timestamp of submgt counter";
                        }

                    } // list ipv4-hosts

                    list ipv6-hosts {
                        key "counter";
                        description "Enter the ipv6-hosts list instance";

                        leaf counter {
                            type types-submgt:submgt-statistics-ipv6-type;
                            description "Type of submgt ipv6 hosts counter";
                        }

                        leaf current-value {
                            type uint32;
                            description "Current value of submgt counter";
                        }

                        leaf peak-value {
                            type uint32;
                            description "Peak value of submgt counter";
                        }

                        leaf peak-timestamp {
                            type yang:date-and-time;
                            description "Peak timestamp of submgt counter";
                        }

                    } // list ipv6-hosts

                    list total-hosts {
                        key "counter";
                        description "Enter the total-hosts list instance";

                        leaf counter {
                            type types-submgt:submgt-statistics-total-type;
                            description "Type of submgt total hosts counter";
                        }

                        leaf current-value {
                            type uint32;
                            description "Current value of submgt counter";
                        }

                        leaf peak-value {
                            type uint32;
                            description "Peak value of submgt counter";
                        }

                        leaf peak-timestamp {
                            type yang:date-and-time;
                            description "Peak timestamp of submgt counter";
                        }

                    } // list total-hosts

                    list sessions {
                        key "counter";
                        description "Enter the sessions list instance";

                        leaf counter {
                            type types-submgt:submgt-statistics-session-type;
                            description "Type of submgt sessions counter";
                        }

                        leaf current-value {
                            type uint32;
                            description "Current value of submgt counter";
                        }

                        leaf peak-value {
                            type uint32;
                            description "Peak value of submgt counter";
                        }

                        leaf peak-timestamp {
                            type yang:date-and-time;
                            description "Peak timestamp of submgt counter";
                        }

                    } // list sessions

                } // container statistics

            } // container subscriber-management

            uses state-svc-ies-sub-if-subscriber-interface;
            uses state-svc-ies-vdo-if-video-interface;
        } // list ies

    } // grouping state-svc-ies

}
