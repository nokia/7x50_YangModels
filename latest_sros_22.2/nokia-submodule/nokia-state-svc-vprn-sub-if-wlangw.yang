submodule nokia-state-svc-vprn-sub-if-wlangw {

    yang-version "1.1";

    belongs-to nokia-state { prefix "state"; }

    import nokia-sros-yang-extensions     { prefix "sros-ext"; }
    import nokia-types-nat                { prefix "types-nat"; }
    import nokia-types-sros               { prefix "types-sros"; }
    import nokia-types-wlangw             { prefix "types-wlangw"; }


    sros-ext:sros-major-release "rel22";

    organization "Nokia";

    contact
        "Nokia SR OS Support
         Web: <http://www.nokia.com>";

    description
        "Nokia YANG Data model with operational state for vprn service subscriber interface WLAN Gateway on SR OS based routers.

         Copyright 2016 Nokia. All rights reserved. Reproduction of this document
         is authorized on the condition that the foregoing copyright notice is included.

         This nokia-state-svc-vprn-sub-if-wlangw YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";

    revision "2021-11-05";

    grouping state-svc-vprn-sub-if-wlangw-wlan-gw {
        container wlan-gw {
            description "Enter the wlan-gw context";

            container pool-manager {
                description "Enter the pool-manager context";

                list isa-subnet {
                    key "prefix";
                    description "Enter the isa-subnet list instance";

                    leaf prefix {
                        type types-sros:ipv6-prefix;
                        description "Pool prefix";
                    }

                    leaf address-family {
                        type types-wlangw:pool-address-family;
                        description "Address family of the pool prefix";
                    }

                    leaf deprecated {
                        type boolean;
                        description "This prefix originally belonged to another ISA and is kept for redundancy purposes";
                    }

                    leaf usage-level {
                        type types-sros:percent;
                        description "Percentage of addresses in use for the prefix";
                    }

                    leaf dhcpv6-option {
                        type types-sros:hex-string {
                            length "0..512";
                        }
                        description "DHCPv6 options as defined in RFC 3315 section 22";
                    }

                    leaf remaining-lease-time {
                        type uint32;
                        units "seconds";
                        description "Remaining lease time of the pool prefix";
                    }

                    leaf wlan-gw-group {
                        type uint32 {
                            range "1..4";
                        }
                        description "The group identifier of the ISA for the given prefix";
                    }

                    leaf member {
                        type types-nat:bb-group-member;
                        description "The member identifier of the ISA for the given prefix";
                    }

                    leaf ipv4-prefix {
                        type types-sros:ipv4-prefix;
                        description "IPv4 subnet address of the pool prefix";
                    }

                    leaf default-gateway {
                        type types-sros:ipv4-unicast-address;
                        description "Default gateway of the IPv4 subnet of the pool prefix";
                    }

                    leaf-list dns-server {
                        type types-sros:ipv6-address;
                        description "All DNS server IPv6 addresses provided by the DHCPv6 server";
                    }

                } // list isa-subnet

            } // container pool-manager

            container redundancy {
                description "Enter the redundancy context";

                leaf active {
                    type boolean;
                    description "Whether this WLAN Gateway is the active gateway in an active/standby redundancy setup.";
                }

            } // container redundancy

        } // container wlan-gw

    } // grouping state-svc-vprn-sub-if-wlangw-wlan-gw

}
