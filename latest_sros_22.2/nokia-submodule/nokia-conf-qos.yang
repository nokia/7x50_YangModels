submodule nokia-conf-qos {

    yang-version "1.1";

    belongs-to nokia-conf { prefix "conf"; }

    import ietf-yang-types                { prefix "yang"; }
    import nokia-sros-yang-extensions     { prefix "sros-ext"; }
    import nokia-types-filter             { prefix "types-filter"; }
    import nokia-types-qos                { prefix "types-qos"; }
    import nokia-types-services           { prefix "types-services"; }
    import nokia-types-sros               { prefix "types-sros"; }

    include nokia-conf-groups;


    sros-ext:sros-major-release "rel22";

    organization "Nokia";

    contact
        "Nokia SR OS Support
         Web: <http://www.nokia.com>";

    description
        "Nokia YANG Data model to configure QoS policies on SR OS based routers.

         Copyright 2016 Nokia. All rights reserved. Reproduction of this document
         is authorized on the condition that the foregoing copyright notice is included.

         This nokia-conf-qos YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";

    revision "2022-01-18";

    grouping conf-qos {
        container qos {
            description "Enter the qos context";

            leaf-list apply-groups {
                type leafref {
                    path "../../groups/group/name";
                }
                max-elements 8;
                ordered-by user;
                description "Apply a configuration group at this level";
            }

            leaf-list apply-groups-exclude {
                type leafref {
                    path "../../groups/group/name";
                }
                max-elements 8;
                ordered-by user;
                description "Exclude a configuration group at this level";
            }

            container md-auto-id {
                description "Enter the md-auto-id context";

                container qos-policy-id-range {
                    presence "Enable the qos-policy-id-range context";
                    description "Enable the qos-policy-id-range context";

                    leaf start {
                        type types-qos:qos-policy-id {
                            range "2..65535";
                        }
                        sros-ext:immutable;
                        mandatory true;
                        description "Lower bound of the ID range";
                    }

                    leaf end {
                        type types-qos:qos-policy-id {
                            range "2..65535";
                        }
                        sros-ext:immutable;
                        mandatory true;
                        description "Upper bound of the ID range";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                } // container qos-policy-id-range

            } // container md-auto-id

            list sap-ingress {
                key "sap-ingress-policy-name";
                description "Enter the sap-ingress list instance";

                leaf sap-ingress-policy-name {
                    type types-qos:qos-policy-name;
                    description "Policy name";
                }

                leaf policy-id {
                    type types-qos:qos-policy-id;
                    sros-ext:immutable;
                    description "Ingress SAP QoS policy ID";
                }

                leaf policer-allocation {
                    type types-qos:sap-ingress-policer-alloc;
                    sros-ext:immutable;
                    default "none";
                    description "FC policer mapping for SAP ingress policy";
                }

                leaf scope {
                    type types-qos:item-scope;
                    default "template";
                    description "Scope of the policy";
                }

                leaf description {
                    type types-sros:description;
                    description "Text description";
                }

                leaf default-fc {
                    type types-qos:sap-ingress-fc-name;
                    description "Default forwarding class or sub forwarding class for traffic not matching specific classification";
                }

                leaf default-priority {
                    type types-qos:default-priority;
                    default "low";
                    description "Priority to assign to traffic ingressing as the default action queue";
                }

                leaf policers-hqos-manageable {
                    type boolean;
                    default "false";
                    description "Manage policers through the hierarchical QoS process";
                }

                leaf ingress-classification-policy {
                    type leafref {
                        path "../../ingress-classification-policy/ingress-classification-policy-name";
                    }
                    description "Attach ingress classification policy";
                }

                leaf-list apply-groups {
                    type leafref {
                        path "../../../groups/group/name";
                    }
                    max-elements 8;
                    ordered-by user;
                    description "Apply a configuration group at this level";
                }

                leaf-list apply-groups-exclude {
                    type leafref {
                        path "../../../groups/group/name";
                    }
                    max-elements 8;
                    ordered-by user;
                    description "Exclude a configuration group at this level";
                }

                container subscriber-mgmt {
                    description "Enter the subscriber-mgmt context";

                    container pcc-rule-entry {
                        description "Enter the pcc-rule-entry context";

                        container range {
                            presence "Enable the range context";
                            description "Enable the range context";

                            leaf start {
                                type types-qos:entry-id;
                                mandatory true;
                                description "Lower bound of the filter and QoS policy entries range";
                            }

                            leaf end {
                                type types-qos:entry-id;
                                mandatory true;
                                description "Upper bound of the filter and QoS policy entries range";
                            }

                        } // container range

                    } // container pcc-rule-entry

                    container dynamic-policer {
                        description "Enter the dynamic-policer context";

                        leaf cbs {
                            type types-qos:plcr-burst-size;
                            description "Exceed threshold of the CIR leaky bucket of the policer";
                        }

                        leaf mbs {
                            type types-qos:plcr-burst-size;
                            description "High priority violate threshold of PIR leaky bucket of this policer";
                        }

                        leaf packet-byte-offset {
                            type types-qos:per-packet-offset;
                            default "0";
                            description "Size of each packet, handled by the policer, to be modified";
                        }

                        leaf stat-mode {
                            type types-qos:ingress-policer-stat-mode;
                            default "minimal";
                            description "Mode of statistics collected by the policer";
                        }

                        container policer-id-range {
                            presence "Enable the policer-id-range context";
                            description "Enable the policer-id-range context";

                            leaf start {
                                type types-qos:ingress-policer-id;
                                mandatory true;
                                description "Lower bound of the dynamic policer ID range";
                            }

                            leaf end {
                                type types-qos:ingress-policer-id;
                                mandatory true;
                                description "Upper bound of the dynamic policer ID range";
                            }

                        } // container policer-id-range

                        container arbiter-parent {
                            description "Enter the arbiter-parent context";

                            leaf arbiter-name {
                                type types-sros:named-item;
                                description "Arbiter name";
                            }

                            leaf level {
                                type types-qos:hierarchy-level;
                                default "1";
                                description "Level of priority while feeding to the parent";
                            }

                            leaf weight {
                                type types-qos:weight {
                                    range "1..100";
                                }
                                default "1";
                                description "Weight to be used by the arbiter for feeding this policer";
                            }

                        } // container arbiter-parent

                    } // container dynamic-policer

                } // container subscriber-mgmt

                container mac-criteria {
                    description "Enter the mac-criteria context";

                    leaf type {
                        type types-qos:mac-criteria-type;
                        sros-ext:immutable;
                        default "normal";
                        description "MAC criteria filter type";
                    }

                    list entry {
                        key "entry-id";
                        description "Enter the entry list instance";

                        leaf entry-id {
                            type types-qos:entry-id;
                            description "Identifier for MAC match criteria and the corresponding action for a SAP-ingress policy";
                        }

                        leaf description {
                            type types-sros:description;
                            description "Text description";
                        }

                        leaf-list apply-groups {
                            type leafref {
                                path "../../../../../groups/group/name";
                            }
                            max-elements 8;
                            ordered-by user;
                            description "Apply a configuration group at this level";
                        }

                        leaf-list apply-groups-exclude {
                            type leafref {
                                path "../../../../../groups/group/name";
                            }
                            max-elements 8;
                            ordered-by user;
                            description "Exclude a configuration group at this level";
                        }

                        container match {
                            description "Enter the match context";

                            leaf frame-type {
                                type types-qos:mac-frame-type;
                                description "Match MAC criteria for ingress SAP QoS policy";
                            }

                            leaf etype {
                                type types-services:etype-value;
                                description "Ethernet type";
                            }

                            leaf snap-pid {
                                type int32 {
                                    range "0..65535";
                                }
                                description "Parameter snap-pid as MAC filter match criteria";
                            }

                            leaf snap-oui {
                                type enumeration {
                                    enum "zero"                         { value 2; }
                                    enum "non-zero"                     { value 3; }
                                }
                                description "Parameter snap-oui as MAC filter match criteria";
                            }

                            leaf atm-vci {
                                type types-qos:atm-vc-indentifier;
                                description "ATM VC Identifier to match as part of the MAC match criteria";
                            }

                            container src-mac {
                                presence "Enable the src-mac context";
                                description "Enable the src-mac context";

                                leaf address {
                                    type yang:mac-address;
                                    mandatory true;
                                    description "Source MAC address as QoS policy match criterion";
                                }

                                leaf mask {
                                    type yang:mac-address;
                                    default "ff:ff:ff:ff:ff:ff";
                                    description "Mask for source MAC address";
                                }

                            } // container src-mac

                            container dst-mac {
                                presence "Enable the dst-mac context";
                                description "Enable the dst-mac context";

                                leaf address {
                                    type yang:mac-address;
                                    mandatory true;
                                    description "Destination MAC address as QoS policy match criterion";
                                }

                                leaf mask {
                                    type yang:mac-address;
                                    default "ff:ff:ff:ff:ff:ff";
                                    description "Mask for destination MAC address";
                                }

                            } // container dst-mac

                            container dot1p {
                                presence "Enable the dot1p context";
                                description "Enable the dot1p context";

                                leaf priority {
                                    type types-qos:dot1p-priority;
                                    mandatory true;
                                    description "802.1P priority value to use as the match criterion";
                                }

                                leaf mask {
                                    type types-qos:dot1p-priority;
                                    default "7";
                                    description "3-bit mask for the 802.1p value";
                                }

                            } // container dot1p

                            container llc-dsap {
                                presence "Enable the llc-dsap context";
                                description "Enable the llc-dsap context";

                                leaf dsap {
                                    type types-qos:service-access-point;
                                    mandatory true;
                                    description "DSAP value";
                                }

                                leaf mask {
                                    type types-qos:service-access-point;
                                    default "255";
                                    description "DSAP mask";
                                }

                            } // container llc-dsap

                            container llc-ssap {
                                presence "Enable the llc-ssap context";
                                description "Enable the llc-ssap context";

                                leaf ssap {
                                    type types-qos:service-access-point;
                                    mandatory true;
                                    description "SSAP value";
                                }

                                leaf mask {
                                    type types-qos:service-access-point;
                                    default "255";
                                    description "Source SAP mask";
                                }

                            } // container llc-ssap

                            container inner-tag {
                                presence "Enable the inner-tag context";
                                description "Enable the inner-tag context";

                                leaf vlan {
                                    type int32 {
                                        range "0..4095";
                                    }
                                    mandatory true;
                                    description "Value to match against the VID of the second VLAN tag";
                                }

                                leaf mask {
                                    type uint32 {
                                        range "1..4095";
                                    }
                                    default "4095";
                                    description "Mask to VID of the inner VLAN tag before comparing it with the inner-tag or outer-tag value";
                                }

                            } // container inner-tag

                            container outer-tag {
                                presence "Enable the outer-tag context";
                                description "Enable the outer-tag context";

                                leaf vlan {
                                    type int32 {
                                        range "0..4095";
                                    }
                                    mandatory true;
                                    description "Match against VID of the first VLAN tag in the packet carried transparently through service";
                                }

                                leaf mask {
                                    type uint32 {
                                        range "1..4095";
                                    }
                                    default "4095";
                                    description "First tag carried transparently through the service";
                                }

                            } // container outer-tag

                        } // container match

                        container action {
                            description "Enter the action context";

                            leaf type {
                                type types-qos:criteria-action-type;
                                default "ignore-match";
                                description "Action for criteria entry";
                            }

                            leaf fc {
                                type types-qos:sap-ingress-fc-name;
                                description "Forwarding class or sub forwarding class to classify traffic matching the criteria";
                            }

                            leaf priority {
                                type types-qos:priority;
                                description "Priority for the packet";
                            }

                            leaf policer {
                                type leafref {
                                    path "../../../../policer/policer-id";
                                }
                                description "Policer identifier for the traffic matching MAC Criteria";
                            }

                        } // container action

                    } // list entry

                } // container mac-criteria

                container ip-criteria {
                    description "Enter the ip-criteria context";

                    leaf type {
                        type types-qos:ip-filter-type;
                        sros-ext:immutable;
                        default "normal";
                        description "IPv4 criteria entry type";
                    }

                    list entry {
                        key "entry-id";
                        description "Enter the entry list instance";

                        leaf entry-id {
                            type types-qos:entry-id;
                            description "IP criteria entry to create or edit for the policy";
                        }

                        leaf description {
                            type types-sros:description;
                            description "Text description";
                        }

                        leaf tag {
                            type uint32 {
                                range "0..255";
                            }
                            default "0";
                            description "Tag ID associated with the criteria entry";
                        }

                        leaf-list apply-groups {
                            type leafref {
                                path "../../../../../groups/group/name";
                            }
                            max-elements 8;
                            ordered-by user;
                            description "Apply a configuration group at this level";
                        }

                        leaf-list apply-groups-exclude {
                            type leafref {
                                path "../../../../../groups/group/name";
                            }
                            max-elements 8;
                            ordered-by user;
                            description "Exclude a configuration group at this level";
                        }

                        container match {
                            description "Enter the match context";

                            leaf protocol {
                                type types-sros:match-ip-protocol;
                                description "IP protocol to match";
                            }

                            leaf dscp {
                                type types-qos:dscp-name;
                                description "DSCP value to match in the packet";
                            }

                            leaf fragment {
                                type enumeration {
                                    enum "false"                        { value 2; }
                                    enum "true"                         { value 3; }
                                }
                                description "Match performed when the packet is either a fragment or not, or matches all packets";
                            }

                            container dst-ip {
                                description "Enter the dst-ip context";

                                choice dst-ip {
                                    case address-and-mask-or-prefix {

                                        leaf address {
                                            type union {
                                                type types-sros:ipv4-address;
                                                type types-sros:ipv4-prefix-with-host-bits;
                                            }
                                            description "Destination IPv4 address for SAP QoS policy match";
                                        }

                                        leaf mask {
                                            type types-sros:ipv4-address;
                                            description "IP address to match with source IP of the packet";
                                        }

                                    }
                                    case ip-prefix-list {

                                        leaf ip-prefix-list {
                                            type leafref {
                                                path "../../../../../../match-list/ip-prefix-list/prefix-list-name";
                                            }
                                            description "IP-prefix list as match criterion";
                                        }

                                    }
                                }
                            } // container dst-ip

                            container src-ip {
                                description "Enter the src-ip context";

                                choice src-ip {
                                    case address-and-mask-or-prefix {

                                        leaf address {
                                            type union {
                                                type types-sros:ipv4-address;
                                                type types-sros:ipv4-prefix-with-host-bits;
                                            }
                                            description "Source IPv4 address for SAP QoS policy match criterion";
                                        }

                                        leaf mask {
                                            type types-sros:ipv4-address;
                                            description "IP address to match with source IP of the packet";
                                        }

                                    }
                                    case ip-prefix-list {

                                        leaf ip-prefix-list {
                                            type leafref {
                                                path "../../../../../../match-list/ip-prefix-list/prefix-list-name";
                                            }
                                            description "IP-prefix list as match criterion";
                                        }

                                    }
                                }
                            } // container src-ip

                            container src-port {
                                description "Enter the src-port context";

                                choice port-match-mapping {
                                    case lt {

                                        leaf lt {
                                            type int32 {
                                                range "0..65535";
                                            }
                                            description "Value 'less than' assigned as match condition";
                                        }

                                    }
                                    case eq {

                                        leaf eq {
                                            type int32 {
                                                range "0..65535";
                                            }
                                            description "Value 'equal to' assigned as match condition";
                                        }

                                    }
                                    case gt {

                                        leaf gt {
                                            type int32 {
                                                range "0..65535";
                                            }
                                            description "Value 'greater than' assigned as match condition";
                                        }

                                    }
                                    case range {

                                        container range {
                                            description "Enter the range context";

                                            leaf start {
                                                type int32 {
                                                    range "0..65535";
                                                }
                                                description "Lower bound of the port range";
                                            }

                                            leaf end {
                                                type int32 {
                                                    range "0..65535";
                                                }
                                                description "Upper bound of the port range";
                                            }

                                        } // container range

                                    }
                                }
                            } // container src-port

                            container dst-port {
                                description "Enter the dst-port context";

                                choice port-match-mapping {
                                    case lt {

                                        leaf lt {
                                            type int32 {
                                                range "0..65535";
                                            }
                                            description "Value 'less than' assigned as match condition";
                                        }

                                    }
                                    case eq {

                                        leaf eq {
                                            type int32 {
                                                range "0..65535";
                                            }
                                            description "Value 'equal to' assigned as match condition";
                                        }

                                    }
                                    case gt {

                                        leaf gt {
                                            type int32 {
                                                range "0..65535";
                                            }
                                            description "Value 'greater than' assigned as match condition";
                                        }

                                    }
                                    case range {

                                        container range {
                                            description "Enter the range context";

                                            leaf start {
                                                type int32 {
                                                    range "0..65535";
                                                }
                                                description "Lower bound of the port range";
                                            }

                                            leaf end {
                                                type int32 {
                                                    range "0..65535";
                                                }
                                                description "Upper bound of the port range";
                                            }

                                        } // container range

                                    }
                                }
                            } // container dst-port

                            container vxlan-vni {
                                description "Enter the vxlan-vni context";

                                choice vxlan-vni-mapping {
                                    case eq {

                                        leaf eq {
                                            type uint32 {
                                                range "1..16777215";
                                            }
                                            description "Value 'equal to' assigned as match condition";
                                        }

                                    }
                                    case range {

                                        container range {
                                            description "Enter the range context";

                                            leaf start {
                                                type uint32 {
                                                    range "1..16777215";
                                                }
                                                description "Lower bound of the VNI range";
                                            }

                                            leaf end {
                                                type uint32 {
                                                    range "1..16777215";
                                                }
                                                description "Upper bound of the VNI range";
                                            }

                                        } // container range

                                    }
                                }
                            } // container vxlan-vni

                        } // container match

                        container action {
                            description "Enter the action context";

                            leaf type {
                                type types-qos:criteria-action-type;
                                default "ignore-match";
                                description "Action for criteria entry";
                            }

                            leaf fc {
                                type types-qos:sap-ingress-fc-name;
                                description "Forwarding class or sub forwarding class to classify traffic matching the criteria";
                            }

                            leaf priority {
                                type types-qos:priority;
                                description "Priority for the packet";
                            }

                            leaf policer {
                                type leafref {
                                    path "../../../../policer/policer-id";
                                }
                                description "Policer identifier for the traffic matching MAC Criteria";
                            }

                        } // container action

                    } // list entry

                } // container ip-criteria

                container ipv6-criteria {
                    description "Enter the ipv6-criteria context";

                    leaf type {
                        type types-qos:ip-filter-type;
                        sros-ext:immutable;
                        default "normal";
                        description "IPv6 criteria entry type";
                    }

                    list entry {
                        key "entry-id";
                        description "Enter the entry list instance";

                        leaf entry-id {
                            type types-qos:entry-id;
                            description "IPv6 criteria entry to create or edit for the policy";
                        }

                        leaf description {
                            type types-sros:description;
                            description "Text description";
                        }

                        leaf tag {
                            type uint32 {
                                range "0..255";
                            }
                            default "0";
                            description "Tag ID associated with the criteria entry";
                        }

                        leaf-list apply-groups {
                            type leafref {
                                path "../../../../../groups/group/name";
                            }
                            max-elements 8;
                            ordered-by user;
                            description "Apply a configuration group at this level";
                        }

                        leaf-list apply-groups-exclude {
                            type leafref {
                                path "../../../../../groups/group/name";
                            }
                            max-elements 8;
                            ordered-by user;
                            description "Exclude a configuration group at this level";
                        }

                        container match {
                            description "Enter the match context";

                            leaf next-header {
                                type types-sros:match-ip-protocol;
                                description "IP protocol to match";
                            }

                            leaf dscp {
                                type types-qos:dscp-name;
                                description "DSCP value to match in the packet";
                            }

                            leaf fragment {
                                type enumeration {
                                    enum "false"                        { value 2; }
                                    enum "true"                         { value 3; }
                                    enum "first-only"                   { value 4; }
                                    enum "non-first-only"               { value 5; }
                                }
                                description "Match performed when the packet is either a fragment or not, or matches all packets";
                            }

                            container dst-ip {
                                description "Enter the dst-ip context";

                                choice dst-ip {
                                    case address-and-mask-or-prefix {

                                        leaf address {
                                            type union {
                                                type types-sros:ipv6-address;
                                                type types-sros:ipv6-prefix-with-host-bits;
                                            }
                                            description "IPv6 address to match destination IP of the packet";
                                        }

                                        leaf mask {
                                            type types-sros:ipv6-address;
                                            description "IP address to match with source IP of the packet";
                                        }

                                    }
                                    case ipv6-prefix-list {

                                        leaf ipv6-prefix-list {
                                            type leafref {
                                                path "../../../../../../match-list/ipv6-prefix-list/prefix-list-name";
                                            }
                                            description "IPv6 prefix list as match criterion for IPv6 addresses";
                                        }

                                    }
                                }
                            } // container dst-ip

                            container src-ip {
                                description "Enter the src-ip context";

                                choice src-ip {
                                    case address-and-mask-or-prefix {

                                        leaf address {
                                            type union {
                                                type types-sros:ipv6-address;
                                                type types-sros:ipv6-prefix-with-host-bits;
                                            }
                                            description "IPv4 address to match";
                                        }

                                        leaf mask {
                                            type types-sros:ipv6-address;
                                            description "IP address to match with source IP of the packet";
                                        }

                                    }
                                    case ipv6-prefix-list {

                                        leaf ipv6-prefix-list {
                                            type leafref {
                                                path "../../../../../../match-list/ipv6-prefix-list/prefix-list-name";
                                            }
                                            description "IPv6 prefix list as match criterion for IPv6 addresses";
                                        }

                                    }
                                }
                            } // container src-ip

                            container src-port {
                                description "Enter the src-port context";

                                choice port-match-mapping {
                                    case lt {

                                        leaf lt {
                                            type int32 {
                                                range "0..65535";
                                            }
                                            description "Value 'less than' assigned as match condition";
                                        }

                                    }
                                    case eq {

                                        leaf eq {
                                            type int32 {
                                                range "0..65535";
                                            }
                                            description "Value 'equal to' assigned as match condition";
                                        }

                                    }
                                    case gt {

                                        leaf gt {
                                            type int32 {
                                                range "0..65535";
                                            }
                                            description "Value 'greater than' assigned as match condition";
                                        }

                                    }
                                    case range {

                                        container range {
                                            description "Enter the range context";

                                            leaf start {
                                                type int32 {
                                                    range "0..65535";
                                                }
                                                description "Lower bound of the port range";
                                            }

                                            leaf end {
                                                type int32 {
                                                    range "0..65535";
                                                }
                                                description "Upper bound of the port range";
                                            }

                                        } // container range

                                    }
                                }
                            } // container src-port

                            container dst-port {
                                description "Enter the dst-port context";

                                choice port-match-mapping {
                                    case lt {

                                        leaf lt {
                                            type int32 {
                                                range "0..65535";
                                            }
                                            description "Value 'less than' assigned as match condition";
                                        }

                                    }
                                    case eq {

                                        leaf eq {
                                            type int32 {
                                                range "0..65535";
                                            }
                                            description "Value 'equal to' assigned as match condition";
                                        }

                                    }
                                    case gt {

                                        leaf gt {
                                            type int32 {
                                                range "0..65535";
                                            }
                                            description "Value 'greater than' assigned as match condition";
                                        }

                                    }
                                    case range {

                                        container range {
                                            description "Enter the range context";

                                            leaf start {
                                                type int32 {
                                                    range "0..65535";
                                                }
                                                description "Lower bound of the port range";
                                            }

                                            leaf end {
                                                type int32 {
                                                    range "0..65535";
                                                }
                                                description "Upper bound of the port range";
                                            }

                                        } // container range

                                    }
                                }
                            } // container dst-port

                            container vxlan-vni {
                                description "Enter the vxlan-vni context";

                                choice vxlan-vni-mapping {
                                    case eq {

                                        leaf eq {
                                            type uint32 {
                                                range "1..16777215";
                                            }
                                            description "Value 'equal to' assigned as match condition";
                                        }

                                    }
                                    case range {

                                        container range {
                                            description "Enter the range context";

                                            leaf start {
                                                type uint32 {
                                                    range "1..16777215";
                                                }
                                                description "Lower bound of the VNI range";
                                            }

                                            leaf end {
                                                type uint32 {
                                                    range "1..16777215";
                                                }
                                                description "Upper bound of the VNI range";
                                            }

                                        } // container range

                                    }
                                }
                            } // container vxlan-vni

                        } // container match

                        container action {
                            description "Enter the action context";

                            leaf type {
                                type types-qos:criteria-action-type;
                                default "ignore-match";
                                description "Action for criteria entry";
                            }

                            leaf fc {
                                type types-qos:sap-ingress-fc-name;
                                description "Forwarding class or sub forwarding class to classify traffic matching the criteria";
                            }

                            leaf priority {
                                type types-qos:priority;
                                description "Priority for the packet";
                            }

                            leaf policer {
                                type leafref {
                                    path "../../../../policer/policer-id";
                                }
                                description "Policer identifier for the traffic matching MAC Criteria";
                            }

                        } // container action

                    } // list entry

                } // container ipv6-criteria

                list queue {
                    key "queue-id";
                    description "Enter the queue list instance";

                    leaf queue-id {
                        type types-qos:ingress-queue-id;
                        description "SAP-ingress policer identifier";
                    }

                    leaf multipoint {
                        type boolean;
                        sros-ext:immutable;
                        description "Apply as a multicast queue";
                    }

                    leaf queue-type {
                        type types-qos:queue-type;
                        sros-ext:immutable;
                        default "auto-expedited";
                        description "Priority that this queue receives from the hardware level schedulers";
                    }

                    leaf queue-mode {
                        type enumeration {
                            enum "priority"                     { value 1; }
                            enum "profile"                      { value 2; }
                        }
                        sros-ext:immutable;
                        default "priority";
                        description "Operating mode for this queue";
                    }

                    leaf cbs {
                        type union {
                            type int32 {
                                range "0..1048576";
                            }
                            type enumeration {
                                enum "auto"                         { value -1; }
                            }
                        }
                        units "kilobytes";
                        default "auto";
                        description "Reserved buffer space for the queue";
                    }

                    leaf mbs {
                        type union {
                            type types-qos:bytes {
                                range "0..1073741824";
                            }
                            type enumeration {
                                enum "auto"                         { value -1; }
                            }
                        }
                        units "bytes";
                        default "auto";
                        description "Maximum buffer space that is allowed for queue";
                    }

                    leaf burst-limit {
                        type union {
                            type types-qos:bytes {
                                range "1..14000000";
                            }
                            type enumeration {
                                enum "auto"                         { value -1; }
                            }
                        }
                        default "auto";
                        description "Explicit shaping burst size of a queue";
                    }

                    leaf adv-config-policy {
                        type leafref {
                            path "../../../adv-config-policy/adv-config-policy-name";
                        }
                        description "Name of the advanced configuration policy to apply with this queue";
                    }

                    leaf packet-byte-offset {
                        type types-qos:per-packet-offset {
                            range "-32..30";
                        }
                        default "0";
                        description "Value of the adjustment on the size of each packet for queue accounting";
                    }

                    leaf cir-non-profiling {
                        type boolean;
                        default "false";
                        description "Prevent profile modification of CIR dependent packets";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                    choice rate-or-percent-rate {
                        default "rate";
                        case rate {

                            container rate {
                                description "Enter the rate context";

                                leaf pir {
                                    type types-qos:queue-pir-rate-maximum;
                                    units "kilobps";
                                    default "max";
                                    description "Administrative PIR";
                                }

                                choice rate-cir-fir-or-police {
                                    default "cir-fir";
                                    case cir-fir {

                                        leaf cir {
                                            type types-qos:queue-cir-rate-maximum;
                                            units "kilobps";
                                            default "0";
                                            description "Administrative CIR";
                                        }

                                        leaf fir {
                                            type types-qos:queue-fir-rate-maximum;
                                            units "kilobps";
                                            default "0";
                                            description "Administrative FIR";
                                        }

                                    }
                                    case police {

                                        leaf police {
                                            type empty;
                                            description "Drop the traffic feeding into queue above the PIR rate";
                                        }

                                    }
                                }
                            } // container rate

                        }
                        case percent-rate {

                            container percent-rate {
                                description "Enter the percent-rate context";

                                leaf pir {
                                    type decimal64 {
                                        range "0.01..100.00";
                                        fraction-digits 2;
                                    }
                                    description "Administrative PIR percent";
                                }

                                leaf reference-rate {
                                    type enumeration {
                                        enum "port-limit"                   { value 2; }
                                        enum "local-limit"                  { value 3; }
                                        enum "reference-port-limit"         { value 4; }
                                    }
                                    default "port-limit";
                                    description "Reference rate";
                                }

                                choice percent-rate-cir-fir-or-police {
                                    default "cir-fir";
                                    case cir-fir {

                                        leaf cir {
                                            type decimal64 {
                                                range "0.00..100.00";
                                                fraction-digits 2;
                                            }
                                            default "0.00";
                                            description "Administrative CIR percent";
                                        }

                                        leaf fir {
                                            type decimal64 {
                                                range "0.00..100.00";
                                                fraction-digits 2;
                                            }
                                            default "0.00";
                                            description "Administrative FIR percent";
                                        }

                                    }
                                    case police {

                                        leaf police {
                                            type empty;
                                            description "Drop out-of-profile traffic feeding into queue instance";
                                        }

                                    }
                                }
                            } // container percent-rate

                        }
                    }
                    container scheduler-parent {
                        description "Enter the scheduler-parent context";

                        leaf scheduler-name {
                            type types-sros:named-item;
                            description "Scheduler name";
                        }

                        leaf level {
                            type types-qos:hierarchy-level;
                            default "1";
                            description "Level of priority while feeding to the parent";
                        }

                        leaf weight {
                            type types-qos:weight;
                            default "1";
                            description "Weight to be used by the scheduler for feeding this queue";
                        }

                        leaf cir-level {
                            type types-qos:cir-level;
                            default "0";
                            description "Level of priority while feeding to the parent";
                        }

                        leaf cir-weight {
                            type types-qos:cir-weight;
                            default "1";
                            description "Weight that is used by the scheduler until the committed rate for feeding this queue";
                        }

                    } // container scheduler-parent

                    container adaptation-rule {
                        description "Enter the adaptation-rule context";

                        leaf pir {
                            type types-qos:adaptation-rule;
                            default "closest";
                            description "Constraint used when deriving the operational PIR value";
                        }

                        leaf cir {
                            type types-qos:adaptation-rule;
                            default "closest";
                            description "Constraint used when deriving the operational CIR value";
                        }

                        leaf fir {
                            type types-qos:adaptation-rule;
                            default "closest";
                            description "Constraint used when deriving the operational FIR value";
                        }

                    } // container adaptation-rule

                    container drop-tail {
                        description "Enter the drop-tail context";

                        container low {
                            description "Enter the low context";

                            leaf percent-reduction-from-mbs {
                                type types-qos:burst-percent;
                                description "Low drop-tail percent from MBS that is reduced";
                            }

                        } // container low

                    } // container drop-tail

                } // list queue

                list dscp {
                    key "dscp-name";
                    description "Enter the dscp list instance";

                    leaf dscp-name {
                        type types-qos:dscp-name;
                        description "Name for the Differentiated Services Code Point (DSCP)";
                    }

                    leaf fc {
                        type types-qos:sap-ingress-fc-name;
                        description "Forwarding class or sub forwarding class to classify traffic matching the specific DSCP";
                    }

                    leaf priority {
                        type types-qos:priority;
                        description "Priority for the packet";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                } // list dscp

                list dot1p {
                    key "dot1p-value";
                    description "Enter the dot1p list instance";

                    leaf dot1p-value {
                        type types-qos:dot1p-priority;
                        description "Dot1p value to match in the packet";
                    }

                    leaf fc {
                        type types-qos:sap-ingress-fc-name;
                        description "Forwarding class or sub forwarding class to classify traffic matching the specific Dot1p";
                    }

                    leaf priority {
                        type types-qos:priority;
                        description "Priority for packets that match the Dot1p value";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                } // list dot1p

                list prec {
                    key "prec-value";
                    description "Enter the prec list instance";

                    leaf prec-value {
                        type types-qos:precedence-value;
                        description "Precedence value for which mapping is performed";
                    }

                    leaf fc {
                        type types-qos:sap-ingress-fc-name;
                        description "Forwarding class or sub forwarding class to classify traffic matching the precedence value";
                    }

                    leaf priority {
                        type types-qos:priority;
                        description "Priority for the matching traffic";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                } // list prec

                list lsp-exp {
                    key "lsp-exp-value";
                    description "Enter the lsp-exp list instance";

                    leaf lsp-exp-value {
                        type types-qos:lsp-exp-value;
                        description "Value to assign the unique MPLS LSP EXP value that will match the lsp-exp rule";
                    }

                    leaf fc {
                        type types-qos:sap-ingress-fc-name;
                        description "Forwarding class or sub forwarding class to classify traffic matching the LSP EXP value";
                    }

                    leaf priority {
                        type types-qos:priority;
                        description "Priority for the matching traffic";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                } // list lsp-exp

                list policer {
                    key "policer-id";
                    description "Enter the policer list instance";

                    leaf policer-id {
                        type types-qos:ingress-policer-id;
                        description "SAP-ingress policer identifier";
                    }

                    leaf description {
                        type types-sros:description;
                        description "Text description";
                    }

                    leaf stat-mode {
                        type types-qos:sap-ingress-policer-stat-mode;
                        description "Mode of statistics collected by the policer";
                    }

                    leaf mbs {
                        type types-qos:plcr-burst-size;
                        description "High priority violate threshold of PIR leaky bucket";
                    }

                    leaf high-prio-only {
                        type types-qos:burst-percent;
                        description "Percentage of PIR leaky bucket's MBS of this policer that is reserved for high priority traffic";
                    }

                    leaf cbs {
                        type types-qos:plcr-burst-size;
                        description "Exceed threshold of the CIR leaky bucket of the policer";
                    }

                    leaf packet-byte-offset {
                        type types-qos:per-packet-offset;
                        default "0";
                        description "Size of each packet, handled by the policer, to be modified";
                    }

                    leaf adv-config-policy {
                        type leafref {
                            path "../../../adv-config-policy/adv-config-policy-name";
                        }
                        description "Name of the advanced configuration policy to apply with this queue";
                    }

                    leaf profile-capped {
                        type boolean;
                        default "false";
                        description "Enforce an overall in-profile burst limit to the CIR bucket at ingress policer";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                    choice rate-or-percent-rate {
                        default "rate";
                        case rate {

                            container rate {
                                description "Enter the rate context";

                                leaf pir {
                                    type types-qos:policer-pir-rate-maximum;
                                    units "kilobps";
                                    default "max";
                                    description "Administrative PIR";
                                }

                                leaf cir {
                                    type types-qos:policer-cir-rate-maximum;
                                    units "kilobps";
                                    default "0";
                                    description "Administrative CIR";
                                }

                            } // container rate

                        }
                        case percent-rate {

                            container percent-rate {
                                description "Enter the percent-rate context";

                                leaf pir {
                                    type decimal64 {
                                        range "0.01..100.00";
                                        fraction-digits 2;
                                    }
                                    description "Administrative PIR percent";
                                }

                                leaf cir {
                                    type decimal64 {
                                        range "0.00..100.00";
                                        fraction-digits 2;
                                    }
                                    default "0.00";
                                    description "Administrative CIR percent";
                                }

                                leaf reference-rate {
                                    type enumeration {
                                        enum "local-limit"                  { value 2; }
                                        enum "reference-port-limit"         { value 3; }
                                    }
                                    default "local-limit";
                                    description "Reference rate";
                                }

                            } // container percent-rate

                        }
                    }
                    container adaptation-rule {
                        description "Enter the adaptation-rule context";

                        leaf pir {
                            type types-qos:adaptation-rule;
                            default "closest";
                            description "Constraint used when deriving the operational PIR value";
                        }

                        leaf cir {
                            type types-qos:adaptation-rule;
                            default "closest";
                            description "Constraint used when deriving the operational CIR value";
                        }

                    } // container adaptation-rule

                    container arbiter-parent {
                        description "Enter the arbiter-parent context";

                        leaf arbiter-name {
                            type types-sros:named-item;
                            description "Arbiter name";
                        }

                        leaf level {
                            type types-qos:hierarchy-level;
                            default "1";
                            description "Level of priority while feeding to the parent";
                        }

                        leaf weight {
                            type types-qos:weight {
                                range "1..100";
                            }
                            default "1";
                            description "Weight to be used by the arbiter for feeding this policer";
                        }

                    } // container arbiter-parent

                    container scheduler-parent {
                        description "Enter the scheduler-parent context";

                        leaf scheduler-name {
                            type types-sros:named-item;
                            description "Scheduler name";
                        }

                        leaf level {
                            type types-qos:hierarchy-level;
                            default "1";
                            description "Priority level for bandwidth on the parent scheduler";
                        }

                        leaf weight {
                            type types-qos:weight;
                            default "1";
                            description "Policer weight at the above-CIR priority level";
                        }

                        leaf cir-level {
                            type types-qos:cir-level;
                            default "0";
                            description "Port priority level for within-CIR offered load";
                        }

                        leaf cir-weight {
                            type types-qos:cir-weight;
                            default "1";
                            description "Weight to use in the within-CIR port priority level";
                        }

                    } // container scheduler-parent

                } // list policer

                list fc {
                    key "fc-name";
                    description "Enter the fc list instance";

                    leaf fc-name {
                        type types-qos:sap-ingress-fc-name;
                        description "Forwarding class (and optional subclass) name";
                    }

                    leaf profile {
                        type types-qos:profile;
                        description "Profile of the packets associated with this forwarding class";
                    }

                    leaf de-1-out-profile {
                        type boolean;
                        default "false";
                        description "Frames with DE value to be assigned as out of profile";
                    }

                    leaf egress-fc {
                        type types-sros:fc-name;
                        description "Forwarding class to override the forwarding class determined by ingress classification";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                    choice queue-policer-mapping {
                        case queue {

                            leaf queue {
                                type leafref {
                                    path "../../queue/queue-id";
                                }
                                description "Queue to assign for packets in this forwarding class";
                            }

                        }
                        case queue-group-queue {

                            container queue-group-queue {
                                presence "Enable the queue-group-queue context";
                                description "Enable the queue-group-queue context";

                                leaf queue-group-name {
                                    type leafref {
                                        path "../../../../queue-group-templates/ingress/queue-group/ingress-queue-group-name";
                                    }
                                    mandatory true;
                                    description "Queue group to forward traffic";
                                }

                                leaf queue {
                                    type leafref {
                                        path "../../../../queue-group-templates/ingress/queue-group[ingress-queue-group-name=current()/../queue-group-name]/queue/queue-id";
                                    }
                                    mandatory true;
                                    description "Queue to assign for packets in this forwarding class";
                                }

                            } // container queue-group-queue

                        }
                        case policer {

                            leaf policer {
                                type types-qos:ingress-policer-id;
                                description "Policer identifier for the unicast normal traffic in this forwarding class";
                            }

                            leaf fp-redirect-group-policer {
                                type empty;
                                description "Specified policer to be used as defined in the FP (forwarding-plane)";
                            }

                        }
                    }
                    choice multicast-queue-policer-mapping {
                        case multicast-queue {

                            leaf multicast-queue {
                                type leafref {
                                    path "../../queue/queue-id";
                                }
                                description "Broadcast queue to assign for packets in this forwarding class";
                            }

                        }
                        case multicast-queue-group-queue {

                            container multicast-queue-group-queue {
                                presence "Enable the multicast-queue-group-queue context";
                                description "Enable the unknown-queue-group-queue context";

                                leaf queue-group-name {
                                    type leafref {
                                        path "../../../../queue-group-templates/ingress/queue-group/ingress-queue-group-name";
                                    }
                                    mandatory true;
                                    description "Queue group name to forward traffic";
                                }

                                leaf queue {
                                    type leafref {
                                        path "../../../../queue-group-templates/ingress/queue-group[ingress-queue-group-name=current()/../queue-group-name]/queue/queue-id";
                                    }
                                    mandatory true;
                                    description "Broadcast queue to assign for packets in this forwarding class";
                                }

                            } // container multicast-queue-group-queue

                        }
                        case multicast-policer {

                            leaf multicast-policer {
                                type types-qos:ingress-policer-id;
                                description "Policer identifier for the unknown broadcast traffic in this forwarding class";
                            }

                            leaf fp-redirect-group-multicast-policer {
                                type empty;
                                description "Broadcast policer to be used as defined in the FP (forwarding-plane)";
                            }

                        }
                    }
                    choice broadcast-queue-policer-mapping {
                        case broadcast-queue {

                            leaf broadcast-queue {
                                type leafref {
                                    path "../../queue/queue-id";
                                }
                                description "Broadcast queue to assign for packets in this forwarding class";
                            }

                        }
                        case broadcast-queue-group-queue {

                            container broadcast-queue-group-queue {
                                presence "Enable the broadcast-queue-group-queue context";
                                description "Enable the unknown-queue-group-queue context";

                                leaf queue-group-name {
                                    type leafref {
                                        path "../../../../queue-group-templates/ingress/queue-group/ingress-queue-group-name";
                                    }
                                    mandatory true;
                                    description "Queue group name to forward traffic";
                                }

                                leaf queue {
                                    type leafref {
                                        path "../../../../queue-group-templates/ingress/queue-group[ingress-queue-group-name=current()/../queue-group-name]/queue/queue-id";
                                    }
                                    mandatory true;
                                    description "Broadcast queue to assign for packets in this forwarding class";
                                }

                            } // container broadcast-queue-group-queue

                        }
                        case broadcast-policer {

                            leaf broadcast-policer {
                                type types-qos:ingress-policer-id;
                                description "Policer identifier for the unknown broadcast traffic in this forwarding class";
                            }

                            leaf fp-redirect-group-broadcast-policer {
                                type empty;
                                description "Broadcast policer to be used as defined in the FP (forwarding-plane)";
                            }

                        }
                    }
                    choice unknown-queue-policer-mapping {
                        case unknown-queue {

                            leaf unknown-queue {
                                type leafref {
                                    path "../../queue/queue-id";
                                }
                                description "Broadcast queue to assign for packets in this forwarding class";
                            }

                        }
                        case unknown-queue-group-queue {

                            container unknown-queue-group-queue {
                                presence "Enable the unknown-queue-group-queue context";
                                description "Enable the unknown-queue-group-queue context";

                                leaf queue-group-name {
                                    type leafref {
                                        path "../../../../queue-group-templates/ingress/queue-group/ingress-queue-group-name";
                                    }
                                    mandatory true;
                                    description "Queue group name to forward traffic";
                                }

                                leaf queue {
                                    type leafref {
                                        path "../../../../queue-group-templates/ingress/queue-group[ingress-queue-group-name=current()/../queue-group-name]/queue/queue-id";
                                    }
                                    mandatory true;
                                    description "Broadcast queue to assign for packets in this forwarding class";
                                }

                            } // container unknown-queue-group-queue

                        }
                        case unknown-policer {

                            leaf unknown-policer {
                                type types-qos:ingress-policer-id;
                                description "Policer identifier for the unknown broadcast traffic in this forwarding class";
                            }

                            leaf fp-redirect-group-unknown-policer {
                                type empty;
                                description "Broadcast policer to be used as defined in the FP (forwarding-plane)";
                            }

                        }
                    }
                    container in-remark {
                        description "Enter the in-remark context";

                        choice in-profile {
                            case dscp {

                                leaf dscp {
                                    type types-qos:dscp-name;
                                    description "DSCP to override DSCP bits of the matching packet";
                                }

                            }
                            case prec {

                                leaf prec {
                                    type types-qos:precedence-value;
                                    description "Value to override precedence bits of matching packet";
                                }

                            }
                        }
                    } // container in-remark

                    container out-remark {
                        description "Enter the out-remark context";

                        choice out-profile {
                            case dscp {

                                leaf dscp {
                                    type types-qos:dscp-name;
                                    description "DSCP to override DSCP bits of the matching packet";
                                }

                            }
                            case prec {

                                leaf prec {
                                    type types-qos:precedence-value;
                                    description "Value to override precedence bits of matching packet";
                                }

                            }
                        }
                    } // container out-remark

                } // list fc

            } // list sap-ingress

            list slope-policy {
                key "slope-policy-name";
                max-elements 511;
                description "Enter the slope-policy list instance";

                leaf slope-policy-name {
                    type types-sros:named-item;
                    description "Slope policy name";
                }

                leaf description {
                    type types-sros:description;
                    description "Text description";
                }

                leaf time-average-factor {
                    type uint32 {
                        range "0..15";
                    }
                    default "7";
                    description "Apply time average factor to weight between previous and new shared buffer utilization result";
                }

                leaf-list apply-groups {
                    type leafref {
                        path "../../../groups/group/name";
                    }
                    max-elements 8;
                    ordered-by user;
                    description "Apply a configuration group at this level";
                }

                leaf-list apply-groups-exclude {
                    type leafref {
                        path "../../../groups/group/name";
                    }
                    max-elements 8;
                    ordered-by user;
                    description "Exclude a configuration group at this level";
                }

                container highplus-slope {
                    description "Enter the highplus-slope context";

                    leaf admin-state {
                        type types-sros:admin-state;
                        description "Administrative state of the highplus priority RED slope";
                    }

                    leaf start-avg {
                        type uint32 {
                            range "0..100";
                        }
                        description "Buffer percentage after which the drop probability starts to rise above value";
                    }

                    leaf max-avg {
                        type uint32 {
                            range "0..100";
                        }
                        description "Buffer percentage after which the drop probability reaches maximum average";
                    }

                    leaf max-prob {
                        type uint32 {
                            range "0..100";
                        }
                        description "Drop probability increase at highplus start-average";
                    }

                } // container highplus-slope

                container high-slope {
                    description "Enter the high-slope context";

                    leaf admin-state {
                        type types-sros:admin-state;
                        description "Administrative state of the high priority RED slope";
                    }

                    leaf start-avg {
                        type uint32 {
                            range "0..100";
                        }
                        description "Buffer percentage after which the drop probability starts to rise above value";
                    }

                    leaf max-avg {
                        type uint32 {
                            range "0..100";
                        }
                        description "Buffer percentage after which the drop probability reaches maximum average";
                    }

                    leaf max-prob {
                        type uint32 {
                            range "0..100";
                        }
                        description "Drop probability to increase at high start-average";
                    }

                } // container high-slope

                container low-slope {
                    description "Enter the low-slope context";

                    leaf admin-state {
                        type types-sros:admin-state;
                        description "Administrative state of the low priority RED slope";
                    }

                    leaf start-avg {
                        type uint32 {
                            range "0..100";
                        }
                        description "Buffer percentage after which the drop probability starts to rise above value";
                    }

                    leaf max-avg {
                        type uint32 {
                            range "0..100";
                        }
                        description "Buffer percentage after which the drop probability reaches maximum average";
                    }

                    leaf max-prob {
                        type uint32 {
                            range "0..100";
                        }
                        description "Drop probability to increase at low start-average";
                    }

                } // container low-slope

                container exceed-slope {
                    description "Enter the exceed-slope context";

                    leaf admin-state {
                        type types-sros:admin-state;
                        description "Administrative state of the exceed-priority RED slope";
                    }

                    leaf start-avg {
                        type uint32 {
                            range "0..100";
                        }
                        description "Buffer percentage after which the drop probability starts to rise above value";
                    }

                    leaf max-avg {
                        type uint32 {
                            range "0..100";
                        }
                        description "Buffer percentage after which the drop probability reaches maximum average";
                    }

                    leaf max-prob {
                        type uint32 {
                            range "0..100";
                        }
                        description "Drop probability to increase at exceed start-average";
                    }

                } // container exceed-slope

            } // list slope-policy

            list hsmda-slope-policy {
                status obsolete;
                key "hsmda-slope-policy-name";
                max-elements 511;
                description "Enter the hsmda-slope-policy list instance";

                leaf hsmda-slope-policy-name {
                    status obsolete;
                    type types-sros:named-item;
                    description "HSMDA slope policy name";
                }

                leaf description {
                    status obsolete;
                    type types-sros:description;
                    description "Text description";
                }

                leaf-list apply-groups {
                    status obsolete;
                    type leafref {
                        path "../../../groups/group/name";
                    }
                    max-elements 8;
                    ordered-by user;
                    description "Apply a configuration group at this level";
                }

                leaf-list apply-groups-exclude {
                    status obsolete;
                    type leafref {
                        path "../../../groups/group/name";
                    }
                    max-elements 8;
                    ordered-by user;
                    description "Exclude a configuration group at this level";
                }

                container high-slope {
                    status obsolete;
                    description "Enter the high-slope context";

                    leaf admin-state {
                        status obsolete;
                        type types-sros:admin-state;
                        default "enable";
                        description "Administrative state of the high priority RED slope";
                    }

                    leaf start-depth {
                        status obsolete;
                        type decimal64 {
                            range "0.01..100.00";
                            fraction-digits 2;
                        }
                        default "100.00";
                        description "Buffer percentage after which the drop probability starts to rise above value";
                    }

                    leaf max-depth {
                        status obsolete;
                        type decimal64 {
                            range "0.01..100.00";
                            fraction-digits 2;
                        }
                        default "100.00";
                        description "Buffer percentage after which the drop probability reaches maximum average";
                    }

                    leaf max-prob {
                        status obsolete;
                        type decimal64 {
                            range "0.01..100.00";
                            fraction-digits 2;
                        }
                        default "100.00";
                        description "Drop probability when the HSMDA queue depth reaches maximum depth";
                    }

                } // container high-slope

                container low-slope {
                    status obsolete;
                    description "Enter the low-slope context";

                    leaf admin-state {
                        status obsolete;
                        type types-sros:admin-state;
                        default "enable";
                        description "Administrative state of the low priority RED slope";
                    }

                    leaf start-depth {
                        status obsolete;
                        type decimal64 {
                            range "0.01..100.00";
                            fraction-digits 2;
                        }
                        default "90.00";
                        description "Buffer percentage after which the drop probability starts to rise above value";
                    }

                    leaf max-depth {
                        status obsolete;
                        type decimal64 {
                            range "0.01..100.00";
                            fraction-digits 2;
                        }
                        default "90.00";
                        description "Buffer percentage after which the drop probability reaches maximum average";
                    }

                    leaf max-prob {
                        status obsolete;
                        type decimal64 {
                            range "0.01..100.00";
                            fraction-digits 2;
                        }
                        default "100.00";
                        description "Drop probability when the HSMDA queue depth reaches maximum depth";
                    }

                } // container low-slope

            } // list hsmda-slope-policy

            list hsmda-wrr-policy {
                status obsolete;
                key "hsmda-wrr-policy-name";
                max-elements 31;
                description "Enter the hsmda-wrr-policy list instance";

                leaf hsmda-wrr-policy-name {
                    status obsolete;
                    type types-sros:named-item;
                    description "HSMDA WRR policy name";
                }

                leaf description {
                    status obsolete;
                    type types-sros:description;
                    description "Text description";
                }

                leaf include-queues {
                    status obsolete;
                    type enumeration {
                        enum "1-2"                          { value 1; }
                        enum "1-3"                          { value 2; }
                    }
                    default "1-2";
                    description "Queues to include includes into the HSMDA WRR scheduling loop policy";
                }

                leaf schedule-using-class {
                    status obsolete;
                    type int32 {
                        range "1..3";
                    }
                    default "1";
                    description "Class to schedule the queues specified within the HSMDA scheduler";
                }

                leaf class-agg-weight {
                    status obsolete;
                    type int32 {
                        range "1|2|4|8";
                    }
                    default "1";
                    description "Weight assigned to the group of queues specified within the HSMDA scheduler";
                }

                leaf-list apply-groups {
                    status obsolete;
                    type leafref {
                        path "../../../groups/group/name";
                    }
                    max-elements 8;
                    ordered-by user;
                    description "Apply a configuration group at this level";
                }

                leaf-list apply-groups-exclude {
                    status obsolete;
                    type leafref {
                        path "../../../groups/group/name";
                    }
                    max-elements 8;
                    ordered-by user;
                    description "Exclude a configuration group at this level";
                }

            } // list hsmda-wrr-policy

            list hsmda-pool-policy {
                status obsolete;
                key "hsmda-pool-policy-name";
                max-elements 31;
                description "Enter the hsmda-pool-policy list instance";

                leaf hsmda-pool-policy-name {
                    status obsolete;
                    type types-sros:named-item;
                    description "The name of the HSMDA Pool Policy.";
                }

                leaf description {
                    status obsolete;
                    type types-sros:description;
                    description "Text description";
                }

                leaf system-reserve {
                    status obsolete;
                    type decimal64 {
                        range "1.00..30.00";
                        fraction-digits 2;
                    }
                    default "10.00";
                    description "Specifies the percentage of HSMDA buffers reserved for internal system use.";
                }

                leaf-list apply-groups {
                    status obsolete;
                    type leafref {
                        path "../../../groups/group/name";
                    }
                    max-elements 8;
                    ordered-by user;
                    description "Apply a configuration group at this level";
                }

                leaf-list apply-groups-exclude {
                    status obsolete;
                    type leafref {
                        path "../../../groups/group/name";
                    }
                    max-elements 8;
                    ordered-by user;
                    description "Exclude a configuration group at this level";
                }

                container root-tier {
                    status obsolete;
                    description "Enter the root-tier context";

                    list root-pool {
                        status obsolete;
                        key "root-pool-id";
                        description "Enter the root-pool list instance";

                        leaf root-pool-id {
                            status obsolete;
                            type uint32 {
                                range "1..8";
                            }
                            description "Root pool identifier for the HSMDA pool policy";
                        }

                        leaf allocation-weight {
                            status obsolete;
                            type uint32 {
                                range "0..100";
                            }
                            default "0";
                            description "Specifies the weight that will be applied to the first root pool and is divided by the sum of all root pool weights to derive the pool's buffer allocation factor.";
                        }

                        leaf-list apply-groups {
                            status obsolete;
                            type leafref {
                                path "../../../../../groups/group/name";
                            }
                            max-elements 8;
                            ordered-by user;
                            description "Apply a configuration group at this level";
                        }

                        leaf-list apply-groups-exclude {
                            status obsolete;
                            type leafref {
                                path "../../../../../groups/group/name";
                            }
                            max-elements 8;
                            ordered-by user;
                            description "Exclude a configuration group at this level";
                        }

                    } // list root-pool

                } // container root-tier

                container class-tier {
                    status obsolete;
                    description "Enter the class-tier context";

                    list class-pool {
                        status obsolete;
                        key "class-pool-id";
                        description "Enter the class-pool list instance";

                        leaf class-pool-id {
                            status obsolete;
                            type uint32 {
                                range "1..8";
                            }
                            description "Class pool for the HSMDA pool policy";
                        }

                        leaf root-parent {
                            status obsolete;
                            type leafref {
                                path "../../../root-tier/root-pool/root-pool-id";
                            }
                            description "Specifies the parent root to which this class-pool is associated.";
                        }

                        leaf allocation-percent {
                            status obsolete;
                            type decimal64 {
                                range "0.01..100.00";
                                fraction-digits 2;
                            }
                            description "Specifies the percentage of the root-pool with which it is associated, as specified by root-parent will be available to this class-pool.";
                        }

                        leaf-list apply-groups {
                            status obsolete;
                            type leafref {
                                path "../../../../../groups/group/name";
                            }
                            max-elements 8;
                            ordered-by user;
                            description "Apply a configuration group at this level";
                        }

                        leaf-list apply-groups-exclude {
                            status obsolete;
                            type leafref {
                                path "../../../../../groups/group/name";
                            }
                            max-elements 8;
                            ordered-by user;
                            description "Exclude a configuration group at this level";
                        }

                    } // list class-pool

                } // container class-tier

            } // list hsmda-pool-policy

            list hsmda-scheduler-policy {
                status obsolete;
                key "hsmda-scheduler-policy-name";
                max-elements 63;
                description "Enter the hsmda-scheduler-policy list instance";

                leaf hsmda-scheduler-policy-name {
                    status obsolete;
                    type types-sros:named-item;
                    description "The name of the HSMDA scheduler policy.";
                }

                leaf description {
                    status obsolete;
                    type types-sros:description;
                    description "Text description";
                }

                leaf max-rate {
                    status obsolete;
                    type union {
                        type uint32 {
                            range "1..100000";
                        }
                        type enumeration {
                            enum "max"                          { value -1; }
                        }
                    }
                    units "megabps";
                    default "max";
                    description "Specifies the maximum rate for this HSMDA scheduler policy.";
                }

                leaf burst-limit {
                    status obsolete;
                    type union {
                        type types-qos:bytes {
                            range "1..327680";
                        }
                        type enumeration {
                            enum "auto"                         { value -1; }
                        }
                    }
                    default "auto";
                    description "Explicit shaping burst size of a queue";
                }

                leaf-list apply-groups {
                    status obsolete;
                    type leafref {
                        path "../../../groups/group/name";
                    }
                    max-elements 8;
                    ordered-by user;
                    description "Apply a configuration group at this level";
                }

                leaf-list apply-groups-exclude {
                    status obsolete;
                    type leafref {
                        path "../../../groups/group/name";
                    }
                    max-elements 8;
                    ordered-by user;
                    description "Exclude a configuration group at this level";
                }

                list group {
                    status obsolete;
                    key "group-id";
                    description "Enter the group list instance";

                    leaf group-id {
                        status obsolete;
                        type uint32 {
                            range "1..2";
                        }
                        description "Group ID for the HSMDA scheduler policy";
                    }

                    leaf rate {
                        status obsolete;
                        type union {
                            type uint32 {
                                range "1..100000";
                            }
                            type enumeration {
                                enum "max"                          { value -1; }
                            }
                        }
                        units "megabps";
                        default "max";
                        description "Specifies the group maximum rate.";
                    }

                    leaf burst-limit {
                        status obsolete;
                        type union {
                            type types-qos:bytes {
                                range "1..327680";
                            }
                            type enumeration {
                                enum "auto"                         { value -1; }
                            }
                        }
                        default "auto";
                        description "Explicit shaping burst size of a queue";
                    }

                    leaf-list apply-groups {
                        status obsolete;
                        type leafref {
                            path "../../../../groups/group/name";
                        }
                        max-elements 8;
                        ordered-by user;
                        description "Apply a configuration group at this level";
                    }

                    leaf-list apply-groups-exclude {
                        status obsolete;
                        type leafref {
                            path "../../../../groups/group/name";
                        }
                        max-elements 8;
                        ordered-by user;
                        description "Exclude a configuration group at this level";
                    }

                } // list group

                list scheduling-class {
                    status obsolete;
                    key "class-id";
                    description "Enter the scheduling-class list instance";

                    leaf class-id {
                        status obsolete;
                        type uint32 {
                            range "1..8";
                        }
                        description "Class identifier for the HSMDA scheduler policy scheduling class";
                    }

                    leaf-list apply-groups {
                        status obsolete;
                        type leafref {
                            path "../../../../groups/group/name";
                        }
                        max-elements 8;
                        ordered-by user;
                        description "Apply a configuration group at this level";
                    }

                    leaf-list apply-groups-exclude {
                        status obsolete;
                        type leafref {
                            path "../../../../groups/group/name";
                        }
                        max-elements 8;
                        ordered-by user;
                        description "Exclude a configuration group at this level";
                    }

                    choice rate-or-group {
                        status obsolete;
                        default "rate";
                        case rate {
                            status obsolete;

                            leaf rate {
                                status obsolete;
                                type union {
                                    type uint32 {
                                        range "1..100000";
                                    }
                                    type enumeration {
                                        enum "max"                          { value -1; }
                                    }
                                }
                                units "megabps";
                                default "max";
                                description "Specifies the scheduling class maximum rate.";
                            }

                            leaf burst-limit {
                                status obsolete;
                                type union {
                                    type types-qos:bytes {
                                        range "1..327680";
                                    }
                                    type enumeration {
                                        enum "auto"                         { value -1; }
                                    }
                                }
                                default "auto";
                                description "Explicit shaping burst size of a queue";
                            }

                        }
                        case group {
                            status obsolete;

                            container group {
                                status obsolete;
                                presence "Enable the group context";
                                description "Enable the group context";

                                leaf group-id {
                                    status obsolete;
                                    type uint32 {
                                        range "1..2";
                                    }
                                    mandatory true;
                                    description "Specifies the group associated with this scheduling class.";
                                }

                                leaf weight {
                                    status obsolete;
                                    type int32 {
                                        range "1..100";
                                    }
                                    default "1";
                                    description "Specifies the weight in group associated with this scheduling class.";
                                }

                            } // container group

                        }
                    }
                } // list scheduling-class

            } // list hsmda-scheduler-policy

            list atm-td-profile {
                key "atm-td-profile-id";
                description "Enter the atm-td-profile list instance";

                leaf atm-td-profile-id {
                    type types-qos:atm-traffic-descr-idx;
                    description "ATM traffic descriptor ID";
                }

                leaf shaping {
                    type boolean;
                    description "Enable egress shaping";
                }

                leaf service-category {
                    type types-qos:atm-service-category;
                    default "ubr";
                    description "ATM service category";
                }

                leaf description {
                    type types-sros:description;
                    description "Text description";
                }

                leaf descriptor-type {
                    type enumeration {
                        enum "p01"                          { value 0; }
                        enum "p01-and-s01"                  { value 1; }
                        enum "p01-and-s0"                   { value 2; }
                        enum "p01-and-s0-tag"               { value 3; }
                    }
                    description "ATM traffic descriptor type";
                }

                leaf policing {
                    type boolean;
                    default "false";
                    description "Allow ingress traffic policing";
                }

                leaf clp-tagging {
                    type boolean;
                    default "false";
                    description "Control the setting of CLP bit in the ATM cell header";
                }

                leaf weight {
                    type int32 {
                        range "1..255";
                    }
                    description "Relative weight for the ATM traffic descriptor based on ATM VP shaper scheduling";
                }

                leaf-list apply-groups {
                    type leafref {
                        path "../../../groups/group/name";
                    }
                    max-elements 8;
                    ordered-by user;
                    description "Apply a configuration group at this level";
                }

                leaf-list apply-groups-exclude {
                    type leafref {
                        path "../../../groups/group/name";
                    }
                    max-elements 8;
                    ordered-by user;
                    description "Exclude a configuration group at this level";
                }

                container traffic {
                    description "Enter the traffic context";

                    leaf sir {
                        type uint32;
                        units "kilobps";
                        default "0";
                        description "Sustained information rate";
                    }

                    leaf pir {
                        type uint32;
                        units "kilobps";
                        description "Peak information rate";
                    }

                    leaf mir {
                        type uint32;
                        units "kilobps";
                        default "0";
                        description "Minimum information rate";
                    }

                    leaf mbs {
                        type uint32;
                        description "Maximum burst size in cell";
                    }

                    leaf cdvt {
                        type uint32;
                        units "microseconds";
                        default "250";
                        description "Cell Delay Variation Tolerance";
                    }

                } // container traffic

            } // list atm-td-profile

            list network-queue {
                key "network-queue-policy";
                max-elements 255;
                description "Enter the network-queue list instance";

                leaf network-queue-policy {
                    type types-sros:named-item;
                    description "Name for network queue policy";
                }

                leaf description {
                    type types-sros:description;
                    description "Text description";
                }

                leaf hs-attachment-policy {
                    type leafref {
                        path "../../hs-attachment-policy/name";
                    }
                    description "HS attachment policy applied";
                }

                leaf-list apply-groups {
                    type leafref {
                        path "../../../groups/group/name";
                    }
                    max-elements 8;
                    ordered-by user;
                    description "Apply a configuration group at this level";
                }

                leaf-list apply-groups-exclude {
                    type leafref {
                        path "../../../groups/group/name";
                    }
                    max-elements 8;
                    ordered-by user;
                    description "Exclude a configuration group at this level";
                }

                container egress-hsmda {
                    status obsolete;
                    description "Enter the egress-hsmda context";

                    leaf packet-byte-offset {
                        status obsolete;
                        type types-qos:egress-per-packet-offset;
                        default "0";
                        description "Packet byte offset to use for the HSMDA egress queues";
                    }

                    leaf wrr-policy {
                        status obsolete;
                        type leafref {
                            path "../../../hsmda-wrr-policy/hsmda-wrr-policy-name";
                        }
                        description "WRR policy to use on this HSMDA egress queue";
                    }

                    list queue {
                        status obsolete;
                        key "queue-id";
                        description "Enter the queue list instance";

                        leaf queue-id {
                            status obsolete;
                            type types-qos:egress-queue-id;
                            description "Egress HSMDA queue ID";
                        }

                        leaf burst-limit {
                            status obsolete;
                            type union {
                                type types-qos:bytes {
                                    range "1..1000000";
                                }
                                type enumeration {
                                    enum "auto"                         { value -1; }
                                }
                            }
                            default "auto";
                            description "Explicit shaping burst size of a queue";
                        }

                        leaf mbs {
                            status obsolete;
                            type union {
                                type types-qos:bytes {
                                    range "0..2688000";
                                }
                                type enumeration {
                                    enum "auto"                         { value -1; }
                                }
                            }
                            units "bytes";
                            default "auto";
                            description "Percentage of buffer space allowed for the queue";
                        }

                        leaf percent-rate {
                            status obsolete;
                            type decimal64 {
                                range "0.01..100.00";
                                fraction-digits 2;
                            }
                            default "100.00";
                            description "PIR percentage rate";
                        }

                        leaf slope-policy {
                            status obsolete;
                            type leafref {
                                path "../../../../hsmda-slope-policy/hsmda-slope-policy-name";
                            }
                            description "Slop policy name to override the default slope policy for the named buffer pool";
                        }

                        leaf wrr-weight {
                            status obsolete;
                            type types-qos:hsmda-wrr-weight;
                            default "1";
                            description "Weight value for the HSMDA queue";
                        }

                        leaf-list apply-groups {
                            status obsolete;
                            type leafref {
                                path "../../../../../groups/group/name";
                            }
                            max-elements 8;
                            ordered-by user;
                            description "Apply a configuration group at this level";
                        }

                        leaf-list apply-groups-exclude {
                            status obsolete;
                            type leafref {
                                path "../../../../../groups/group/name";
                            }
                            max-elements 8;
                            ordered-by user;
                            description "Exclude a configuration group at this level";
                        }

                        container adaptation-rule {
                            status obsolete;
                            description "Enter the adaptation-rule context";

                            leaf pir {
                                status obsolete;
                                type types-qos:adaptation-rule;
                                default "closest";
                                description "Constraint used when deriving the operational PIR value";
                            }

                        } // container adaptation-rule

                    } // list queue

                } // container egress-hsmda

                list fc {
                    key "fc-name";
                    description "Enter the fc list instance";

                    leaf fc-name {
                        type types-sros:fc-name;
                        description "Forwarding class name";
                    }

                    leaf queue {
                        type leafref {
                            path "../../queue/queue-id";
                        }
                        description "Queue for packets in this forwarding class";
                    }

                    leaf multicast-queue {
                        type leafref {
                            path "../../queue/queue-id";
                        }
                        description "Multicast queue for packets in this forwarding class";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                    container egress-hsmda {
                        status obsolete;
                        description "Enter the egress-hsmda context";

                        leaf queue {
                            status obsolete;
                            type types-qos:egress-queue-id;
                            description "Egress HSDMA queue for packets in this forwarding class";
                        }

                    } // container egress-hsmda

                } // list fc

                list queue {
                    key "queue-id";
                    description "Enter the queue list instance";

                    leaf queue-id {
                        type types-qos:network-queue-queue-id;
                        description "Queue identifier";
                    }

                    leaf multipoint {
                        type boolean;
                        sros-ext:immutable;
                        description "Apply as a multicast queue";
                    }

                    leaf queue-type {
                        type enumeration {
                            enum "expedited"                    { value 1; }
                            enum "auto-expedited"               { value 2; }
                            enum "best-effort"                  { value 3; }
                        }
                        sros-ext:immutable;
                        default "auto-expedited";
                        description "Priority that this queue receives from the hardware level schedulers";
                    }

                    leaf cbs {
                        type decimal64 {
                            range "0.00..100.00";
                            fraction-digits 2;
                        }
                        description "Reserved buffer space for the queue";
                    }

                    leaf mbs {
                        type decimal64 {
                            range "0.00..100.00";
                            fraction-digits 2;
                        }
                        description "Percentage of buffer space allowed for the queue";
                    }

                    leaf avg-frame-overhead {
                        type decimal64 {
                            range "0.00..100.00";
                            fraction-digits 2;
                        }
                        default "0.00";
                        description "Average packet-to-frame encapsulation overhead";
                    }

                    leaf hs-alt-port-class-pool {
                        type boolean;
                        default "false";
                        description "Use HS alternate class port pool buffer for traffic";
                    }

                    leaf hs-wrr-weight {
                        type types-qos:hs-wrr-weight;
                        default "1";
                        description "Weighted Round Robin (WRR) weight to parent with this queue into the scheduler";
                    }

                    leaf hs-class-weight {
                        type types-qos:hs-class-weight;
                        default "1";
                        description "Scheduling class weight";
                    }

                    leaf hs-mbs {
                        type decimal64 {
                            range "0.00..100.00";
                            fraction-digits 2;
                        }
                        default "100.00";
                        description "Percentage of buffer space allowed for the HS queue";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                    container rate {
                        description "Enter the rate context";

                        leaf pir {
                            type int32 {
                                range "1..100";
                            }
                            units "percent";
                            default "100";
                            description "PIR percentage rate";
                        }

                        leaf cir {
                            type int32 {
                                range "0..100";
                            }
                            units "percent";
                            description "CIR percentage rate";
                        }

                        leaf fir {
                            type int32 {
                                range "0..100";
                            }
                            units "percent";
                            default "0";
                            description "FIR percentage";
                        }

                    } // container rate

                    container port-parent {
                        presence "Enable the port-parent context";
                        description "Enable the port-parent context";

                        leaf level {
                            type types-qos:hierarchy-level;
                            default "1";
                            description "Port priority level for above-CIR behavior";
                        }

                        leaf weight {
                            type types-qos:weight;
                            default "1";
                            description "Weight that this queue uses to receive bandwidth from the port level scheduler";
                        }

                        leaf cir-level {
                            type types-qos:cir-level;
                            default "0";
                            description "Port priority that this queue uses to receive bandwidth from the port level scheduler";
                        }

                        leaf cir-weight {
                            type types-qos:cir-weight;
                            default "0";
                            description "Weight that this queue uses to receive bandwidth from the port level scheduler";
                        }

                    } // container port-parent

                    container adaptation-rule {
                        description "Enter the adaptation-rule context";

                        leaf pir {
                            type types-qos:adaptation-rule;
                            default "closest";
                            description "Constraint used when deriving the operational PIR value";
                        }

                        leaf cir {
                            type types-qos:adaptation-rule;
                            default "closest";
                            description "Constraint used when deriving the operational CIR value";
                        }

                        leaf fir {
                            type types-qos:adaptation-rule;
                            default "closest";
                            description "Constraint used when deriving the operational FIR value";
                        }

                    } // container adaptation-rule

                    container drop-tail {
                        description "Enter the drop-tail context";

                        container low {
                            description "Enter the low context";

                            leaf percent-reduction-from-mbs {
                                type types-qos:burst-percent;
                                description "Low drop-tail percent from MBS that is reduced";
                            }

                        } // container low

                    } // container drop-tail

                    container hs-wred-queue {
                        description "Enter the hs-wred-queue context";

                        leaf policy {
                            type leafref {
                                path "../../../../slope-policy/slope-policy-name";
                            }
                            description "Slope policy name";
                        }

                    } // container hs-wred-queue

                } // list queue

                list hs-wrr-group {
                    key "group-id";
                    description "Enter the hs-wrr-group list instance";

                    leaf group-id {
                        type types-qos:hs-wrr-group-id;
                        description "HS WRR group identifier";
                    }

                    leaf hs-class-weight {
                        type types-qos:hs-class-weight;
                        default "1";
                        description "Weight of scheduling class";
                    }

                    leaf rate {
                        type uint32 {
                            range "1..100";
                        }
                        default "100";
                        description "PIR rate";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                    container adaptation-rule {
                        description "Enter the adaptation-rule context";

                        leaf pir {
                            type types-qos:adaptation-rule;
                            default "closest";
                            description "Constraint used when deriving the operational PIR value";
                        }

                    } // container adaptation-rule

                } // list hs-wrr-group

            } // list network-queue

            list shared-queue {
                key "shared-queue-policy-name";
                description "Enter the shared-queue list instance";

                leaf shared-queue-policy-name {
                    type types-sros:named-item;
                    description "Name of the default shared queue policy";
                }

                leaf description {
                    type types-sros:description-or-empty;
                    description "Text description";
                }

                leaf-list apply-groups {
                    type leafref {
                        path "../../../groups/group/name";
                    }
                    max-elements 8;
                    ordered-by user;
                    description "Apply a configuration group at this level";
                }

                leaf-list apply-groups-exclude {
                    type leafref {
                        path "../../../groups/group/name";
                    }
                    max-elements 8;
                    ordered-by user;
                    description "Exclude a configuration group at this level";
                }

                list queue {
                    key "queue-id";
                    description "Enter the queue list instance";

                    leaf queue-id {
                        type int32 {
                            range "1..32";
                        }
                        description "Shared queue identifier";
                    }

                    leaf multipoint {
                        type boolean;
                        description "Apply as a multicast queue";
                    }

                    leaf queue-type {
                        type enumeration {
                            enum "expedited"                    { value 1; }
                            enum "auto-expedited"               { value 2; }
                            enum "best-effort"                  { value 3; }
                        }
                        default "auto-expedited";
                        description "Priority that this queue receives from the hardware level schedulers";
                    }

                    leaf cbs {
                        type int32 {
                            range "0..100";
                        }
                        units "percent";
                        description "Committed burst size as a percentage of the maximum reserved buffer space for the queue";
                    }

                    leaf mbs {
                        type int32 {
                            range "0..100";
                        }
                        units "percent";
                        description "Maximum burst size as a percentage of maximum reserved buffer space for the queue";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                    container rate {
                        description "Enter the rate context";

                        leaf pir {
                            type int32 {
                                range "1..100";
                            }
                            units "percent";
                            default "100";
                            description "PIR percentage rate";
                        }

                        leaf cir {
                            type int32 {
                                range "0..100";
                            }
                            units "percent";
                            description "CIR percentage rate";
                        }

                        leaf fir {
                            type int32 {
                                range "0..100";
                            }
                            units "percent";
                            default "0";
                            description "FIR percentage rate";
                        }

                    } // container rate

                    container drop-tail {
                        description "Enter the drop-tail context";

                        container low {
                            description "Enter the low context";

                            leaf percent-reduction-from-mbs {
                                type types-qos:burst-percent;
                                description "Low drop-tail percent from MBS that is reduced";
                            }

                        } // container low

                    } // container drop-tail

                } // list queue

                list fc {
                    key "fc-name";
                    description "Enter the fc list instance";

                    leaf fc-name {
                        type types-sros:fc-name;
                        description "Forwarding class mapping to queue mapping";
                    }

                    leaf queue {
                        type int32 {
                            range "1..8";
                        }
                        description "Logical queue that the traffic, classified into this forwarding class, should use";
                    }

                    leaf broadcast-queue {
                        type int32 {
                            range "9..32";
                        }
                        description "Logical queue that the broadcast traffic, classified into this forwarding class, should use";
                    }

                    leaf multicast-queue {
                        type int32 {
                            range "9..32";
                        }
                        description "Logical queue that the multicast traffic, classified into this forwarding class, should use";
                    }

                    leaf unknown-queue {
                        type int32 {
                            range "9..32";
                        }
                        description "Logical queue that the unknown traffic, classified into this forwarding class, should use";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                } // list fc

            } // list shared-queue

            list adv-config-policy {
                key "adv-config-policy-name";
                max-elements 255;
                description "Enter the adv-config-policy list instance";

                leaf adv-config-policy-name {
                    type types-sros:named-item;
                    description "Advanced QoS policy name";
                }

                leaf description {
                    type types-sros:description;
                    description "Text description";
                }

                leaf-list apply-groups {
                    type leafref {
                        path "../../../groups/group/name";
                    }
                    max-elements 8;
                    ordered-by user;
                    description "Apply a configuration group at this level";
                }

                leaf-list apply-groups-exclude {
                    type leafref {
                        path "../../../groups/group/name";
                    }
                    max-elements 8;
                    ordered-by user;
                    description "Exclude a configuration group at this level";
                }

                container child-control {
                    description "Enter the child-control context";

                    container bandwidth-distribution {
                        description "Enter the bandwidth-distribution context";

                        leaf enqueue-on-pir-zero {
                            type boolean;
                            default "false";
                            description "Enqueue the packets when bandwidth-distribution granularity rate is set to zero";
                        }

                        leaf internal-scheduler-weight-mode {
                            type types-qos:internal-scheduler-weight-mode;
                            description "Weight mode applied to this advanced QoS policy";
                        }

                        leaf limit-pir-zero-drain {
                            type boolean;
                            default "false";
                            description "Throttle the queue draining based on bandwidth-distribution granularity rate";
                        }

                        leaf lub-init-min-pir {
                            type boolean;
                            default "false";
                            description "Apply minimum rate operational PIR to queue for use by enqueued packets prior to an HQoS iteration";
                        }

                        container above-offered-cap {
                            description "Enter the above-offered-cap context";

                            choice rate-or-percent-rate {
                                case rate {

                                    leaf rate {
                                        type union {
                                            type int64 {
                                                range "0..100000000";
                                            }
                                            type enumeration {
                                                enum "max"                          { value -1; }
                                            }
                                        }
                                        description "Explicit number to assign as limit to the child's fair share increase";
                                    }

                                }
                                case percent {

                                    leaf percent {
                                        type decimal64 {
                                            range "0.00..100.00";
                                            fraction-digits 2;
                                        }
                                        description "Percentage of the child's administrative PIR used as the fair share increase limit";
                                    }

                                }
                            }
                        } // container above-offered-cap

                        container above-offered-allowance {
                            description "Enter the above-offered-allowance context";

                            container unconsumed-agg-rate {
                                description "Enter the unconsumed-agg-rate context";

                                leaf percent {
                                    type decimal64 {
                                        range "0.00..100.00";
                                        fraction-digits 2;
                                    }
                                    default "100.00";
                                    description "Percentage of the unconsumed aggregate rate";
                                }

                            } // container unconsumed-agg-rate

                            container delta-consumed-agg-rate {
                                description "Enter the delta-consumed-agg-rate context";

                                leaf percent {
                                    type decimal64 {
                                        range "0.00..100.00";
                                        fraction-digits 2;
                                    }
                                    default "20.00";
                                    description "Percentage of the delta consumed aggregate rate";
                                }

                            } // container delta-consumed-agg-rate

                            container unconsumed-higher-tier-rate {
                                description "Enter the unconsumed-higher-tier-rate context";

                                leaf percent {
                                    type decimal64 {
                                        range "0.00..100.00";
                                        fraction-digits 2;
                                    }
                                    default "100.00";
                                    description "Percentage of the unconsumed higher-tier rate";
                                }

                            } // container unconsumed-higher-tier-rate

                            container delta-consumed-higher-tier-rate {
                                description "Enter the delta-consumed-higher-tier-rate context";

                                leaf percent {
                                    type decimal64 {
                                        range "0.00..100.00";
                                        fraction-digits 2;
                                    }
                                    default "5.00";
                                    description "Percentage of the delta consumed higher-tier rate";
                                }

                            } // container delta-consumed-higher-tier-rate

                        } // container above-offered-allowance

                        container granularity {
                            description "Enter the granularity context";

                            choice rate-or-percent-rate {
                                case rate {

                                    leaf rate {
                                        type int64 {
                                            range "0..100000000";
                                        }
                                        description "Rounding rate step value";
                                    }

                                }
                                case percent {

                                    leaf percent {
                                        type decimal64 {
                                            range "0.00..100.00";
                                            fraction-digits 2;
                                        }
                                        description "Rounding percentage value for administrative PIR";
                                    }

                                }
                            }
                        } // container granularity

                    } // container bandwidth-distribution

                    container offered-measurement {
                        description "Enter the offered-measurement context";

                        leaf fast-start {
                            type boolean;
                            default "false";
                            description "Allow fast detection of initial bandwidth on a child policer or queue associated with policy";
                        }

                        leaf fast-stop {
                            type boolean;
                            default "false";
                            description "Allow fast detection of lack of offered rate on a child policer or queue associated with the policy";
                        }

                        leaf sample-interval {
                            type uint32 {
                                range "1..8";
                            }
                            default "1";
                            description "Interval for sampling the child's offered rate";
                        }

                        container add {
                            description "Enter the add context";

                            leaf min-only {
                                type boolean;
                                default "false";
                                description "Use specified increase value as a minimum offered rate even for inactive queues or policers";
                            }

                            leaf active-min-only {
                                type boolean;
                                default "false";
                                description "Use increase in rate or percentage as minimum offered rate only for active queues or policers";
                            }

                            choice rate-or-percent-rate {
                                case rate {

                                    leaf rate {
                                        type int64 {
                                            range "0..100000000";
                                        }
                                        description "Rate value to add to child's offered rate";
                                    }

                                }
                                case percent {

                                    leaf percent {
                                        type decimal64 {
                                            range "0.00..100.00";
                                            fraction-digits 2;
                                        }
                                        description "Percentage of child's administrative PIR to add to child's offered rate";
                                    }

                                }
                            }
                        } // container add

                        container granularity {
                            description "Enter the granularity context";

                            choice rate-or-percent-rate {
                                case rate {

                                    leaf rate {
                                        type int64 {
                                            range "0..100000000";
                                        }
                                        description "Value to use as child's offered rate change sensitivity value";
                                    }

                                }
                                case percent {

                                    leaf percent {
                                        type decimal64 {
                                            range "0.00..100.00";
                                            fraction-digits 2;
                                        }
                                        description "Percentage of child's administrative PIR used as threshold sensitivity to offered rate change";
                                    }

                                }
                            }
                        } // container granularity

                        container hold-time {
                            description "Enter the hold-time context";

                            leaf high-rate {
                                type uint32 {
                                    range "0..60";
                                }
                                default "0";
                                description "Time during which current offered rate is maintained for a child policer or queue";
                            }

                            leaf active-min-only {
                                type boolean;
                                default "false";
                                description "Use specified increase value as minimum offered rate only for active queues or policers";
                            }

                        } // container hold-time

                        container max-decrement {
                            description "Enter the max-decrement context";

                            choice rate-or-percent-rate {
                                case rate {

                                    leaf rate {
                                        type int64 {
                                            range "0..100000000";
                                        }
                                        description "Value to use as the decrement limit to offered rate change";
                                    }

                                }
                                case percent {

                                    leaf percent {
                                        type decimal64 {
                                            range "0.00..100.00";
                                            fraction-digits 2;
                                        }
                                        description "Value of the child's administrative PIR to use as the decrement limit to offered rate change";
                                    }

                                }
                            }
                        } // container max-decrement

                        container time-average-factor {
                            description "Enter the time-average-factor context";

                            leaf weighting-factor {
                                type uint32 {
                                    range "0..64";
                                }
                                default "0";
                                description "New offered rate with a sample of the previous offered rate";
                            }

                            leaf dec-only {
                                type boolean;
                                default "false";
                                description "Apply time average factor adjustment when the offered rate decreases compared to previous";
                            }

                        } // container time-average-factor

                    } // container offered-measurement

                } // container child-control

            } // list adv-config-policy

            list mlppp-profile-ingress {
                key "mc-mlppp-ingress-prof-index";
                max-elements 128;
                description "Enter the mlppp-profile-ingress list instance";

                leaf mc-mlppp-ingress-prof-index {
                    type uint32 {
                        range "1..65535";
                    }
                    description "Index of the ingress MultiClass MLPPP profile";
                }

                leaf description {
                    type types-sros:description-or-empty;
                    description "Text description";
                }

                leaf-list apply-groups {
                    type leafref {
                        path "../../../groups/group/name";
                    }
                    max-elements 8;
                    ordered-by user;
                    description "Apply a configuration group at this level";
                }

                leaf-list apply-groups-exclude {
                    type leafref {
                        path "../../../groups/group/name";
                    }
                    max-elements 8;
                    ordered-by user;
                    description "Exclude a configuration group at this level";
                }

                list class {
                    key "class-id";
                    description "Enter the class list instance";

                    leaf class-id {
                        type int32 {
                            range "0..3";
                        }
                        description "Policy class";
                    }

                    leaf reassembly-timeout {
                        type uint32 {
                            range "1..1000";
                        }
                        description "Reassembly timeout for this policy";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                } // list class

            } // list mlppp-profile-ingress

            list mlppp-profile-egress {
                key "mc-mlppp-egress-prof-index";
                max-elements 128;
                description "Enter the mlppp-profile-egress list instance";

                leaf mc-mlppp-egress-prof-index {
                    type uint32 {
                        range "1..65535";
                    }
                    description "Index of the egress MultiClass MLPPP profile";
                }

                leaf description {
                    type types-sros:description-or-empty;
                    description "Text description";
                }

                leaf-list apply-groups {
                    type leafref {
                        path "../../../groups/group/name";
                    }
                    max-elements 8;
                    ordered-by user;
                    description "Apply a configuration group at this level";
                }

                leaf-list apply-groups-exclude {
                    type leafref {
                        path "../../../groups/group/name";
                    }
                    max-elements 8;
                    ordered-by user;
                    description "Exclude a configuration group at this level";
                }

                list class {
                    key "class-id";
                    description "Enter the class list instance";

                    leaf class-id {
                        type int32 {
                            range "0..3";
                        }
                        description "Policy class";
                    }

                    leaf mir {
                        type uint32 {
                            range "1..100";
                        }
                        description "Minimum information rate (MIR) as percentage";
                    }

                    leaf max-queue-size {
                        type uint32 {
                            range "1..1000";
                        }
                        description "Buffer queue size";
                    }

                    leaf weight {
                        type uint32 {
                            range "1..100";
                        }
                        description "Weight of this multiclass class as a percentage";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                } // list class

                list fc {
                    key "fc-name";
                    description "Enter the fc list instance";

                    leaf fc-name {
                        type types-sros:fc-name;
                        description "Forwarding class name";
                    }

                    leaf mlppp-class {
                        type uint32 {
                            range "0..3";
                        }
                        description "Mapping of the system forwarding class to the MLPPP classes";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                } // list fc

            } // list mlppp-profile-egress

            list mc-fr-profile-ingress {
                key "mc-fr-ingress-prof-index";
                max-elements 128;
                description "Enter the mc-fr-profile-ingress list instance";

                leaf mc-fr-ingress-prof-index {
                    type uint32 {
                        range "1..65535";
                    }
                    description "Index of the ingress MultiClass Frame Relay profile";
                }

                leaf description {
                    type types-sros:description;
                    description "Text description";
                }

                leaf-list apply-groups {
                    type leafref {
                        path "../../../groups/group/name";
                    }
                    max-elements 8;
                    ordered-by user;
                    description "Apply a configuration group at this level";
                }

                leaf-list apply-groups-exclude {
                    type leafref {
                        path "../../../groups/group/name";
                    }
                    max-elements 8;
                    ordered-by user;
                    description "Exclude a configuration group at this level";
                }

                list class {
                    key "class-id";
                    description "Enter the class list instance";

                    leaf class-id {
                        type int32 {
                            range "0..3";
                        }
                        description "Frame-relay ingress class per multi-class frame-relay ingress profile";
                    }

                    leaf reassembly-timeout {
                        type uint32 {
                            range "1..1000";
                        }
                        description "Reassembly timeout for a specific frame-relay multi-class ingress class";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                } // list class

            } // list mc-fr-profile-ingress

            list mc-fr-profile-egress {
                key "mc-fr-egress-prof-index";
                max-elements 128;
                description "Enter the mc-fr-profile-egress list instance";

                leaf mc-fr-egress-prof-index {
                    type uint32 {
                        range "1..65535";
                    }
                    description "Egress MultiClass Frame Relay Profile Index";
                }

                leaf description {
                    type types-sros:description;
                    description "Text description";
                }

                leaf-list apply-groups {
                    type leafref {
                        path "../../../groups/group/name";
                    }
                    max-elements 8;
                    ordered-by user;
                    description "Apply a configuration group at this level";
                }

                leaf-list apply-groups-exclude {
                    type leafref {
                        path "../../../groups/group/name";
                    }
                    max-elements 8;
                    ordered-by user;
                    description "Exclude a configuration group at this level";
                }

                list class {
                    key "class-id";
                    description "Enter the class list instance";

                    leaf class-id {
                        type int32 {
                            range "0..3";
                        }
                        description "Frame-relay egress class per multi-class frame-relay egress profile";
                    }

                    leaf mir {
                        type uint32 {
                            range "1..100";
                        }
                        description "Minimum information rate (MIR) as percentage";
                    }

                    leaf max-queue-size {
                        type uint32 {
                            range "1..1000";
                        }
                        description "Buffer queue size";
                    }

                    leaf weight {
                        type uint32 {
                            range "1..100";
                        }
                        description "Weight of this multiclass class as a percentage";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                } // list class

            } // list mc-fr-profile-egress

            list policer-control-policy {
                key "policer-control-policy-name";
                max-elements 2047;
                description "Enter the policer-control-policy list instance";

                leaf policer-control-policy-name {
                    type types-sros:named-item;
                    description "Policer control policy name";
                }

                leaf description {
                    type types-sros:description;
                    description "Text description";
                }

                leaf-list apply-groups {
                    type leafref {
                        path "../../../groups/group/name";
                    }
                    max-elements 8;
                    ordered-by user;
                    description "Apply a configuration group at this level";
                }

                leaf-list apply-groups-exclude {
                    type leafref {
                        path "../../../groups/group/name";
                    }
                    max-elements 8;
                    ordered-by user;
                    description "Exclude a configuration group at this level";
                }

                container root {
                    description "Enter the root context";

                    leaf profile-preferred {
                        type boolean;
                        default "false";
                        description "Provide a preference to consume PIR bucket tokens at a given priority level";
                    }

                    choice max-rate-or-max-percent-rate {
                        default "max-rate";
                        case max-rate {

                            leaf max-rate {
                                type types-qos:max-rate;
                                default "max";
                                description "Maximum frame-based bandwidth limit of the arbiter";
                            }

                        }
                        case max-percent-rate {

                            leaf max-percent-rate {
                                type decimal64 {
                                    range "0.01..100.00";
                                    fraction-digits 2;
                                }
                                description "Maximum rate of the arbiter";
                            }

                        }
                    }
                    container priority-mbs-thresholds {
                        description "Enter the priority-mbs-thresholds context";

                        leaf min-thresh-separation {
                            type union {
                                type types-qos:bytes {
                                    range "0..16777216";
                                }
                                type enumeration {
                                    enum "auto"                         { value -1; }
                                }
                            }
                            units "bytes";
                            default "auto";
                            description "Minimum separation between policer discard thresholds";
                        }

                        list priority {
                            key "priority-level";
                            description "Enter the priority list instance";

                            leaf priority-level {
                                type types-qos:hierarchy-level;
                                description "Priority level";
                            }

                            leaf mbs-contribution {
                                type union {
                                    type types-qos:bytes {
                                        range "0..16777216";
                                    }
                                    type enumeration {
                                        enum "auto"                         { value -1; }
                                    }
                                }
                                units "bytes";
                                default "auto";
                                description "Minimum amount of cumulative buffer space";
                            }

                            leaf fixed-mbs {
                                type boolean;
                                default "false";
                                description "Consider cumulative buffer space to be fixed";
                            }

                            leaf-list apply-groups {
                                type leafref {
                                    path "../../../../../../groups/group/name";
                                }
                                max-elements 8;
                                ordered-by user;
                                description "Apply a configuration group at this level";
                            }

                            leaf-list apply-groups-exclude {
                                type leafref {
                                    path "../../../../../../groups/group/name";
                                }
                                max-elements 8;
                                ordered-by user;
                                description "Exclude a configuration group at this level";
                            }

                        } // list priority

                    } // container priority-mbs-thresholds

                } // container root

                list tier {
                    key "tier-id";
                    description "Enter the tier list instance";

                    leaf tier-id {
                        type int32 {
                            range "1..2";
                        }
                        description "Tier for policer control policer arbiter";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                    list arbiter {
                        key "arbiter-name";
                        description "Enter the arbiter list instance";

                        leaf arbiter-name {
                            type types-sros:named-item;
                            description "Arbiter name";
                        }

                        leaf description {
                            type types-sros:description;
                            description "Text description";
                        }

                        leaf-list apply-groups {
                            type leafref {
                                path "../../../../../groups/group/name";
                            }
                            max-elements 8;
                            ordered-by user;
                            description "Apply a configuration group at this level";
                        }

                        leaf-list apply-groups-exclude {
                            type leafref {
                                path "../../../../../groups/group/name";
                            }
                            max-elements 8;
                            ordered-by user;
                            description "Exclude a configuration group at this level";
                        }

                        choice rate-or-percent-rate {
                            default "rate";
                            case rate {

                                leaf rate {
                                    type types-qos:max-rate;
                                    default "max";
                                    description "Maximum frame-based bandwidth limit";
                                }

                            }
                            case percent-rate {

                                leaf percent-rate {
                                    type decimal64 {
                                        range "0.01..100.00";
                                        fraction-digits 2;
                                    }
                                    description "Maximum rate of the arbiter";
                                }

                                leaf reference-rate {
                                    type enumeration {
                                        enum "local-limit"                  { value 2; }
                                        enum "reference-port-limit"         { value 3; }
                                    }
                                    default "local-limit";
                                    description "Reference rate";
                                }

                            }
                        }
                        container arbiter-parent {
                            description "Enter the arbiter-parent context";

                            leaf arbiter-name {
                                type types-sros:named-item;
                                description "Arbiter name";
                            }

                            leaf level {
                                type types-qos:hierarchy-level;
                                default "1";
                                description "Level the child arbiter uses on its parent";
                            }

                            leaf weight {
                                type types-qos:weight {
                                    range "1..100";
                                }
                                default "1";
                                description "Weight attribute at parent level applied to children";
                            }

                        } // container arbiter-parent

                    } // list arbiter

                } // list tier

            } // list policer-control-policy

            container queue-group-templates {
                description "Enter the queue-group-templates context";

                leaf-list apply-groups {
                    type leafref {
                        path "../../../groups/group/name";
                    }
                    max-elements 8;
                    ordered-by user;
                    description "Apply a configuration group at this level";
                }

                leaf-list apply-groups-exclude {
                    type leafref {
                        path "../../../groups/group/name";
                    }
                    max-elements 8;
                    ordered-by user;
                    description "Exclude a configuration group at this level";
                }

                container ingress {
                    description "Enter the ingress context";

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                    list queue-group {
                        key "ingress-queue-group-name";
                        description "Enter the queue-group list instance";

                        leaf ingress-queue-group-name {
                            type types-sros:named-item;
                            description "Ingress queue group template name";
                        }

                        leaf description {
                            type types-sros:description;
                            description "Text description";
                        }

                        leaf-list apply-groups {
                            type leafref {
                                path "../../../../../groups/group/name";
                            }
                            max-elements 8;
                            ordered-by user;
                            description "Apply a configuration group at this level";
                        }

                        leaf-list apply-groups-exclude {
                            type leafref {
                                path "../../../../../groups/group/name";
                            }
                            max-elements 8;
                            ordered-by user;
                            description "Exclude a configuration group at this level";
                        }

                        list queue {
                            key "queue-id";
                            description "Enter the queue list instance";

                            leaf queue-id {
                                type types-qos:ingress-queue-id;
                                description "Ingress Queue-Group Queue identifier";
                            }

                            leaf multipoint {
                                type boolean;
                                sros-ext:immutable;
                                default "false";
                                description "Create an ingress multipoint queue";
                            }

                            leaf queue-type {
                                type types-qos:queue-group-queue-type;
                                sros-ext:immutable;
                                default "best-effort";
                                description "Priority that this queue receives from the hardware level schedulers";
                            }

                            leaf queue-mode {
                                type types-qos:queue-mode;
                                sros-ext:immutable;
                                default "priority";
                                description "Queue operational mode for explicitly profiled packets";
                            }

                            leaf cbs {
                                type union {
                                    type types-qos:bytes {
                                        range "0..1048576";
                                    }
                                    type enumeration {
                                        enum "auto"                         { value -1; }
                                    }
                                }
                                units "kilobytes";
                                default "auto";
                                description "Reserved buffer space for the queue";
                            }

                            leaf mbs {
                                type union {
                                    type types-qos:bytes {
                                        range "0..1073741824";
                                    }
                                    type enumeration {
                                        enum "auto"                         { value -1; }
                                    }
                                }
                                units "bytes";
                                default "auto";
                                description "Maximum buffer space that is allowed for queue";
                            }

                            leaf burst-limit {
                                type union {
                                    type types-qos:bytes {
                                        range "1..14000000";
                                    }
                                    type enumeration {
                                        enum "auto"                         { value -1; }
                                    }
                                }
                                default "auto";
                                description "Explicit shaping burst size of a queue";
                            }

                            leaf adv-config-policy {
                                type leafref {
                                    path "../../../../../adv-config-policy/adv-config-policy-name";
                                }
                                description "Name of the advanced configuration policy to apply with this queue";
                            }

                            leaf packet-byte-offset {
                                type types-qos:per-packet-offset;
                                default "0";
                                description "Value of the adjustment on the size of each packet for queue accounting";
                            }

                            leaf cir-non-profiling {
                                type boolean;
                                default "false";
                                description "Prevent profile modification of CIR dependent packets";
                            }

                            leaf-list apply-groups {
                                type leafref {
                                    path "../../../../../../groups/group/name";
                                }
                                max-elements 8;
                                ordered-by user;
                                description "Apply a configuration group at this level";
                            }

                            leaf-list apply-groups-exclude {
                                type leafref {
                                    path "../../../../../../groups/group/name";
                                }
                                max-elements 8;
                                ordered-by user;
                                description "Exclude a configuration group at this level";
                            }

                            choice rate-or-percent-rate {
                                default "rate";
                                case rate {

                                    container rate {
                                        description "Enter the rate context";

                                        leaf pir {
                                            type types-qos:queue-pir-rate;
                                            units "kilobps";
                                            default "max";
                                            description "Administrative PIR";
                                        }

                                        choice cir-and-fir-or-policed {
                                            default "cir-and-fir";
                                            case cir-and-fir {

                                                leaf cir {
                                                    type types-qos:queue-cir-rate;
                                                    units "kilobps";
                                                    default "0";
                                                    description "Administrative CIR";
                                                }

                                                leaf fir {
                                                    type types-qos:queue-cir-rate;
                                                    units "kilobps";
                                                    default "0";
                                                    description "Administrative FIR";
                                                }

                                            }
                                            case police {

                                                leaf police {
                                                    type empty;
                                                    description "Drop out-of-profile traffic feeding into queue instance";
                                                }

                                            }
                                        }
                                    } // container rate

                                }
                                case percent-rate {

                                    container percent-rate {
                                        description "Enter the percent-rate context";

                                        leaf pir {
                                            type decimal64 {
                                                range "0.01..100.00";
                                                fraction-digits 2;
                                            }
                                            description "Administrative PIR";
                                        }

                                        leaf reference-rate {
                                            type enumeration {
                                                enum "port-limit"                   { value 2; }
                                                enum "local-limit"                  { value 3; }
                                                enum "reference-port-limit"         { value 4; }
                                            }
                                            default "port-limit";
                                            description "Reference rate";
                                        }

                                        choice percent-rate-cir-fir-or-police {
                                            default "cir-fir";
                                            case cir-fir {

                                                leaf cir {
                                                    type decimal64 {
                                                        range "0.00..100.00";
                                                        fraction-digits 2;
                                                    }
                                                    default "0.00";
                                                    description "Administrative CIR";
                                                }

                                                leaf fir {
                                                    type decimal64 {
                                                        range "0.00..100.00";
                                                        fraction-digits 2;
                                                    }
                                                    default "0.00";
                                                    description "Administrative FIR";
                                                }

                                            }
                                            case police {

                                                leaf police {
                                                    type empty;
                                                    description "Drop out-of-profile traffic feeding into physical queue";
                                                }

                                            }
                                        }
                                    } // container percent-rate

                                }
                            }
                            container scheduler-parent {
                                description "Enter the scheduler-parent context";

                                leaf scheduler-name {
                                    type types-sros:named-item;
                                    description "Scheduler name";
                                }

                                leaf level {
                                    type types-qos:hierarchy-level;
                                    default "1";
                                    description "Level of priority while feeding to the parent";
                                }

                                leaf weight {
                                    type types-qos:weight;
                                    default "1";
                                    description "Weight to be used by the scheduler for feeding this queue";
                                }

                                leaf cir-level {
                                    type types-qos:cir-level;
                                    default "0";
                                    description "Level of priority while feeding to the parent";
                                }

                                leaf cir-weight {
                                    type types-qos:cir-weight;
                                    default "1";
                                    description "Weight that is used by the scheduler until the committed rate for feeding this queue";
                                }

                            } // container scheduler-parent

                            container adaptation-rule {
                                description "Enter the adaptation-rule context";

                                leaf pir {
                                    type types-qos:adaptation-rule;
                                    default "closest";
                                    description "Constraint for deriving operational FIR for the queue";
                                }

                                leaf cir {
                                    type types-qos:adaptation-rule;
                                    default "closest";
                                    description "Constraint for deriving operational CIR for the queue";
                                }

                                leaf fir {
                                    type types-qos:adaptation-rule;
                                    default "closest";
                                    description "Constraint for deriving operational FIR for the queue";
                                }

                            } // container adaptation-rule

                            container drop-tail {
                                description "Enter the drop-tail context";

                                container low {
                                    description "Enter the low context";

                                    leaf percent-reduction-from-mbs {
                                        type types-qos:burst-percent;
                                        description "Low drop-tail percent from MBS that is reduced";
                                    }

                                } // container low

                            } // container drop-tail

                        } // list queue

                        list policer {
                            key "policer-id";
                            description "Enter the policer list instance";

                            leaf policer-id {
                                type types-qos:ingress-policer-id {
                                    range "1..32";
                                }
                                description "Ingress Queue-Group Policer identifier";
                            }

                            leaf description {
                                type types-sros:description;
                                description "Text description";
                            }

                            leaf cbs {
                                type types-qos:plcr-burst-size;
                                description "Exceed threshold of the CIR leaky bucket of the policer";
                            }

                            leaf mbs {
                                type types-qos:plcr-burst-size;
                                description "High priority 'violate' threshold of PIR leaky bucket of this policer";
                            }

                            leaf high-prio-only {
                                type types-qos:burst-percent;
                                description "Percentage of PIR leaky bucket's MBS of this policer that is reserved for high priority traffic";
                            }

                            leaf packet-byte-offset {
                                type types-qos:per-packet-offset;
                                default "0";
                                description "Size of each packet, handled by the policer, to be modified";
                            }

                            leaf profile-capped {
                                type boolean;
                                default "false";
                                description "Enforce a limit on the profile";
                            }

                            leaf stat-mode {
                                type types-qos:ingress-policer-stat-mode;
                                default "minimal";
                                description "Mode of statistics collected by the policer";
                            }

                            leaf adv-config-policy {
                                type leafref {
                                    path "../../../../../adv-config-policy/adv-config-policy-name";
                                }
                                description "Name of the advanced configuration policy to apply with this queue";
                            }

                            leaf-list apply-groups {
                                type leafref {
                                    path "../../../../../../groups/group/name";
                                }
                                max-elements 8;
                                ordered-by user;
                                description "Apply a configuration group at this level";
                            }

                            leaf-list apply-groups-exclude {
                                type leafref {
                                    path "../../../../../../groups/group/name";
                                }
                                max-elements 8;
                                ordered-by user;
                                description "Exclude a configuration group at this level";
                            }

                            choice rate-or-percent-rate {
                                default "rate";
                                case rate {

                                    container rate {
                                        description "Enter the rate context";

                                        leaf pir {
                                            type types-qos:policer-pir-rate;
                                            units "kilobps";
                                            default "max";
                                            description "Administrative PIR";
                                        }

                                        leaf cir {
                                            type types-qos:policer-cir-rate;
                                            units "kilobps";
                                            default "0";
                                            description "Administrative CIR";
                                        }

                                    } // container rate

                                }
                                case percent-rate {

                                    container percent-rate {
                                        description "Enter the percent-rate context";

                                        leaf pir {
                                            type decimal64 {
                                                range "0.01..100.00";
                                                fraction-digits 2;
                                            }
                                            description "Administrative PIR";
                                        }

                                        leaf cir {
                                            type decimal64 {
                                                range "0.00..100.00";
                                                fraction-digits 2;
                                            }
                                            default "0.00";
                                            description "Administrative CIR";
                                        }

                                    } // container percent-rate

                                }
                            }
                            container adaptation-rule {
                                description "Enter the adaptation-rule context";

                                leaf pir {
                                    type types-qos:adaptation-rule;
                                    default "closest";
                                    description "Constraint used when deriving the operational PIR value";
                                }

                                leaf cir {
                                    type types-qos:adaptation-rule;
                                    default "closest";
                                    description "Constraint used when deriving the operational CIR value";
                                }

                            } // container adaptation-rule

                            container arbiter-parent {
                                description "Enter the arbiter-parent context";

                                leaf arbiter-name {
                                    type types-sros:named-item;
                                    description "Arbiter name";
                                }

                                leaf level {
                                    type types-qos:hierarchy-level;
                                    default "1";
                                    description "Level of priority while feeding to the parent";
                                }

                                leaf weight {
                                    type types-qos:weight {
                                        range "1..100";
                                    }
                                    default "1";
                                    description "Weight to be used by the arbiter for feeding this policer";
                                }

                            } // container arbiter-parent

                        } // list policer

                    } // list queue-group

                } // container ingress

                container egress {
                    description "Enter the egress context";

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                    list queue-group {
                        key "egress-queue-group-name";
                        description "Enter the queue-group list instance";

                        leaf egress-queue-group-name {
                            type types-sros:named-item;
                            description "Egress queue group template name";
                        }

                        leaf description {
                            type types-sros:description-or-empty;
                            description "Text description";
                        }

                        leaf queues-hqos-manageable {
                            type boolean;
                            default "true";
                            description "Manage queues through the Hierarchical QoS process";
                        }

                        leaf hs-attachment-policy {
                            type leafref {
                                path "../../../../hs-attachment-policy/name";
                            }
                            description "HS attachment policy applied";
                        }

                        leaf-list apply-groups {
                            type leafref {
                                path "../../../../../groups/group/name";
                            }
                            max-elements 8;
                            ordered-by user;
                            description "Apply a configuration group at this level";
                        }

                        leaf-list apply-groups-exclude {
                            type leafref {
                                path "../../../../../groups/group/name";
                            }
                            max-elements 8;
                            ordered-by user;
                            description "Exclude a configuration group at this level";
                        }

                        container hsmda-queues {
                            status obsolete;
                            description "Enter the hsmda-queues context";

                            leaf low-burst-max-class {
                                status obsolete;
                                type uint32 {
                                    range "1..8";
                                }
                                default "8";
                                description "Specifies which class should use the low priority burst threshold. Use the low priority burst threshold for all classes starting from 1, up to and including that specified by this value. Use the high priority burst threshold for all classes greater than the this value, up to and including class 8.";
                            }

                            leaf packet-byte-offset {
                                status obsolete;
                                type types-qos:egress-per-packet-offset;
                                default "0";
                                description "Packet byte offset to use for the HSMDA egress queues";
                            }

                            leaf wrr-policy {
                                status obsolete;
                                type leafref {
                                    path "../../../../../hsmda-wrr-policy/hsmda-wrr-policy-name";
                                }
                                description "WRR policy to use on this HSMDA egress queue";
                            }

                            list queue {
                                status obsolete;
                                key "queue-id";
                                description "Enter the queue list instance";

                                leaf queue-id {
                                    status obsolete;
                                    type types-qos:egress-queue-id;
                                    description "Egress HSMDA queue ID";
                                }

                                leaf burst-limit {
                                    status obsolete;
                                    type union {
                                        type types-qos:bytes {
                                            range "1..1000000";
                                        }
                                        type enumeration {
                                            enum "auto"                         { value -1; }
                                        }
                                    }
                                    default "auto";
                                    description "Explicit shaping burst size of a queue";
                                }

                                leaf mbs {
                                    status obsolete;
                                    type types-qos:hsmda-queue-burst-size;
                                    units "bytes";
                                    description "Buffer space allowed for the queue";
                                }

                                leaf rate {
                                    status obsolete;
                                    type types-qos:hsmda-queue-pir-rate;
                                    default "max";
                                    description "PIR rate";
                                }

                                leaf slope-policy {
                                    status obsolete;
                                    type leafref {
                                        path "../../../../../../hsmda-slope-policy/hsmda-slope-policy-name";
                                    }
                                    description "Name of the slope policy which overrides the default policy for the named buffer pool";
                                }

                                leaf wrr-weight {
                                    status obsolete;
                                    type types-qos:hsmda-wrr-weight;
                                    default "1";
                                    description "Weight value for the HSMDA queue";
                                }

                                leaf-list apply-groups {
                                    status obsolete;
                                    type leafref {
                                        path "../../../../../../../groups/group/name";
                                    }
                                    max-elements 8;
                                    ordered-by user;
                                    description "Apply a configuration group at this level";
                                }

                                leaf-list apply-groups-exclude {
                                    status obsolete;
                                    type leafref {
                                        path "../../../../../../../groups/group/name";
                                    }
                                    max-elements 8;
                                    ordered-by user;
                                    description "Exclude a configuration group at this level";
                                }

                                container adaptation-rule {
                                    status obsolete;
                                    description "Enter the adaptation-rule context";

                                    leaf pir {
                                        status obsolete;
                                        type types-qos:adaptation-rule;
                                        default "closest";
                                        description "Constraint used when deriving the operational PIR value";
                                    }

                                } // container adaptation-rule

                            } // list queue

                        } // container hsmda-queues

                        list fc {
                            key "fc-name";
                            description "Enter the fc list instance";

                            leaf fc-name {
                                type types-sros:fc-name;
                                description "Forwarding class name";
                            }

                            leaf-list apply-groups {
                                type leafref {
                                    path "../../../../../../groups/group/name";
                                }
                                max-elements 8;
                                ordered-by user;
                                description "Apply a configuration group at this level";
                            }

                            leaf-list apply-groups-exclude {
                                type leafref {
                                    path "../../../../../../groups/group/name";
                                }
                                max-elements 8;
                                ordered-by user;
                                description "Exclude a configuration group at this level";
                            }

                            container queue {
                                description "Enter the queue context";

                                choice queue-or-none {
                                    default "none";
                                    case queue-id {

                                        leaf queue-id {
                                            type leafref {
                                                path "../../../queue/queue-id";
                                            }
                                            description "Queue defined in forwarding class mapping";
                                        }

                                    }
                                    case none {

                                        leaf none {
                                            type empty;
                                            description "No mid-pool is associated with this parent-pool";
                                        }

                                    }
                                }
                            } // container queue

                        } // list fc

                        list queue {
                            key "queue-id";
                            description "Enter the queue list instance";

                            leaf queue-id {
                                type types-qos:egress-queue-id;
                                description "Egress Queue-Group queue identifier";
                            }

                            leaf queue-type {
                                type enumeration {
                                    enum "expedited"                    { value 1; }
                                    enum "best-effort"                  { value 3; }
                                }
                                description "Priority that this queue receives from the hardware level schedulers";
                            }

                            leaf adv-config-policy {
                                type leafref {
                                    path "../../../../../adv-config-policy/adv-config-policy-name";
                                }
                                description "Name of the advanced configuration policy";
                            }

                            leaf burst-limit {
                                type union {
                                    type types-qos:bytes {
                                        range "1..14000000";
                                    }
                                    type enumeration {
                                        enum "auto"                         { value -1; }
                                    }
                                }
                                default "auto";
                                description "Explicit shaping burst size of a queue";
                            }

                            leaf cbs {
                                type union {
                                    type int32 {
                                        range "0..1048576";
                                    }
                                    type enumeration {
                                        enum "auto"                         { value -1; }
                                    }
                                }
                                units "kilobytes";
                                default "auto";
                                description "Reserved buffer space for the queue";
                            }

                            leaf mbs {
                                type union {
                                    type types-qos:bytes {
                                        range "0..1073741824";
                                    }
                                    type enumeration {
                                        enum "auto"                         { value -1; }
                                    }
                                }
                                units "bytes";
                                default "auto";
                                description "Buffer space allowed for the queue";
                            }

                            leaf packet-byte-offset {
                                type types-qos:egress-per-packet-offset;
                                default "0";
                                description "Packet byte offset for addition of policing information";
                            }

                            leaf dynamic-mbs {
                                type boolean;
                                default "false";
                                description "Allow modifying of the MBS size for a queue to maintain maximum latency for traffic";
                            }

                            leaf queue-delay {
                                type uint32 {
                                    range "1..5000";
                                }
                                units "milliseconds";
                                description "Target queue delay for forwarding packets through this queue";
                            }

                            leaf hs-alt-port-class-pool {
                                type boolean;
                                default "false";
                                description "Use HS alternate class port pool buffer for traffic";
                            }

                            leaf hs-wrr-weight {
                                type types-qos:hs-wrr-weight;
                                default "1";
                                description "Weighted Round Robin (WRR) weight to parent with this queue into the scheduler";
                            }

                            leaf hs-class-weight {
                                type types-qos:hs-class-weight;
                                default "1";
                                description "Scheduling class weight";
                            }

                            leaf-list apply-groups {
                                type leafref {
                                    path "../../../../../../groups/group/name";
                                }
                                max-elements 8;
                                ordered-by user;
                                description "Apply a configuration group at this level";
                            }

                            leaf-list apply-groups-exclude {
                                type leafref {
                                    path "../../../../../../groups/group/name";
                                }
                                max-elements 8;
                                ordered-by user;
                                description "Exclude a configuration group at this level";
                            }

                            choice rate-or-percent-rate {
                                default "rate";
                                case rate {

                                    container rate {
                                        description "Enter the rate context";

                                        leaf pir {
                                            type types-qos:queue-pir-rate;
                                            units "kilobps";
                                            default "max";
                                            description "Administrative PIR";
                                        }

                                        leaf cir {
                                            type types-qos:queue-cir-rate;
                                            units "kilobps";
                                            default "0";
                                            description "Administrative CIR";
                                        }

                                    } // container rate

                                }
                                case percent-rate {

                                    container percent-rate {
                                        description "Enter the percent-rate context";

                                        leaf pir {
                                            type decimal64 {
                                                range "0.01..100.00";
                                                fraction-digits 2;
                                            }
                                            description "Administrative PIR percent";
                                        }

                                        leaf cir {
                                            type decimal64 {
                                                range "0.00..100.00";
                                                fraction-digits 2;
                                            }
                                            default "0.00";
                                            description "Administrative CIR percent";
                                        }

                                        leaf reference-rate {
                                            type enumeration {
                                                enum "port-limit"                   { value 2; }
                                                enum "local-limit"                  { value 3; }
                                                enum "reference-port-limit"         { value 4; }
                                            }
                                            default "port-limit";
                                            description "Reference rate";
                                        }

                                    } // container percent-rate

                                }
                            }
                            choice parent-mapping {
                                case scheduler-parent {

                                    container scheduler-parent {
                                        presence "Enable the scheduler-parent context";
                                        description "Enable the scheduler-parent context";

                                        leaf scheduler-name {
                                            type types-sros:named-item;
                                            mandatory true;
                                            description "Parent scheduler name";
                                        }

                                        leaf level {
                                            type types-qos:hierarchy-level;
                                            default "1";
                                            description "Level of priority while feeding to the parent";
                                        }

                                        leaf weight {
                                            type types-qos:weight;
                                            default "1";
                                            description "Weight to be used by the scheduler for feeding this queue";
                                        }

                                        leaf cir-level {
                                            type types-qos:cir-level;
                                            default "0";
                                            description "Level of priority while feeding to the parent";
                                        }

                                        leaf cir-weight {
                                            type types-qos:cir-weight;
                                            default "1";
                                            description "Weight that is used by the scheduler until the committed rate for feeding this queue";
                                        }

                                    } // container scheduler-parent

                                }
                                case port-parent {

                                    container port-parent {
                                        presence "Enable the port-parent context";
                                        description "Enable the port-parent context";

                                        leaf level {
                                            type types-qos:hierarchy-level;
                                            default "1";
                                            description "Port priority that this queue uses to receive bandwidth from the port level scheduler";
                                        }

                                        leaf weight {
                                            type types-qos:weight;
                                            default "1";
                                            description "Weight that this queue uses to receive bandwidth from the port level scheduler";
                                        }

                                        leaf cir-level {
                                            type types-qos:cir-level;
                                            default "0";
                                            description "Port priority that this queue uses to receive bandwidth from the port level scheduler";
                                        }

                                        leaf cir-weight {
                                            type types-qos:cir-weight;
                                            default "0";
                                            description "Weight that this queue uses to receive bandwidth from the port level scheduler";
                                        }

                                    } // container port-parent

                                }
                            }
                            container adaptation-rule {
                                description "Enter the adaptation-rule context";

                                leaf pir {
                                    type types-qos:adaptation-rule;
                                    default "closest";
                                    description "Constraint used when deriving the operational PIR value";
                                }

                                leaf cir {
                                    type types-qos:adaptation-rule;
                                    default "closest";
                                    description "Constraint used when deriving the operational CIR value";
                                }

                            } // container adaptation-rule

                            container wred-queue {
                                description "Enter the wred-queue context";

                                leaf policy {
                                    type leafref {
                                        path "../../../../../../slope-policy/slope-policy-name";
                                    }
                                    description "Slope policy name";
                                }

                                leaf mode {
                                    type types-qos:wred-queue-mode;
                                    description "Generic pool association of the queue to allow queue-specific WRED slopes";
                                }

                                leaf usage {
                                    type types-qos:wred-queue-slope-usage;
                                    description "Congestion control type";
                                }

                            } // container wred-queue

                            container drop-tail {
                                description "Enter the drop-tail context";

                                container highplus {
                                    description "Enter the highplus context";

                                    leaf percent-reduction-from-mbs {
                                        type types-qos:burst-percent;
                                        description "Percentage of drop-tail being that is reduced from MBS for high plus profile packets";
                                    }

                                } // container highplus

                                container high {
                                    description "Enter the high context";

                                    leaf percent-reduction-from-mbs {
                                        type types-qos:burst-percent;
                                        description "Percentage of drop-tail being that is reduced from MBS for high profile packets";
                                    }

                                } // container high

                                container low {
                                    description "Enter the low context";

                                    leaf percent-reduction-from-mbs {
                                        type types-qos:burst-percent;
                                        description "Low drop-tail percent from MBS that is reduced";
                                    }

                                } // container low

                                container exceed {
                                    description "Enter the exceed context";

                                    leaf percent-reduction-from-mbs {
                                        type types-qos:burst-percent;
                                        description "Percentage of drop-tail that is reduced from MBS for exceed profile packets";
                                    }

                                } // container exceed

                            } // container drop-tail

                            container hs-wred-queue {
                                description "Enter the hs-wred-queue context";

                                leaf policy {
                                    type leafref {
                                        path "../../../../../../slope-policy/slope-policy-name";
                                    }
                                    description "Slope policy name";
                                }

                            } // container hs-wred-queue

                        } // list queue

                        list policer {
                            key "policer-id";
                            description "Enter the policer list instance";

                            leaf policer-id {
                                type types-qos:qgroup-egress-policer-id;
                                description "Egress queue-group policer ID";
                            }

                            leaf description {
                                type types-sros:description;
                                description "Text description";
                            }

                            leaf cbs {
                                type types-qos:plcr-burst-size;
                                description "Exceed threshold of the CIR leaky bucket of the policer";
                            }

                            leaf mbs {
                                type types-qos:plcr-burst-size;
                                description "High priority 'violate' threshold of PIR leaky bucket of this policer";
                            }

                            leaf high-prio-only {
                                type types-qos:burst-percent;
                                description "Percentage of PIR leaky bucket's MBS of this policer that is reserved for high priority traffic";
                            }

                            leaf packet-byte-offset {
                                type types-qos:egress-per-packet-offset;
                                default "0";
                                description "Size of each packet, handled by the policer, to be modified";
                            }

                            leaf profile-capped {
                                type boolean;
                                default "false";
                                description "Enforce a limit on the profile";
                            }

                            leaf stat-mode {
                                type types-qos:egress-policer-stat-mode;
                                default "minimal";
                                description "Mode of statistics collected by the policer";
                            }

                            leaf adv-config-policy {
                                type leafref {
                                    path "../../../../../adv-config-policy/adv-config-policy-name";
                                }
                                description "Name of the advanced configuration policy to apply with this queue";
                            }

                            leaf exceed-pir {
                                type boolean;
                                default "false";
                                description "Allow forwarding of packets with an exceed-profile state and traffic exceeding the PIR";
                            }

                            leaf-list apply-groups {
                                type leafref {
                                    path "../../../../../../groups/group/name";
                                }
                                max-elements 8;
                                ordered-by user;
                                description "Apply a configuration group at this level";
                            }

                            leaf-list apply-groups-exclude {
                                type leafref {
                                    path "../../../../../../groups/group/name";
                                }
                                max-elements 8;
                                ordered-by user;
                                description "Exclude a configuration group at this level";
                            }

                            choice rate-or-percent-rate {
                                default "rate";
                                case rate {

                                    container rate {
                                        description "Enter the rate context";

                                        leaf pir {
                                            type types-qos:policer-pir-rate;
                                            units "kilobps";
                                            default "max";
                                            description "Administrative PIR";
                                        }

                                        leaf cir {
                                            type types-qos:policer-cir-rate;
                                            units "kilobps";
                                            default "0";
                                            description "Administrative CIR";
                                        }

                                    } // container rate

                                }
                                case percent-rate {

                                    container percent-rate {
                                        description "Enter the percent-rate context";

                                        leaf pir {
                                            type decimal64 {
                                                range "0.01..100.00";
                                                fraction-digits 2;
                                            }
                                            description "Administrative PIR";
                                        }

                                        leaf cir {
                                            type decimal64 {
                                                range "0.00..100.00";
                                                fraction-digits 2;
                                            }
                                            default "0.00";
                                            description "Administrative CIR";
                                        }

                                        leaf reference-rate {
                                            type enumeration {
                                                enum "local-limit"                  { value 2; }
                                                enum "reference-port-limit"         { value 3; }
                                            }
                                            default "local-limit";
                                            description "Reference rate";
                                        }

                                    } // container percent-rate

                                }
                            }
                            container adaptation-rule {
                                description "Enter the adaptation-rule context";

                                leaf pir {
                                    type types-qos:adaptation-rule;
                                    default "closest";
                                    description "Constraint used when deriving the operational PIR value";
                                }

                                leaf cir {
                                    type types-qos:adaptation-rule;
                                    default "closest";
                                    description "Constraint used when deriving the operational CIR value";
                                }

                            } // container adaptation-rule

                            container arbiter-parent {
                                description "Enter the arbiter-parent context";

                                leaf arbiter-name {
                                    type types-sros:named-item;
                                    description "Arbiter name";
                                }

                                leaf level {
                                    type types-qos:hierarchy-level;
                                    default "1";
                                    description "Priority level";
                                }

                                leaf weight {
                                    type types-qos:weight {
                                        range "1..100";
                                    }
                                    default "1";
                                    description "Weight in the priority level";
                                }

                            } // container arbiter-parent

                        } // list policer

                        list hs-wrr-group {
                            key "group-id";
                            description "Enter the hs-wrr-group list instance";

                            leaf group-id {
                                type types-qos:hs-wrr-group-id;
                                description "HS WRR group identifier";
                            }

                            leaf hs-class-weight {
                                type types-qos:hs-class-weight;
                                default "1";
                                description "Weight of scheduling class";
                            }

                            leaf-list apply-groups {
                                type leafref {
                                    path "../../../../../../groups/group/name";
                                }
                                max-elements 8;
                                ordered-by user;
                                description "Apply a configuration group at this level";
                            }

                            leaf-list apply-groups-exclude {
                                type leafref {
                                    path "../../../../../../groups/group/name";
                                }
                                max-elements 8;
                                ordered-by user;
                                description "Exclude a configuration group at this level";
                            }

                            choice rate-or-percent-rate {
                                default "rate";
                                case rate {

                                    leaf rate {
                                        type union {
                                            type uint32 {
                                                range "1..2000000000";
                                            }
                                            type enumeration {
                                                enum "max"                          { value -1; }
                                            }
                                        }
                                        units "kilobps";
                                        default "max";
                                        description "Administrative PIR";
                                    }

                                }
                                case percent-rate {

                                    leaf percent-rate {
                                        type decimal64 {
                                            range "0.01..100.00";
                                            fraction-digits 2;
                                        }
                                        description "Administrative PIR percent";
                                    }

                                }
                            }
                            container adaptation-rule {
                                description "Enter the adaptation-rule context";

                                leaf pir {
                                    type types-qos:adaptation-rule;
                                    default "closest";
                                    description "Constraint used when deriving the operational PIR value";
                                }

                            } // container adaptation-rule

                        } // list hs-wrr-group

                    } // list queue-group

                } // container egress

            } // container queue-group-templates

            list network {
                key "network-policy-name";
                max-elements 255;
                description "Enter the network list instance";

                leaf network-policy-name {
                    type types-qos:network-policy-name;
                    description "QoS network policy name";
                }

                leaf policy-id {
                    type types-qos:qos-policy-id;
                    sros-ext:immutable;
                    description "QoS network policy ID";
                }

                leaf description {
                    type types-sros:description;
                    description "Text description";
                }

                leaf scope {
                    type types-qos:item-scope;
                    default "template";
                    description "Scope of the policy";
                }

                leaf-list apply-groups {
                    type leafref {
                        path "../../../groups/group/name";
                    }
                    max-elements 8;
                    ordered-by user;
                    description "Apply a configuration group at this level";
                }

                leaf-list apply-groups-exclude {
                    type leafref {
                        path "../../../groups/group/name";
                    }
                    max-elements 8;
                    ordered-by user;
                    description "Exclude a configuration group at this level";
                }

                container ingress {
                    description "Enter the ingress context";

                    leaf ler-use-dscp {
                        type boolean;
                        default "false";
                        description "Honor the DSCP markings instead of the LSP-EXP bits";
                    }

                    container default-action {
                        description "Enter the default-action context";

                        leaf fc {
                            type types-sros:fc-name;
                            default "be";
                            description "Default forwarding class to use while classifying the ingress traffic";
                        }

                        leaf profile {
                            type types-qos:profile;
                            default "out";
                            description "Default profile for the ingressing traffic";
                        }

                    } // container default-action

                    list dot1p {
                        key "dot1p-value";
                        description "Enter the dot1p list instance";

                        leaf dot1p-value {
                            type types-qos:dot1p-priority;
                            description "Dot1p value to match in the packet";
                        }

                        leaf fc {
                            type types-sros:fc-name;
                            mandatory true;
                            description "Forwarding class";
                        }

                        leaf profile {
                            type types-qos:profile-de;
                            mandatory true;
                            description "Default profile to be used for the ingressing traffic";
                        }

                        leaf-list apply-groups {
                            type leafref {
                                path "../../../../../groups/group/name";
                            }
                            max-elements 8;
                            ordered-by user;
                            description "Apply a configuration group at this level";
                        }

                        leaf-list apply-groups-exclude {
                            type leafref {
                                path "../../../../../groups/group/name";
                            }
                            max-elements 8;
                            ordered-by user;
                            description "Exclude a configuration group at this level";
                        }

                    } // list dot1p

                    list dscp {
                        key "dscp-name";
                        description "Enter the dscp list instance";

                        leaf dscp-name {
                            type types-qos:dscp-name;
                            description "DSCP associated with the forwarding class";
                        }

                        leaf fc {
                            type types-sros:fc-name;
                            mandatory true;
                            description "Forwarding class";
                        }

                        leaf profile {
                            type types-qos:profile;
                            mandatory true;
                            description "Default profile to use for the ingressing traffic";
                        }

                        leaf-list apply-groups {
                            type leafref {
                                path "../../../../../groups/group/name";
                            }
                            max-elements 8;
                            ordered-by user;
                            description "Apply a configuration group at this level";
                        }

                        leaf-list apply-groups-exclude {
                            type leafref {
                                path "../../../../../groups/group/name";
                            }
                            max-elements 8;
                            ordered-by user;
                            description "Exclude a configuration group at this level";
                        }

                    } // list dscp

                    list lsp-exp {
                        key "lsp-exp-value";
                        description "Enter the lsp-exp list instance";

                        leaf lsp-exp-value {
                            type types-qos:lsp-exp-value;
                            description "Value to assign the unique MPLS LSP EXP value that will match the lsp-exp rule";
                        }

                        leaf fc {
                            type types-sros:fc-name;
                            mandatory true;
                            description "Forwarding class";
                        }

                        leaf profile {
                            type types-qos:profile;
                            mandatory true;
                            description "Default profile to use for the ingressing traffic";
                        }

                        leaf-list apply-groups {
                            type leafref {
                                path "../../../../../groups/group/name";
                            }
                            max-elements 8;
                            ordered-by user;
                            description "Apply a configuration group at this level";
                        }

                        leaf-list apply-groups-exclude {
                            type leafref {
                                path "../../../../../groups/group/name";
                            }
                            max-elements 8;
                            ordered-by user;
                            description "Exclude a configuration group at this level";
                        }

                    } // list lsp-exp

                    list fc {
                        key "fc-name";
                        description "Enter the fc list instance";

                        leaf fc-name {
                            type types-sros:fc-name;
                            description "Forwarding class name";
                        }

                        leaf-list apply-groups {
                            type leafref {
                                path "../../../../../groups/group/name";
                            }
                            max-elements 8;
                            ordered-by user;
                            description "Apply a configuration group at this level";
                        }

                        leaf-list apply-groups-exclude {
                            type leafref {
                                path "../../../../../groups/group/name";
                            }
                            max-elements 8;
                            ordered-by user;
                            description "Exclude a configuration group at this level";
                        }

                        container fp-redirect-group {
                            description "Enter the fp-redirect-group context";

                            leaf multicast-policer {
                                type types-qos:network-ingress-policer-id;
                                description "Policer to be used for multicast traffic";
                            }

                            leaf policer {
                                type types-qos:network-ingress-policer-id;
                                description "Policer to be used for unicast traffic";
                            }

                            leaf broadcast-policer {
                                type types-qos:network-ingress-policer-id;
                                description "Policer to be used for broadcast traffic";
                            }

                            leaf unknown-policer {
                                type types-qos:network-ingress-policer-id;
                                description "Policer to be used for unknown traffic";
                            }

                        } // container fp-redirect-group

                    } // list fc

                    container ip-criteria {
                        description "Enter the ip-criteria context";

                        list entry {
                            key "entry-id";
                            description "Enter the entry list instance";

                            leaf entry-id {
                                type types-qos:entry-id;
                                description "Network Ingress IP Criteria Entry Index";
                            }

                            leaf description {
                                type types-sros:description;
                                description "Text description";
                            }

                            leaf-list apply-groups {
                                type leafref {
                                    path "../../../../../../groups/group/name";
                                }
                                max-elements 8;
                                ordered-by user;
                                description "Apply a configuration group at this level";
                            }

                            leaf-list apply-groups-exclude {
                                type leafref {
                                    path "../../../../../../groups/group/name";
                                }
                                max-elements 8;
                                ordered-by user;
                                description "Exclude a configuration group at this level";
                            }

                            container match {
                                description "Enter the match context";

                                leaf protocol {
                                    type types-sros:match-ip-protocol;
                                    description "IP protocol to match";
                                }

                                leaf dscp {
                                    type types-qos:dscp-name;
                                    description "DSCP to be used as network QoS policy match criterion";
                                }

                                leaf fragment {
                                    type enumeration {
                                        enum "false"                        { value 2; }
                                        enum "true"                         { value 3; }
                                    }
                                    description "Fragmentation state as the match criterion";
                                }

                                container dst-ip {
                                    description "Enter the dst-ip context";

                                    choice dst-ip {
                                        case address-and-mask-or-prefix {

                                            leaf address {
                                                type union {
                                                    type types-sros:ipv4-address;
                                                    type types-sros:ipv4-prefix-with-host-bits;
                                                }
                                                description "Destination IPv4 address for network QoS policy match";
                                            }

                                            leaf mask {
                                                type types-sros:ipv4-address;
                                                description "IP address to match with source IP of the packet";
                                            }

                                        }
                                        case ip-prefix-list {

                                            leaf ip-prefix-list {
                                                type leafref {
                                                    path "../../../../../../../match-list/ip-prefix-list/prefix-list-name";
                                                }
                                                description "IPv4 prefix list containing IPv4 prefixes to match";
                                            }

                                        }
                                    }
                                } // container dst-ip

                                container src-ip {
                                    description "Enter the src-ip context";

                                    choice src-ip {
                                        case address-and-mask-or-prefix {

                                            leaf address {
                                                type union {
                                                    type types-sros:ipv4-address;
                                                    type types-sros:ipv4-prefix-with-host-bits;
                                                }
                                                description "Source IPv4 address for network QoS policy match";
                                            }

                                            leaf mask {
                                                type types-sros:ipv4-address;
                                                description "IP address to match with source IP of the packet";
                                            }

                                        }
                                        case ip-prefix-list {

                                            leaf ip-prefix-list {
                                                type leafref {
                                                    path "../../../../../../../match-list/ip-prefix-list/prefix-list-name";
                                                }
                                                description "IPv4 prefix list containing IPv4 prefixes to match";
                                            }

                                        }
                                    }
                                } // container src-ip

                                container src-port {
                                    description "Enter the src-port context";

                                    choice port-match-mapping {
                                        case lt {

                                            leaf lt {
                                                type int32 {
                                                    range "0..65535";
                                                }
                                                description "Less than destination port value as the match criterion";
                                            }

                                        }
                                        case eq {

                                            leaf eq {
                                                type int32 {
                                                    range "0..65535";
                                                }
                                                description "Exact source port as the match criterion";
                                            }

                                        }
                                        case gt {

                                            leaf gt {
                                                type int32 {
                                                    range "0..65535";
                                                }
                                                description "Greater than source port value as match criterion";
                                            }

                                        }
                                        case range {

                                            container range {
                                                description "Enter the range context";

                                                leaf start {
                                                    type int32 {
                                                        range "0..65535";
                                                    }
                                                    description "Lower bound of port range to match";
                                                }

                                                leaf end {
                                                    type int32 {
                                                        range "0..65535";
                                                    }
                                                    description "Upper bound of port range to match";
                                                }

                                            } // container range

                                        }
                                        case port-list {

                                            leaf port-list {
                                                type leafref {
                                                    path "../../../../../../../match-list/port-list/port-list-name";
                                                }
                                                description "Port list used as match criterion";
                                            }

                                        }
                                    }
                                } // container src-port

                                container dst-port {
                                    description "Enter the dst-port context";

                                    choice port-match-mapping {
                                        case lt {

                                            leaf lt {
                                                type int32 {
                                                    range "0..65535";
                                                }
                                                description "Less than destination port value as the match criterion";
                                            }

                                        }
                                        case eq {

                                            leaf eq {
                                                type int32 {
                                                    range "0..65535";
                                                }
                                                description "Exact destination port as the match criterion";
                                            }

                                        }
                                        case gt {

                                            leaf gt {
                                                type int32 {
                                                    range "0..65535";
                                                }
                                                description "Greater than destination port value as match criterion";
                                            }

                                        }
                                        case range {

                                            container range {
                                                description "Enter the range context";

                                                leaf start {
                                                    type int32 {
                                                        range "0..65535";
                                                    }
                                                    description "Lower bound of port range to match";
                                                }

                                                leaf end {
                                                    type int32 {
                                                        range "0..65535";
                                                    }
                                                    description "Upper bound of port range to match";
                                                }

                                            } // container range

                                        }
                                        case port-list {

                                            leaf port-list {
                                                type leafref {
                                                    path "../../../../../../../match-list/port-list/port-list-name";
                                                }
                                                description "Port list used as match criterion";
                                            }

                                        }
                                    }
                                } // container dst-port

                            } // container match

                            container action {
                                description "Enter the action context";

                                leaf type {
                                    type types-qos:criteria-action-type;
                                    default "ignore-match";
                                    description "Action for criteria entry";
                                }

                                leaf fc {
                                    type types-sros:fc-name;
                                    description "Forwarding class";
                                }

                                leaf profile {
                                    type types-qos:profile;
                                    description "Default profile for the matching traffic";
                                }

                            } // container action

                        } // list entry

                    } // container ip-criteria

                    container ipv6-criteria {
                        description "Enter the ipv6-criteria context";

                        list entry {
                            key "entry-id";
                            description "Enter the entry list instance";

                            leaf entry-id {
                                type types-qos:entry-id;
                                description "Network Ingress IPv6 Criteria Entry Index";
                            }

                            leaf description {
                                type types-sros:description;
                                description "Text description";
                            }

                            leaf-list apply-groups {
                                type leafref {
                                    path "../../../../../../groups/group/name";
                                }
                                max-elements 8;
                                ordered-by user;
                                description "Apply a configuration group at this level";
                            }

                            leaf-list apply-groups-exclude {
                                type leafref {
                                    path "../../../../../../groups/group/name";
                                }
                                max-elements 8;
                                ordered-by user;
                                description "Exclude a configuration group at this level";
                            }

                            container match {
                                description "Enter the match context";

                                leaf next-header {
                                    type types-sros:match-ip-protocol;
                                    description "IP protocol to match";
                                }

                                leaf dscp {
                                    type types-qos:dscp-name;
                                    description "DSCP value to match in the packet";
                                }

                                leaf fragment {
                                    type enumeration {
                                        enum "false"                        { value 2; }
                                        enum "true"                         { value 3; }
                                        enum "first-only"                   { value 4; }
                                        enum "non-first-only"               { value 5; }
                                    }
                                    description "Fragmentation state as the match criterion";
                                }

                                container dst-ip {
                                    description "Enter the dst-ip context";

                                    choice dst-ip {
                                        case address-and-mask-or-prefix {

                                            leaf address {
                                                type union {
                                                    type types-sros:ipv6-address;
                                                    type types-sros:ipv6-prefix-with-host-bits;
                                                }
                                                description "Destination IPv6 address for network QoS policy match";
                                            }

                                            leaf mask {
                                                type types-sros:ipv6-address;
                                                description "IP address to match with source IP of the packet";
                                            }

                                        }
                                        case ipv6-prefix-list {

                                            leaf ipv6-prefix-list {
                                                type leafref {
                                                    path "../../../../../../../match-list/ipv6-prefix-list/prefix-list-name";
                                                }
                                                description "IPv6 prefix list containing IPv6 prefixes to match";
                                            }

                                        }
                                    }
                                } // container dst-ip

                                container src-ip {
                                    description "Enter the src-ip context";

                                    choice src-ip {
                                        case address-and-mask-or-prefix {

                                            leaf address {
                                                type union {
                                                    type types-sros:ipv6-address;
                                                    type types-sros:ipv6-prefix-with-host-bits;
                                                }
                                                description "Source IPv6 address for network QoS policy match";
                                            }

                                            leaf mask {
                                                type types-sros:ipv6-address;
                                                description "IP address to match with source IP of the packet";
                                            }

                                        }
                                        case ipv6-prefix-list {

                                            leaf ipv6-prefix-list {
                                                type leafref {
                                                    path "../../../../../../../match-list/ipv6-prefix-list/prefix-list-name";
                                                }
                                                description "IPv6 prefix list containing IPv6 prefixes to match";
                                            }

                                        }
                                    }
                                } // container src-ip

                                container src-port {
                                    description "Enter the src-port context";

                                    choice port-match-mapping {
                                        case lt {

                                            leaf lt {
                                                type int32 {
                                                    range "0..65535";
                                                }
                                                description "Less than destination port value as the match criterion";
                                            }

                                        }
                                        case eq {

                                            leaf eq {
                                                type int32 {
                                                    range "0..65535";
                                                }
                                                description "Exact source port as the match criterion";
                                            }

                                        }
                                        case gt {

                                            leaf gt {
                                                type int32 {
                                                    range "0..65535";
                                                }
                                                description "Greater than source port value as match criterion";
                                            }

                                        }
                                        case range {

                                            container range {
                                                description "Enter the range context";

                                                leaf start {
                                                    type int32 {
                                                        range "0..65535";
                                                    }
                                                    description "Lower bound of port range to match";
                                                }

                                                leaf end {
                                                    type int32 {
                                                        range "0..65535";
                                                    }
                                                    description "Upper bound of port range to match";
                                                }

                                            } // container range

                                        }
                                        case port-list {

                                            leaf port-list {
                                                type leafref {
                                                    path "../../../../../../../match-list/port-list/port-list-name";
                                                }
                                                description "Port list used as match criterion";
                                            }

                                        }
                                    }
                                } // container src-port

                                container dst-port {
                                    description "Enter the dst-port context";

                                    choice port-match-mapping {
                                        case lt {

                                            leaf lt {
                                                type int32 {
                                                    range "0..65535";
                                                }
                                                description "Less than destination port value as the match criterion";
                                            }

                                        }
                                        case eq {

                                            leaf eq {
                                                type int32 {
                                                    range "0..65535";
                                                }
                                                description "Exact destination port as the match criterion";
                                            }

                                        }
                                        case gt {

                                            leaf gt {
                                                type int32 {
                                                    range "0..65535";
                                                }
                                                description "Greater than destination port value as match criterion";
                                            }

                                        }
                                        case range {

                                            container range {
                                                description "Enter the range context";

                                                leaf start {
                                                    type int32 {
                                                        range "0..65535";
                                                    }
                                                    description "Lower bound of port range to match";
                                                }

                                                leaf end {
                                                    type int32 {
                                                        range "0..65535";
                                                    }
                                                    description "Upper bound of port range to match";
                                                }

                                            } // container range

                                        }
                                        case port-list {

                                            leaf port-list {
                                                type leafref {
                                                    path "../../../../../../../match-list/port-list/port-list-name";
                                                }
                                                description "Port list used as match criterion";
                                            }

                                        }
                                    }
                                } // container dst-port

                            } // container match

                            container action {
                                description "Enter the action context";

                                leaf type {
                                    type types-qos:criteria-action-type;
                                    default "ignore-match";
                                    description "Action for criteria entry";
                                }

                                leaf fc {
                                    type types-sros:fc-name;
                                    description "Forwarding class";
                                }

                                leaf profile {
                                    type types-qos:profile;
                                    description "Default profile for the matching traffic";
                                }

                            } // container action

                        } // list entry

                    } // container ipv6-criteria

                } // container ingress

                container egress {
                    description "Enter the egress context";

                    container remark-trusted {
                        presence "Enable the remark-trusted context";
                        description "Enable the remark-trusted context";

                        leaf force-egress-marking {
                            type boolean;
                            default "false";
                            description "Remark DSCP bits in the internal IP header";
                        }

                    } // container remark-trusted

                    list dscp {
                        key "dscp-name";
                        description "Enter the dscp list instance";

                        leaf dscp-name {
                            type types-qos:dscp-name;
                            description "DSCP name to perform reclassification actions";
                        }

                        leaf fc {
                            type types-sros:fc-name;
                            mandatory true;
                            description "Forwarding class";
                        }

                        leaf profile {
                            type types-qos:egress-profile;
                            mandatory true;
                            description "Default profile to use for the ingressing traffic";
                        }

                        leaf-list apply-groups {
                            type leafref {
                                path "../../../../../groups/group/name";
                            }
                            max-elements 8;
                            ordered-by user;
                            description "Apply a configuration group at this level";
                        }

                        leaf-list apply-groups-exclude {
                            type leafref {
                                path "../../../../../groups/group/name";
                            }
                            max-elements 8;
                            ordered-by user;
                            description "Exclude a configuration group at this level";
                        }

                    } // list dscp

                    list prec {
                        key "prec-value";
                        description "Enter the prec list instance";

                        leaf prec-value {
                            type types-qos:precedence-value;
                            description "Precedence value for which mapping is performed";
                        }

                        leaf fc {
                            type types-sros:fc-name;
                            mandatory true;
                            description "Forwarding class";
                        }

                        leaf profile {
                            type types-qos:egress-profile;
                            mandatory true;
                            description "Default profile to use for the ingressing traffic";
                        }

                        leaf-list apply-groups {
                            type leafref {
                                path "../../../../../groups/group/name";
                            }
                            max-elements 8;
                            ordered-by user;
                            description "Apply a configuration group at this level";
                        }

                        leaf-list apply-groups-exclude {
                            type leafref {
                                path "../../../../../groups/group/name";
                            }
                            max-elements 8;
                            ordered-by user;
                            description "Exclude a configuration group at this level";
                        }

                    } // list prec

                    list fc {
                        key "fc-name";
                        description "Enter the fc list instance";

                        leaf fc-name {
                            type types-sros:fc-name;
                            description "Forwarding class name";
                        }

                        leaf dot1p-in-profile {
                            type types-qos:dot1p-priority;
                            description "Dot1p marking for in-profile marking";
                        }

                        leaf dot1p-out-profile {
                            type types-qos:dot1p-priority;
                            description "Dot1p marking for out-of-profile marking";
                        }

                        leaf dscp-in-profile {
                            type types-qos:dscp-name;
                            description "DSCP marking for in-profile marking";
                        }

                        leaf dscp-out-profile {
                            type types-qos:dscp-name;
                            description "DSCP marking for out-of-profile marking";
                        }

                        leaf lsp-exp-in-profile {
                            type types-qos:lsp-exp-value;
                            description "LSP-EXP marking for in-profile marking";
                        }

                        leaf lsp-exp-out-profile {
                            type types-qos:lsp-exp-value;
                            description "LSP-EXP marking for out-of-profile marking";
                        }

                        leaf-list apply-groups {
                            type leafref {
                                path "../../../../../groups/group/name";
                            }
                            max-elements 8;
                            ordered-by user;
                            description "Apply a configuration group at this level";
                        }

                        leaf-list apply-groups-exclude {
                            type leafref {
                                path "../../../../../groups/group/name";
                            }
                            max-elements 8;
                            ordered-by user;
                            description "Exclude a configuration group at this level";
                        }

                        container de-mark {
                            presence "Enable the de-mark context";
                            description "Enable the de-mark context";

                            leaf force {
                                type types-qos:de-value;
                                description "DE value";
                            }

                        } // container de-mark

                        container port-redirect-group {
                            description "Enter the port-redirect-group context";

                            leaf queue {
                                type types-qos:egress-queue-id;
                                description "Queue to be used";
                            }

                            leaf policer {
                                type types-qos:qgroup-egress-policer-id;
                                description "Policer to be used";
                            }

                        } // container port-redirect-group

                    } // list fc

                    container ip-criteria {
                        description "Enter the ip-criteria context";

                        list entry {
                            key "entry-id";
                            description "Enter the entry list instance";

                            leaf entry-id {
                                type types-qos:entry-id;
                                description "Entry ID for match criterion and corresponding action";
                            }

                            leaf description {
                                type types-sros:description;
                                description "Text description";
                            }

                            leaf-list apply-groups {
                                type leafref {
                                    path "../../../../../../groups/group/name";
                                }
                                max-elements 8;
                                ordered-by user;
                                description "Apply a configuration group at this level";
                            }

                            leaf-list apply-groups-exclude {
                                type leafref {
                                    path "../../../../../../groups/group/name";
                                }
                                max-elements 8;
                                ordered-by user;
                                description "Exclude a configuration group at this level";
                            }

                            container match {
                                description "Enter the match context";

                                leaf protocol {
                                    type types-sros:match-ip-protocol;
                                    description "IP protocol to match";
                                }

                                leaf dscp {
                                    type types-qos:dscp-name;
                                    description "DSCP value to match in the packet";
                                }

                                leaf fragment {
                                    type enumeration {
                                        enum "false"                        { value 2; }
                                        enum "true"                         { value 3; }
                                    }
                                    description "Fragmentation state as the match criterion";
                                }

                                leaf icmp-type {
                                    type types-filter:ipv4-match-icmp-types;
                                    description "ICMP type in the ICMP header of IPv4 packet to match";
                                }

                                container dst-ip {
                                    description "Enter the dst-ip context";

                                    choice dst-ip {
                                        case address-and-mask-or-prefix {

                                            leaf address {
                                                type union {
                                                    type types-sros:ipv4-address;
                                                    type types-sros:ipv4-prefix-with-host-bits;
                                                }
                                                description "Destination IPv4 address to match";
                                            }

                                            leaf mask {
                                                type types-sros:ipv4-address;
                                                description "Subnet mask";
                                            }

                                        }
                                    }
                                } // container dst-ip

                                container src-ip {
                                    description "Enter the src-ip context";

                                    choice src-ip {
                                        case address-and-mask-or-prefix {

                                            leaf address {
                                                type union {
                                                    type types-sros:ipv4-address;
                                                    type types-sros:ipv4-prefix-with-host-bits;
                                                }
                                                description "Source IPv4 address to match";
                                            }

                                            leaf mask {
                                                type types-sros:ipv4-address;
                                                description "Subnet mask";
                                            }

                                        }
                                    }
                                } // container src-ip

                                container src-port {
                                    description "Enter the src-port context";

                                    choice port-match-mapping {
                                        case lt {

                                            leaf lt {
                                                type int32 {
                                                    range "0..65535";
                                                }
                                                description "Value 'less than' assigned as match condition";
                                            }

                                        }
                                        case eq {

                                            leaf eq {
                                                type int32 {
                                                    range "0..65535";
                                                }
                                                description "Value 'equal to' assigned as match condition";
                                            }

                                        }
                                        case gt {

                                            leaf gt {
                                                type int32 {
                                                    range "0..65535";
                                                }
                                                description "Value 'greater than' assigned as match condition";
                                            }

                                        }
                                        case range {

                                            container range {
                                                description "Enter the range context";

                                                leaf start {
                                                    type int32 {
                                                        range "0..65535";
                                                    }
                                                    description "Lower bound of port range to match";
                                                }

                                                leaf end {
                                                    type int32 {
                                                        range "0..65535";
                                                    }
                                                    description "Upper bound of port range to match";
                                                }

                                            } // container range

                                        }
                                        case port-list {

                                            leaf port-list {
                                                type leafref {
                                                    path "../../../../../../../match-list/port-list/port-list-name";
                                                }
                                                description "Name of the port list as the match criterion";
                                            }

                                        }
                                    }
                                } // container src-port

                                container dst-port {
                                    description "Enter the dst-port context";

                                    choice port-match-mapping {
                                        case lt {

                                            leaf lt {
                                                type int32 {
                                                    range "0..65535";
                                                }
                                                description "Value 'less than' assigned as match condition";
                                            }

                                        }
                                        case eq {

                                            leaf eq {
                                                type int32 {
                                                    range "0..65535";
                                                }
                                                description "Value 'equal to' assigned as match condition";
                                            }

                                        }
                                        case gt {

                                            leaf gt {
                                                type int32 {
                                                    range "0..65535";
                                                }
                                                description "Value 'greater than' assigned as match condition";
                                            }

                                        }
                                        case range {

                                            container range {
                                                description "Enter the range context";

                                                leaf start {
                                                    type int32 {
                                                        range "0..65535";
                                                    }
                                                    description "Lower bound of port range to match";
                                                }

                                                leaf end {
                                                    type int32 {
                                                        range "0..65535";
                                                    }
                                                    description "Upper bound of port range to match";
                                                }

                                            } // container range

                                        }
                                        case port-list {

                                            leaf port-list {
                                                type leafref {
                                                    path "../../../../../../../match-list/port-list/port-list-name";
                                                }
                                                description "Name of the port list as the match criterion";
                                            }

                                        }
                                    }
                                } // container dst-port

                            } // container match

                            container action {
                                description "Enter the action context";

                                leaf type {
                                    type types-qos:criteria-action-type;
                                    default "ignore-match";
                                    description "Action for criteria entry";
                                }

                                leaf fc {
                                    type types-sros:fc-name;
                                    description "Forwarding class";
                                }

                                leaf profile {
                                    type types-qos:egress-profile;
                                    description "Profile reclassification action";
                                }

                                container port-redirect-group {
                                    description "Enter the port-redirect-group context";

                                    leaf queue {
                                        type types-qos:egress-queue-id;
                                        description "Queue to be used for post-policed traffic";
                                    }

                                    leaf policer {
                                        type types-qos:qgroup-egress-policer-id;
                                        description "Policer ID to be used for the matched traffic";
                                    }

                                } // container port-redirect-group

                            } // container action

                        } // list entry

                    } // container ip-criteria

                    container ipv6-criteria {
                        description "Enter the ipv6-criteria context";

                        list entry {
                            key "entry-id";
                            description "Enter the entry list instance";

                            leaf entry-id {
                                type types-qos:entry-id;
                                description "Entry ID for match criterion and corresponding action";
                            }

                            leaf description {
                                type types-sros:description;
                                description "Text description";
                            }

                            leaf-list apply-groups {
                                type leafref {
                                    path "../../../../../../groups/group/name";
                                }
                                max-elements 8;
                                ordered-by user;
                                description "Apply a configuration group at this level";
                            }

                            leaf-list apply-groups-exclude {
                                type leafref {
                                    path "../../../../../../groups/group/name";
                                }
                                max-elements 8;
                                ordered-by user;
                                description "Exclude a configuration group at this level";
                            }

                            container match {
                                description "Enter the match context";

                                leaf next-header {
                                    type types-sros:match-ip-protocol;
                                    description "IP protocol to match";
                                }

                                leaf dscp {
                                    type types-qos:dscp-name;
                                    description "DSCP value to match in the packet";
                                }

                                leaf fragment {
                                    type enumeration {
                                        enum "false"                        { value 2; }
                                        enum "true"                         { value 3; }
                                        enum "first-only"                   { value 4; }
                                        enum "non-first-only"               { value 5; }
                                    }
                                    description "Fragmentation state as the match criterion";
                                }

                                leaf icmp-type {
                                    type types-filter:ipv6-match-icmp-types;
                                    description "ICMPv6 type in ICMPv6 header of IPv6 packet to match";
                                }

                                container dst-ip {
                                    description "Enter the dst-ip context";

                                    choice dst-ip {
                                        case address-and-mask-or-prefix {

                                            leaf address {
                                                type union {
                                                    type types-sros:ipv6-address;
                                                    type types-sros:ipv6-prefix-with-host-bits;
                                                }
                                                description "Destination IPv6 address to match";
                                            }

                                            leaf mask {
                                                type types-sros:ipv6-address;
                                                description "Address mask";
                                            }

                                        }
                                    }
                                } // container dst-ip

                                container src-ip {
                                    description "Enter the src-ip context";

                                    choice src-ip {
                                        case address-and-mask-or-prefix {

                                            leaf address {
                                                type union {
                                                    type types-sros:ipv6-address;
                                                    type types-sros:ipv6-prefix-with-host-bits;
                                                }
                                                description "Source IPv6 address to match";
                                            }

                                            leaf mask {
                                                type types-sros:ipv6-address;
                                                description "Address mask";
                                            }

                                        }
                                    }
                                } // container src-ip

                                container src-port {
                                    description "Enter the src-port context";

                                    choice port-match-mapping {
                                        case lt {

                                            leaf lt {
                                                type int32 {
                                                    range "0..65535";
                                                }
                                                description "Value 'less than' assigned as match condition";
                                            }

                                        }
                                        case eq {

                                            leaf eq {
                                                type int32 {
                                                    range "0..65535";
                                                }
                                                description "Value 'equal to' assigned as match condition";
                                            }

                                        }
                                        case gt {

                                            leaf gt {
                                                type int32 {
                                                    range "0..65535";
                                                }
                                                description "Value 'greater than' assigned as match condition";
                                            }

                                        }
                                        case range {

                                            container range {
                                                description "Enter the range context";

                                                leaf start {
                                                    type int32 {
                                                        range "0..65535";
                                                    }
                                                    description "Lower bound of port range to match";
                                                }

                                                leaf end {
                                                    type int32 {
                                                        range "0..65535";
                                                    }
                                                    description "Upper bound of port range to match";
                                                }

                                            } // container range

                                        }
                                        case port-list {

                                            leaf port-list {
                                                type leafref {
                                                    path "../../../../../../../match-list/port-list/port-list-name";
                                                }
                                                description "Name of the port list as the match criterion";
                                            }

                                        }
                                    }
                                } // container src-port

                                container dst-port {
                                    description "Enter the dst-port context";

                                    choice port-match-mapping {
                                        case lt {

                                            leaf lt {
                                                type int32 {
                                                    range "0..65535";
                                                }
                                                description "Value 'less than' assigned as match condition";
                                            }

                                        }
                                        case eq {

                                            leaf eq {
                                                type int32 {
                                                    range "0..65535";
                                                }
                                                description "Value 'equal to' assigned as match condition";
                                            }

                                        }
                                        case gt {

                                            leaf gt {
                                                type int32 {
                                                    range "0..65535";
                                                }
                                                description "Value 'greater than' assigned as match condition";
                                            }

                                        }
                                        case range {

                                            container range {
                                                description "Enter the range context";

                                                leaf start {
                                                    type int32 {
                                                        range "0..65535";
                                                    }
                                                    description "Lower bound of port range to match";
                                                }

                                                leaf end {
                                                    type int32 {
                                                        range "0..65535";
                                                    }
                                                    description "Upper bound of port range to match";
                                                }

                                            } // container range

                                        }
                                        case port-list {

                                            leaf port-list {
                                                type leafref {
                                                    path "../../../../../../../match-list/port-list/port-list-name";
                                                }
                                                description "Name of the port list as the match criterion";
                                            }

                                        }
                                    }
                                } // container dst-port

                            } // container match

                            container action {
                                description "Enter the action context";

                                leaf type {
                                    type types-qos:criteria-action-type;
                                    default "ignore-match";
                                    description "Action for criteria entry";
                                }

                                leaf fc {
                                    type types-sros:fc-name;
                                    description "Forwarding class";
                                }

                                leaf profile {
                                    type types-qos:egress-profile;
                                    description "Profile reclassification action";
                                }

                                container port-redirect-group {
                                    description "Enter the port-redirect-group context";

                                    leaf queue {
                                        type types-qos:egress-queue-id;
                                        description "Queue to be used for post-policed traffic";
                                    }

                                    leaf policer {
                                        type types-qos:qgroup-egress-policer-id;
                                        description "Policer ID to be used for the matched traffic";
                                    }

                                } // container port-redirect-group

                            } // container action

                        } // list entry

                    } // container ipv6-criteria

                } // container egress

            } // list network

            list port-qos-policy {
                key "port-qos-policy-name";
                max-elements 511;
                description "Enter the port-qos-policy list instance";

                leaf port-qos-policy-name {
                    type types-sros:named-item-64;
                    description "Port QoS policy name";
                }

                leaf description {
                    type types-sros:description;
                    description "Text description";
                }

                leaf scope {
                    type types-qos:item-scope;
                    default "template";
                    description "Scope of the scheduler policy";
                }

                leaf-list apply-groups {
                    type leafref {
                        path "../../../groups/group/name";
                    }
                    max-elements 8;
                    ordered-by user;
                    description "Apply a configuration group at this level";
                }

                leaf-list apply-groups-exclude {
                    type leafref {
                        path "../../../groups/group/name";
                    }
                    max-elements 8;
                    ordered-by user;
                    description "Exclude a configuration group at this level";
                }

                list fc {
                    key "fc-name";
                    description "Enter the fc list instance";

                    leaf fc-name {
                        type types-sros:fc-name;
                        description "Forwarding class name";
                    }

                    leaf queue {
                        type leafref {
                            path "../../queue/queue-id";
                        }
                        description "QoS policy queue for the forwarding class";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                } // list fc

                list queue {
                    key "queue-id";
                    description "Enter the queue list instance";

                    leaf queue-id {
                        type types-qos:egress-queue-id;
                        description "Port QoS policy queue identifier";
                    }

                    leaf queue-mgmt {
                        type leafref {
                            path "../../../queue-mgmt-policy/queue-mgmt-policy-name";
                        }
                        description "Queue management policy to attach to this queue";
                    }

                    leaf wrr-weights {
                        type leafref {
                            path "../../wrr-weights/wrr-weights-id";
                        }
                        description "Weighted Round Robin (WRR) profile associated with this queue";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                    container adaptation-rule {
                        description "Enter the adaptation-rule context";

                        leaf pir {
                            type types-qos:adaptation-rule;
                            default "closest";
                            description "Adaptation rule to use while computing operational PIR value";
                        }

                        leaf cir {
                            type types-qos:adaptation-rule;
                            default "closest";
                            description "Adaptation rule to use while computing operational CIR value";
                        }

                    } // container adaptation-rule

                    container scheduler-mode {
                        description "Enter the scheduler-mode context";

                        choice wfq-or-strict-priority {
                            default "wfq";
                            case wfq {

                                container wfq {
                                    description "Enter the wfq context";

                                    leaf pir-weight {
                                        type uint32 {
                                            range "1..255";
                                        }
                                        default "1";
                                        description "PIR weight for the queue";
                                    }

                                    container percent-rate {
                                        description "Enter the percent-rate context";

                                        leaf pir {
                                            type decimal64 {
                                                range "0.01..100.00";
                                                fraction-digits 2;
                                            }
                                            default "100.00";
                                            description "Administrative PIR percent rate";
                                        }

                                        leaf cir {
                                            type decimal64 {
                                                range "0.00..100.00";
                                                fraction-digits 2;
                                            }
                                            default "0.00";
                                            description "Administrative CIR percent rate";
                                        }

                                    } // container percent-rate

                                } // container wfq

                            }
                        }
                    } // container scheduler-mode

                } // list queue

                list wrr-weights {
                    key "wrr-weights-id";
                    max-elements 1;
                    description "Enter the wrr-weights list instance";

                    leaf wrr-weights-id {
                        type uint32 {
                            range "1..8";
                        }
                        description "Port QoS policy WRR weights identifier";
                    }

                    leaf mc-weight {
                        type types-qos:port-qos-policy-wrr-weight;
                        default "1";
                        description "Weight for the multicast queue";
                    }

                    leaf uc-weight {
                        type types-qos:port-qos-policy-wrr-weight;
                        default "1";
                        description "Weight for the unicast queue";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                } // list wrr-weights

                container packet-byte-offset {
                    description "Enter the packet-byte-offset context";

                    choice add-or-subtract {
                        case add {

                            leaf add {
                                type types-qos:pkt-byte-offset;
                                description "Offset bytes to add";
                            }

                        }
                        case subtract {

                            leaf subtract {
                                type types-qos:pkt-byte-offset;
                                description "Offset bytes to subtract";
                            }

                        }
                    }
                } // container packet-byte-offset

            } // list port-qos-policy

            list vlan-qos-policy {
                key "vlan-qos-policy-name";
                max-elements 511;
                description "Enter the vlan-qos-policy list instance";

                leaf vlan-qos-policy-name {
                    type types-sros:named-item-64;
                    description "VLAN QoS policy name";
                }

                leaf description {
                    type types-sros:description;
                    description "Text description";
                }

                leaf scope {
                    type types-qos:item-scope;
                    default "template";
                    description "Scope of the VLAN QoS policy";
                }

                leaf stat-mode {
                    type enumeration {
                        enum "no-stats"                     { value 1; }
                        enum "enqueued-with-discards"       { value 2; }
                        enum "enqueued-4-profile-with-discards" { value 3; }
                    }
                    default "no-stats";
                    description "Statistics mode of the VLAN QoS policy";
                }

                leaf-list apply-groups {
                    type leafref {
                        path "../../../groups/group/name";
                    }
                    max-elements 8;
                    ordered-by user;
                    description "Apply a configuration group at this level";
                }

                leaf-list apply-groups-exclude {
                    type leafref {
                        path "../../../groups/group/name";
                    }
                    max-elements 8;
                    ordered-by user;
                    description "Exclude a configuration group at this level";
                }

                list cir-weight-profile {
                    key "cir-weight-profile-id";
                    description "Enter the cir-weight-profile list instance";

                    leaf cir-weight-profile-id {
                        type uint32 {
                            range "1..2";
                        }
                        description "VLAN QoS policy CIR weight profile identifier";
                    }

                    leaf weight {
                        type uint32 {
                            range "1..1024";
                        }
                        default "1";
                        description "CIR weight profile weight";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                } // list cir-weight-profile

                list fc {
                    key "fc-name";
                    description "Enter the fc list instance";

                    leaf fc-name {
                        type types-sros:fc-name;
                        description "FC name for which policy entries are created";
                    }

                    leaf queue {
                        type leafref {
                            path "../../queue/queue-id";
                        }
                        description "VLAN QoS queue for the FC";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                } // list fc

                list queue {
                    key "queue-id";
                    description "Enter the queue list instance";

                    leaf queue-id {
                        type types-qos:egress-queue-id;
                        description "Queue identifier for the VLAN QoS policy";
                    }

                    leaf queue-mgmt {
                        type leafref {
                            path "../../../queue-mgmt-policy/queue-mgmt-policy-name";
                        }
                        description "Queue management policy attached to this queue";
                    }

                    leaf scheduling-priority {
                        type uint32 {
                            range "1..6";
                        }
                        description "Specifies scheduling priority of this queue.";
                    }

                    leaf queue-forwarding-type {
                        type enumeration {
                            enum "best-effort"                  { value 0; }
                            enum "expedite-hi"                  { value 1; }
                            enum "expedite-lo"                  { value 2; }
                        }
                        description "Queue forwarding type for this queue";
                    }

                    leaf cir-weight-profile {
                        type uint32 {
                            range "1..2";
                        }
                        default "1";
                        description "CIR weight used by VLAN QoS policy queue";
                    }

                    leaf pir-weight {
                        type uint32 {
                            range "1..253";
                        }
                        default "1";
                        description "PIR weight for a queue";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                    container adaptation-rule {
                        description "Enter the adaptation-rule context";

                        leaf pir {
                            type types-qos:adaptation-rule;
                            default "closest";
                            description "Adaptation rule to use for PIR";
                        }

                        leaf cir {
                            type types-qos:adaptation-rule;
                            default "closest";
                            description "Adaptation rule to use for CIR";
                        }

                    } // container adaptation-rule

                    container queue-type {
                        status obsolete;
                        description "Enter the queue-type context";

                        choice best-effort-hi-low {
                            status obsolete;
                            default "best-effort";
                            case best-effort {
                                status obsolete;

                                container best-effort {
                                    status obsolete;
                                    description "Enter the best-effort context";

                                    leaf cir-weight-profile {
                                        status obsolete;
                                        type uint32 {
                                            range "1..2";
                                        }
                                        default "1";
                                        description "Specifies the weight profile identifier of vlan-qos policy that needs to be used by the arbiter to which this queue would be feeding to.";
                                    }

                                    leaf pir-weight {
                                        status obsolete;
                                        type uint32 {
                                            range "1..253";
                                        }
                                        default "1";
                                        description "Specifies the weight that needs to be used by the arbiter to which this queue would be feeding to.";
                                    }

                                    container percent-rate {
                                        status obsolete;
                                        description "Enter the percent-rate context";

                                        leaf pir {
                                            status obsolete;
                                            type decimal64 {
                                                range "0.01..100.00";
                                                fraction-digits 2;
                                            }
                                            default "100.00";
                                            description "Specifies the administrative PIR percent.";
                                        }

                                        leaf cir {
                                            status obsolete;
                                            type decimal64 {
                                                range "0.00..100.00";
                                                fraction-digits 2;
                                            }
                                            default "0.00";
                                            description "Specifies the administrative CIR percent.";
                                        }

                                    } // container percent-rate

                                } // container best-effort

                            }
                            case expedite-hi {
                                status obsolete;

                                container expedite-hi {
                                    status obsolete;
                                    description "Enter the expedite-hi context";

                                    leaf pir-weight {
                                        status obsolete;
                                        type uint32 {
                                            range "1..253";
                                        }
                                        default "1";
                                        description "Specifies the weight that needs to be used by the arbiter to which this queue would be feeding to.";
                                    }

                                    container percent-rate {
                                        status obsolete;
                                        description "Enter the percent-rate context";

                                        leaf pir {
                                            status obsolete;
                                            type decimal64 {
                                                range "0.01..100.00";
                                                fraction-digits 2;
                                            }
                                            default "100.00";
                                            description "Specifies the administrative PIR percent.";
                                        }

                                        leaf cir {
                                            status obsolete;
                                            type decimal64 {
                                                range "0.00..100.00";
                                                fraction-digits 2;
                                            }
                                            default "0.00";
                                            description "Specifies the administrative CIR percent.";
                                        }

                                    } // container percent-rate

                                } // container expedite-hi

                            }
                            case expedite-lo {
                                status obsolete;

                                container expedite-lo {
                                    status obsolete;
                                    description "Enter the expedite-lo context";

                                    leaf pir-weight {
                                        status obsolete;
                                        type uint32 {
                                            range "1..253";
                                        }
                                        default "1";
                                        description "Specifies the weight that needs to be used by the arbiter to which this queue would be feeding to.";
                                    }

                                    container percent-rate {
                                        status obsolete;
                                        description "Enter the percent-rate context";

                                        leaf pir {
                                            status obsolete;
                                            type decimal64 {
                                                range "0.01..100.00";
                                                fraction-digits 2;
                                            }
                                            default "100.00";
                                            description "Specifies the administrative PIR percent.";
                                        }

                                        leaf cir {
                                            status obsolete;
                                            type decimal64 {
                                                range "0.00..100.00";
                                                fraction-digits 2;
                                            }
                                            default "0.00";
                                            description "Specifies the administrative CIR percent.";
                                        }

                                    } // container percent-rate

                                } // container expedite-lo

                            }
                        }
                    } // container queue-type

                    container percent-rate {
                        description "Enter the percent-rate context";

                        leaf pir {
                            type decimal64 {
                                range "0.01..100.00";
                                fraction-digits 2;
                            }
                            default "100.00";
                            description "Queue PIR as a percentage of the reference rate";
                        }

                        leaf cir {
                            type decimal64 {
                                range "0.00..100.00";
                                fraction-digits 2;
                            }
                            default "0.00";
                            description "Queue CIR as a percentage of the reference rate";
                        }

                    } // container percent-rate

                } // list queue

                container packet-byte-offset {
                    description "Enter the packet-byte-offset context";

                    choice add-or-subtract {
                        case add {

                            leaf add {
                                type types-qos:pkt-byte-offset;
                                description "Offset bytes to add";
                            }

                        }
                        case subtract {

                            leaf subtract {
                                type types-qos:pkt-byte-offset;
                                description "Offset bytes to subtract";
                            }

                        }
                    }
                } // container packet-byte-offset

            } // list vlan-qos-policy

            list queue-mgmt-policy {
                key "queue-mgmt-policy-name";
                max-elements 40;
                description "Enter the queue-mgmt-policy list instance";

                leaf queue-mgmt-policy-name {
                    type types-sros:named-item-64;
                    description "Queue management policy name";
                }

                leaf description {
                    type types-sros:description;
                    description "Text description";
                }

                leaf mbs {
                    type union {
                        type types-qos:kilobytes {
                            range "1..1500000";
                        }
                        type enumeration {
                            enum "auto"                         { value 6250; }
                        }
                    }
                    units "kilobytes";
                    default "6250";
                    description "MBS size for the queue";
                }

                leaf scope {
                    type types-qos:item-scope;
                    default "template";
                    description "Queue management policy scope";
                }

                leaf time-average-factor {
                    type uint32 {
                        range "0..31";
                    }
                    default "7";
                    description "Queue management policy time average factor";
                }

                leaf port-speed {
                    type uint32 {
                        range "10|25|40|50|100|200|400";
                    }
                    units "gigabps";
                    default "100";
                    description "Queue management policy port speed";
                }

                leaf-list apply-groups {
                    type leafref {
                        path "../../../groups/group/name";
                    }
                    max-elements 8;
                    ordered-by user;
                    description "Apply a configuration group at this level";
                }

                leaf-list apply-groups-exclude {
                    type leafref {
                        path "../../../groups/group/name";
                    }
                    max-elements 8;
                    ordered-by user;
                    description "Exclude a configuration group at this level";
                }

                container exceed-slope {
                    description "Enter the exceed-slope context";

                    leaf admin-state {
                        type types-sros:admin-state;
                        default "disable";
                        description "Administrative state of the exceed RED slope";
                    }

                    leaf start-avg {
                        type uint32 {
                            range "0..100";
                        }
                        default "30";
                        description "Start average for exceed-slope RED slope position";
                    }

                    leaf max-avg {
                        type uint32 {
                            range "0..100";
                        }
                        default "55";
                        description "Maximum average exceed-slope RED slope position";
                    }

                    leaf max-prob {
                        type uint32 {
                            range "1..99";
                        }
                        default "75";
                        description "Maximum probability exceed-slope RED slope position";
                    }

                } // container exceed-slope

                container high-slope {
                    description "Enter the high-slope context";

                    leaf admin-state {
                        type types-sros:admin-state;
                        default "disable";
                        description "Administrative state of the high-priority RED slope";
                    }

                    leaf start-avg {
                        type uint32 {
                            range "0..100";
                        }
                        default "70";
                        description "Start average for high-slope RED slope position";
                    }

                    leaf max-avg {
                        type uint32 {
                            range "0..100";
                        }
                        default "90";
                        description "Maximum average high-slope RED slope position";
                    }

                    leaf max-prob {
                        type uint32 {
                            range "1..99";
                        }
                        default "75";
                        description "Maximum probability high-slope RED slope position";
                    }

                } // container high-slope

                container highplus-slope {
                    description "Enter the highplus-slope context";

                    leaf admin-state {
                        type types-sros:admin-state;
                        default "disable";
                        description "Administrative state of the highplus priority RED slope";
                    }

                    leaf start-avg {
                        type uint32 {
                            range "0..100";
                        }
                        default "85";
                        description "Start average for highplus-slope RED slope position";
                    }

                    leaf max-avg {
                        type uint32 {
                            range "0..100";
                        }
                        default "100";
                        description "Maximum average highplus-slope RED slope position";
                    }

                    leaf max-prob {
                        type uint32 {
                            range "1..99";
                        }
                        default "75";
                        description "Maximum probability highplus-slope RED slope position";
                    }

                } // container highplus-slope

                container low-slope {
                    description "Enter the low-slope context";

                    leaf admin-state {
                        type types-sros:admin-state;
                        default "disable";
                        description "Administrative state of the low-priority RED slope";
                    }

                    leaf start-avg {
                        type uint32 {
                            range "0..100";
                        }
                        default "50";
                        description "Start average for low-slope RED slope position";
                    }

                    leaf max-avg {
                        type uint32 {
                            range "0..100";
                        }
                        default "75";
                        description "Maximum average low-slope RED slope position";
                    }

                    leaf max-prob {
                        type uint32 {
                            range "1..99";
                        }
                        default "75";
                        description "Maximum probability low-slope RED slope position";
                    }

                } // container low-slope

            } // list queue-mgmt-policy

            list ingress-classification-policy {
                key "ingress-classification-policy-name";
                max-elements 511;
                description "Enter the ingress-classification-policy list instance";

                leaf ingress-classification-policy-name {
                    type types-sros:named-item-64;
                    description "Name of this ingress classification QoS policy";
                }

                leaf allow-attachment {
                    type types-qos:ingress-class-plcy-prof-attach;
                    sros-ext:immutable;
                    default "any";
                    description "Specifies the profile attachment on epipe-sap.";
                }

                leaf description {
                    type types-sros:description;
                    description "Text description";
                }

                leaf scope {
                    type types-qos:item-scope;
                    default "template";
                    description "Scope of the policy";
                }

                leaf remark {
                    type types-qos:ing-class-remark-value;
                    sros-ext:immutable;
                    default "any";
                    description "Remarking to use at egress";
                }

                leaf dot1p-fc-map {
                    type leafref {
                        path "../../dot1p-fc-map/dot1p-fc-map-name";
                    }
                    description "Attach dot1p FC map to ingress classification policy";
                }

                leaf dscp-fc-map {
                    type leafref {
                        path "../../dscp-fc-map/dscp-fc-map-name";
                    }
                    description "Attach DSCP FC map to ingress classification policy";
                }

                leaf lsp-exp-fc-map {
                    type leafref {
                        path "../../lsp-exp-fc-map/lsp-exp-fc-map-name";
                    }
                    description "Attach LSP-EXP FC map to ingress classification policy";
                }

                leaf-list apply-groups {
                    type leafref {
                        path "../../../groups/group/name";
                    }
                    max-elements 8;
                    ordered-by user;
                    description "Apply a configuration group at this level";
                }

                leaf-list apply-groups-exclude {
                    type leafref {
                        path "../../../groups/group/name";
                    }
                    max-elements 8;
                    ordered-by user;
                    description "Exclude a configuration group at this level";
                }

                container default-action {
                    description "Enter the default-action context";

                    leaf fc {
                        type types-sros:fc-name;
                        default "be";
                        description "Default forwarding class to classify ingress traffic";
                    }

                    leaf profile {
                        type types-qos:profile;
                        default "out";
                        description "Default profile for ingress traffic";
                    }

                } // container default-action

                list dot1p {
                    key "dot1p-value";
                    description "Enter the dot1p list instance";

                    leaf dot1p-value {
                        type types-qos:dot1p-priority;
                        description "Dot1p value to match in the packet";
                    }

                    leaf fc {
                        type types-sros:fc-name;
                        description "Forwarding class";
                    }

                    leaf profile {
                        type types-qos:profile-de;
                        description "Default profile for ingress traffic";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                } // list dot1p

                list dscp {
                    key "dscp-name";
                    description "Enter the dscp list instance";

                    leaf dscp-name {
                        type types-qos:dscp-name;
                        description "DSCP name";
                    }

                    leaf fc {
                        type types-sros:fc-name;
                        description "Forwarding class";
                    }

                    leaf profile {
                        type types-qos:profile;
                        description "Default profile for ingress traffic";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                } // list dscp

                list lsp-exp {
                    key "lsp-exp-value";
                    description "Enter the lsp-exp list instance";

                    leaf lsp-exp-value {
                        type types-qos:lsp-exp-value;
                        description "LSP EXP bit value";
                    }

                    leaf fc {
                        type types-sros:fc-name;
                        description "Forwarding class";
                    }

                    leaf profile {
                        type types-qos:profile;
                        description "Default profile for ingress traffic";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                } // list lsp-exp

            } // list ingress-classification-policy

            list network-ingress {
                key "network-ingress-policy-name";
                max-elements 255;
                description "Enter the network-ingress list instance";

                leaf network-ingress-policy-name {
                    type types-sros:named-item-64;
                    description "Network ingress QoS policy name";
                }

                leaf policer-allocation {
                    type types-qos:network-ingress-policer-mode;
                    sros-ext:immutable;
                    default "none";
                    description "FC policer mapping for network-ingress policy";
                }

                leaf description {
                    type types-sros:description;
                    description "Text description";
                }

                leaf ingress-classification-policy {
                    type leafref {
                        path "../../ingress-classification-policy/ingress-classification-policy-name";
                    }
                    description "Attach ingress classification policy";
                }

                leaf scope {
                    type types-qos:item-scope;
                    default "template";
                    description "Scope of the policy";
                }

                leaf-list apply-groups {
                    type leafref {
                        path "../../../groups/group/name";
                    }
                    max-elements 8;
                    ordered-by user;
                    description "Apply a configuration group at this level";
                }

                leaf-list apply-groups-exclude {
                    type leafref {
                        path "../../../groups/group/name";
                    }
                    max-elements 8;
                    ordered-by user;
                    description "Exclude a configuration group at this level";
                }

                list fc {
                    key "fc-name";
                    description "Enter the fc list instance";

                    leaf fc-name {
                        type types-qos:sap-ingress-fc-name;
                        description "Forwarding class for which this mapping is performed";
                    }

                    leaf multicast-policer {
                        type leafref {
                            path "../../policer/policer-id";
                        }
                        description "Policer identifier to use for multicast traffic";
                    }

                    leaf policer {
                        type leafref {
                            path "../../policer/policer-id";
                        }
                        description "Policer identifier to use for normal traffic";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                } // list fc

                list policer {
                    key "policer-id";
                    description "Enter the policer list instance";

                    leaf policer-id {
                        type types-qos:ingress-policer-id {
                            range "1..16";
                        }
                        description "Network ingress policer identifier";
                    }

                    leaf cbs {
                        type union {
                            type types-qos:bytes {
                                range "128..4161536";
                            }
                            type enumeration {
                                enum "auto"                         { value -1; }
                            }
                        }
                        units "bytes";
                        default "auto";
                        description "Threshold to override CBS for this policer";
                    }

                    leaf mbs {
                        type union {
                            type types-qos:bytes {
                                range "128..4161536";
                            }
                            type enumeration {
                                enum "auto"                         { value -1; }
                            }
                        }
                        units "bytes";
                        default "auto";
                        description "Threshold to override MBS for this policer";
                    }

                    leaf stat-mode {
                        type enumeration {
                            enum "no-stats"                     { value 0; }
                            enum "offered-profile-with-discards" { value 10; }
                        }
                        description "Mode for collecting statistics";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                    container adaptation-rule {
                        description "Enter the adaptation-rule context";

                        leaf pir {
                            type types-qos:adaptation-rule;
                            default "closest";
                            description "Constraint used to derive operational PIR value";
                        }

                        leaf cir {
                            type types-qos:adaptation-rule;
                            default "closest";
                            description "Constraint used to derive operational CIR value";
                        }

                    } // container adaptation-rule

                    container rate {
                        description "Enter the rate context";

                        leaf pir {
                            type union {
                                type uint32 {
                                    range "144..1000000000";
                                }
                                type enumeration {
                                    enum "max"                          { value -1; }
                                }
                            }
                            units "kilobps";
                            default "max";
                            description "Administrative PIR rate";
                        }

                        leaf cir {
                            type union {
                                type uint32 {
                                    range "0..1000000000";
                                }
                                type enumeration {
                                    enum "max"                          { value -1; }
                                }
                            }
                            units "kilobps";
                            default "0";
                            description "Administrative CIR rate";
                        }

                    } // container rate

                } // list policer

            } // list network-ingress

            list sap-egress {
                key "sap-egress-policy-name";
                description "Enter the sap-egress list instance";

                leaf sap-egress-policy-name {
                    type types-qos:qos-policy-name;
                    description "Policy name";
                }

                leaf policy-id {
                    type types-qos:qos-policy-id;
                    sros-ext:immutable;
                    description "Egress SAP QoS policy ID";
                }

                leaf scope {
                    type types-qos:item-scope;
                    default "template";
                    description "Scope of the policy";
                }

                leaf description {
                    type types-sros:description;
                    description "Text description";
                }

                leaf ethernet-ctag {
                    type boolean;
                    default "false";
                    description "Tag value for dot1p and DE (Drop-Eligible) that are used by all dot1-p entries";
                }

                leaf parent-location {
                    type enumeration {
                        enum "auto"                         { value 1; }
                        enum "sla"                          { value 2; }
                    }
                    default "auto";
                    description "Location where queues look to find parent scheduler";
                }

                leaf policers-hqos-manageable {
                    type boolean;
                    default "false";
                    description "Manage policers through the Hierarchical QoS process";
                }

                leaf post-policer-mapping {
                    type leafref {
                        path "../../post-policer-mapping/name";
                    }
                    description "Post policer mapping policy applied to this policy";
                }

                leaf hs-attachment-policy {
                    type leafref {
                        path "../../hs-attachment-policy/name";
                    }
                    description "HS attachment policy applied";
                }

                leaf-list apply-groups {
                    type leafref {
                        path "../../../groups/group/name";
                    }
                    max-elements 8;
                    ordered-by user;
                    description "Apply a configuration group at this level";
                }

                leaf-list apply-groups-exclude {
                    type leafref {
                        path "../../../groups/group/name";
                    }
                    max-elements 8;
                    ordered-by user;
                    description "Exclude a configuration group at this level";
                }

                container subscriber-mgmt {
                    description "Enter the subscriber-mgmt context";

                    container pcc-rule-entry {
                        description "Enter the pcc-rule-entry context";

                        container range {
                            presence "Enable the range context";
                            description "Enable the range context";

                            leaf start {
                                type types-qos:entry-id;
                                mandatory true;
                                description "Lower bound of the filter and QoS policy entries range";
                            }

                            leaf end {
                                type types-qos:entry-id;
                                mandatory true;
                                description "Upper bound of the filter and QoS policy entries range";
                            }

                        } // container range

                    } // container pcc-rule-entry

                    container dynamic-policer {
                        description "Enter the dynamic-policer context";

                        leaf cbs {
                            type types-qos:plcr-burst-size;
                            description "Exceed threshold of the CIR leaky bucket of the policer";
                        }

                        leaf mbs {
                            type types-qos:plcr-burst-size;
                            description "High priority 'violate' threshold of PIR leaky bucket of this policer";
                        }

                        leaf packet-byte-offset {
                            type types-qos:egress-per-packet-offset;
                            default "0";
                            description "Size of each packet, handled by the policer, to be modified";
                        }

                        leaf stat-mode {
                            type enumeration {
                                enum "no-stats"                     { value 0; }
                                enum "minimal"                      { value 1; }
                                enum "offered-profile-no-cir"       { value 2; }
                                enum "offered-total-cir"            { value 3; }
                                enum "offered-profile-cir"          { value 4; }
                                enum "offered-limited-capped-cir"   { value 5; }
                                enum "offered-profile-capped-cir"   { value 6; }
                            }
                            default "minimal";
                            description "Mode of statistics collected by the policer";
                        }

                        container policer-id-range {
                            presence "Enable the policer-id-range context";
                            description "Enable the policer-id-range context";

                            leaf start {
                                type types-qos:ingress-policer-id;
                                mandatory true;
                                description "Lower bound of the dynamic policer ID range";
                            }

                            leaf end {
                                type types-qos:ingress-policer-id;
                                mandatory true;
                                description "Upper bound of the dynamic policer ID range";
                            }

                        } // container policer-id-range

                        container arbiter-parent {
                            description "Enter the arbiter-parent context";

                            leaf arbiter-name {
                                type types-sros:named-item;
                                description "Arbiter name";
                            }

                            leaf level {
                                type types-qos:hierarchy-level;
                                default "1";
                                description "Level of priority while feeding to the parent";
                            }

                            leaf weight {
                                type types-qos:weight {
                                    range "1..100";
                                }
                                default "1";
                                description "Weight to be used by the arbiter for feeding this policer";
                            }

                        } // container arbiter-parent

                    } // container dynamic-policer

                } // container subscriber-mgmt

                container hsmda-queues {
                    status obsolete;
                    description "Enter the hsmda-queues context";

                    leaf low-burst-max-class {
                        status obsolete;
                        type uint32 {
                            range "1..8";
                        }
                        default "8";
                        description "Class that uses low priority burst threshold";
                    }

                    leaf packet-byte-offset {
                        status obsolete;
                        type types-qos:egress-per-packet-offset;
                        default "0";
                        description "Packet byte offset to use for the HSMDA egress queues";
                    }

                    leaf wrr-policy {
                        status obsolete;
                        type leafref {
                            path "../../../hsmda-wrr-policy/hsmda-wrr-policy-name";
                        }
                        description "Weighted Round Robin (WRR) policy";
                    }

                    list queue {
                        status obsolete;
                        key "queue-id";
                        description "Enter the queue list instance";

                        leaf queue-id {
                            status obsolete;
                            type types-qos:egress-queue-id;
                            description "Egress HSMDA queue ID";
                        }

                        leaf burst-limit {
                            status obsolete;
                            type union {
                                type types-qos:bytes {
                                    range "1..1000000";
                                }
                                type enumeration {
                                    enum "auto"                         { value -1; }
                                }
                            }
                            default "auto";
                            description "Explicit shaping burst size of a queue";
                        }

                        leaf mbs {
                            status obsolete;
                            type types-qos:hsmda-queue-burst-size;
                            units "bytes";
                            description "Buffer space allowed for the queue";
                        }

                        leaf rate {
                            status obsolete;
                            type types-qos:hsmda-queue-pir-rate;
                            default "max";
                            description "PIR rate";
                        }

                        leaf slope-policy {
                            status obsolete;
                            type leafref {
                                path "../../../../hsmda-slope-policy/hsmda-slope-policy-name";
                            }
                            description "Name of the slope policy which overrides the default policy for the named buffer pool";
                        }

                        leaf wrr-weight {
                            status obsolete;
                            type types-qos:hsmda-wrr-weight;
                            default "1";
                            description "Weight value for the HSMDA queue";
                        }

                        leaf-list apply-groups {
                            status obsolete;
                            type leafref {
                                path "../../../../../groups/group/name";
                            }
                            max-elements 8;
                            ordered-by user;
                            description "Apply a configuration group at this level";
                        }

                        leaf-list apply-groups-exclude {
                            status obsolete;
                            type leafref {
                                path "../../../../../groups/group/name";
                            }
                            max-elements 8;
                            ordered-by user;
                            description "Exclude a configuration group at this level";
                        }

                        container adaptation-rule {
                            status obsolete;
                            description "Enter the adaptation-rule context";

                            leaf pir {
                                status obsolete;
                                type types-qos:adaptation-rule;
                                default "closest";
                                description "Constraint used when deriving the operational PIR value";
                            }

                        } // container adaptation-rule

                    } // list queue

                } // container hsmda-queues

                list dot1p {
                    key "dot1p-value";
                    description "Enter the dot1p list instance";

                    leaf dot1p-value {
                        type types-qos:dot1p-priority;
                        description "Dot1p value to match in the packet";
                    }

                    leaf fc {
                        type types-sros:fc-name;
                        description "Forwarding class";
                    }

                    leaf profile {
                        type types-qos:egress-profile-de;
                        description "Default profile for the ingressing traffic";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                } // list dot1p

                list dscp {
                    key "dscp-name";
                    description "Enter the dscp list instance";

                    leaf dscp-name {
                        type types-qos:dscp-name;
                        description "DSCP name to perform reclassification actions";
                    }

                    leaf fc {
                        type types-sros:fc-name;
                        description "Forwarding class";
                    }

                    leaf profile {
                        type types-qos:egress-profile;
                        description "Default profile for the ingressing traffic";
                    }

                    leaf hsmda-counter-override {
                        status obsolete;
                        type types-qos:egress-hsmda-counter-id;
                        description "Specifies the counter to use for all the traffic that matches the specific precedence. A value of zero implies that the default counters should be used.";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                } // list dscp

                list prec {
                    key "prec-value";
                    description "Enter the prec list instance";

                    leaf prec-value {
                        type types-qos:precedence-value;
                        description "Precedence value for which mapping is performed";
                    }

                    leaf fc {
                        type types-sros:fc-name;
                        description "Forwarding class";
                    }

                    leaf profile {
                        type types-qos:egress-profile;
                        description "Default profile for the ingressing traffic";
                    }

                    leaf hsmda-counter-override {
                        status obsolete;
                        type types-qos:egress-hsmda-counter-id;
                        description "Specifies the counter to use for all the traffic that matches the specific precedence. A value of zero implies that the default counters should be used.";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                } // list prec

                list queue {
                    key "queue-id";
                    description "Enter the queue list instance";

                    leaf queue-id {
                        type types-qos:egress-queue-id;
                        description "Egress Queue-Group queue identifier";
                    }

                    leaf queue-type {
                        type enumeration {
                            enum "expedited"                    { value 1; }
                            enum "auto-expedited"               { value 2; }
                            enum "best-effort"                  { value 3; }
                        }
                        sros-ext:immutable;
                        default "auto-expedited";
                        description "Priority that this queue receives from the hardware level schedulers";
                    }

                    leaf adv-config-policy {
                        type leafref {
                            path "../../../adv-config-policy/adv-config-policy-name";
                        }
                        description "Name of the advanced configuration policy";
                    }

                    leaf agg-shaper-weight {
                        type types-qos:weight {
                            range "1..100";
                        }
                        default "1";
                        description "Aggregate shaper weight of the sap-egress queue";
                    }

                    leaf avg-frame-overhead {
                        type decimal64 {
                            range "0.00..100.00";
                            fraction-digits 2;
                        }
                        default "0.00";
                        description "Average packet-to-frame encapsulation overhead";
                    }

                    leaf burst-limit {
                        type union {
                            type types-qos:bytes {
                                range "1..14000000";
                            }
                            type enumeration {
                                enum "auto"                         { value -1; }
                            }
                        }
                        default "auto";
                        description "Explicit shaping burst size of a queue";
                    }

                    leaf cbs {
                        type union {
                            type types-qos:bytes {
                                range "0..1048576";
                            }
                            type enumeration {
                                enum "auto"                         { value -1; }
                            }
                        }
                        units "kilobytes";
                        default "auto";
                        description "Reserved buffer space for the queue";
                    }

                    leaf mbs {
                        type union {
                            type types-qos:bytes {
                                range "0..1073741824";
                            }
                            type enumeration {
                                enum "auto"                         { value -1; }
                            }
                        }
                        units "bytes";
                        default "auto";
                        description "Buffer space allowed for the queue";
                    }

                    leaf packet-byte-offset {
                        type int32 {
                            range "-64..32";
                        }
                        default "0";
                        description "Packet byte offset for addition of policing information";
                    }

                    leaf sched-class {
                        type union {
                            type uint32 {
                                range "1..6";
                            }
                            type enumeration {
                                enum "auto"                         { value 0; }
                            }
                        }
                        default "auto";
                        description "Scheduler class for the sap-egress queue";
                    }

                    leaf fir-burst-limit {
                        type union {
                            type types-qos:bytes {
                                range "1..102400";
                            }
                            type enumeration {
                                enum "auto"                         { value -1; }
                            }
                        }
                        default "auto";
                        description "Burst limit for FIR";
                    }

                    leaf hs-alt-port-class-pool {
                        type boolean;
                        default "false";
                        description "Use HS alternate class port pool buffer for traffic";
                    }

                    leaf hs-wrr-weight {
                        type types-qos:hs-wrr-weight;
                        default "1";
                        description "Weighted Round Robin (WRR) weight to parent with this queue into the scheduler";
                    }

                    leaf hs-class-weight {
                        type types-qos:hs-class-weight;
                        default "1";
                        description "Scheduling class weight";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                    choice rate-or-percent-rate {
                        default "rate";
                        case rate {

                            container rate {
                                description "Enter the rate context";

                                leaf pir {
                                    type types-qos:queue-pir-rate-maximum;
                                    units "kilobps";
                                    default "max";
                                    description "Administrative PIR";
                                }

                                leaf cir {
                                    type types-qos:queue-cir-rate-maximum;
                                    units "kilobps";
                                    default "0";
                                    description "Administrative CIR";
                                }

                            } // container rate

                        }
                        case percent-rate {

                            container percent-rate {
                                description "Enter the percent-rate context";

                                leaf pir {
                                    type decimal64 {
                                        range "0.01..100.00";
                                        fraction-digits 2;
                                    }
                                    description "Administrative PIR percent";
                                }

                                leaf cir {
                                    type decimal64 {
                                        range "0.00..100.00";
                                        fraction-digits 2;
                                    }
                                    default "0.00";
                                    description "Administrative CIR percent";
                                }

                                leaf reference-rate {
                                    type enumeration {
                                        enum "port-limit"                   { value 2; }
                                        enum "local-limit"                  { value 3; }
                                        enum "reference-port-limit"         { value 4; }
                                    }
                                    default "port-limit";
                                    description "Reference rate";
                                }

                            } // container percent-rate

                        }
                    }
                    choice parent-mapping {
                        case scheduler-parent {

                            container scheduler-parent {
                                presence "Enable the scheduler-parent context";
                                description "Enable the scheduler-parent context";

                                leaf scheduler-name {
                                    type types-sros:named-item;
                                    mandatory true;
                                    description "Parent scheduler name";
                                }

                                leaf level {
                                    type types-qos:hierarchy-level;
                                    default "1";
                                    description "Level of priority while feeding to the parent";
                                }

                                leaf weight {
                                    type types-qos:weight;
                                    default "1";
                                    description "Weight to be used by the scheduler for feeding this queue";
                                }

                                leaf cir-level {
                                    type types-qos:cir-level;
                                    default "0";
                                    description "Level of priority while feeding to the parent";
                                }

                                leaf cir-weight {
                                    type types-qos:cir-weight;
                                    default "1";
                                    description "Weight that is used by the scheduler until the committed rate for feeding this queue";
                                }

                            } // container scheduler-parent

                        }
                        case port-parent {

                            container port-parent {
                                presence "Enable the port-parent context";
                                description "Enable the port-parent context";

                                leaf level {
                                    type types-qos:hierarchy-level;
                                    default "1";
                                    description "Port priority that this queue uses to receive bandwidth from the port level scheduler";
                                }

                                leaf weight {
                                    type types-qos:weight;
                                    default "1";
                                    description "Weight that this queue uses to receive bandwidth from the port level scheduler";
                                }

                                leaf cir-level {
                                    type types-qos:cir-level;
                                    default "0";
                                    description "Port priority that this queue uses to receive bandwidth from the port level scheduler";
                                }

                                leaf cir-weight {
                                    type types-qos:cir-weight;
                                    default "0";
                                    description "Weight that this queue uses to receive bandwidth from the port level scheduler";
                                }

                            } // container port-parent

                        }
                    }
                    container adaptation-rule {
                        description "Enter the adaptation-rule context";

                        leaf pir {
                            type types-qos:adaptation-rule;
                            default "closest";
                            description "Constraint used when deriving the operational PIR value";
                        }

                        leaf cir {
                            type types-qos:adaptation-rule;
                            default "closest";
                            description "Constraint used when deriving the operational CIR value";
                        }

                    } // container adaptation-rule

                    container wred-queue {
                        description "Enter the wred-queue context";

                        leaf policy {
                            type leafref {
                                path "../../../../slope-policy/slope-policy-name";
                            }
                            description "Slope policy name";
                        }

                        leaf mode {
                            type enumeration {
                                enum "native"                       { value 1; }
                                enum "pool-per-queue"               { value 2; }
                            }
                            description "Generic pool association of the queue to allow queue-specific WRED slopes";
                        }

                        leaf usage {
                            type types-qos:wred-queue-slope-usage;
                            description "Congestion control type";
                        }

                    } // container wred-queue

                    container drop-tail {
                        description "Enter the drop-tail context";

                        container highplus {
                            description "Enter the highplus context";

                            leaf percent-reduction-from-mbs {
                                type types-qos:burst-percent;
                                description "Percentage of drop-tail being that is reduced from MBS for high plus profile packets";
                            }

                        } // container highplus

                        container high {
                            description "Enter the high context";

                            leaf percent-reduction-from-mbs {
                                type types-qos:burst-percent;
                                description "Percentage of drop-tail being that is reduced from MBS for high profile packets";
                            }

                        } // container high

                        container low {
                            description "Enter the low context";

                            leaf percent-reduction-from-mbs {
                                type types-qos:burst-percent;
                                description "Low drop-tail percent from MBS that is reduced";
                            }

                        } // container low

                        container exceed {
                            description "Enter the exceed context";

                            leaf percent-reduction-from-mbs {
                                type types-qos:burst-percent;
                                description "Percentage of drop-tail that is reduced from MBS for exceed profile packets";
                            }

                        } // container exceed

                    } // container drop-tail

                    container hs-wred-queue {
                        description "Enter the hs-wred-queue context";

                        leaf policy {
                            type leafref {
                                path "../../../../slope-policy/slope-policy-name";
                            }
                            description "Slope policy name";
                        }

                    } // container hs-wred-queue

                } // list queue

                list policer {
                    key "policer-id";
                    description "Enter the policer list instance";

                    leaf policer-id {
                        type types-qos:sap-egress-policer-id;
                        description "SAP egress policer ID";
                    }

                    leaf description {
                        type types-sros:description;
                        description "Text description";
                    }

                    leaf adv-config-policy {
                        type leafref {
                            path "../../../adv-config-policy/adv-config-policy-name";
                        }
                        description "Name of the advanced configuration policy to apply with this queue";
                    }

                    leaf cbs {
                        type types-qos:plcr-burst-size;
                        description "Exceed threshold of the CIR leaky bucket of the policer";
                    }

                    leaf dscp-prec-remarking {
                        type boolean;
                        default "false";
                        description "Remark DSCP and precedence based on the profile state of a forwarding packet";
                    }

                    leaf exceed-pir {
                        type boolean;
                        default "false";
                        description "Allow forwarding of packets with an exceed-profile state and traffic exceeding the PIR";
                    }

                    leaf high-prio-only {
                        type types-qos:burst-percent;
                        description "Percentage of PIR leaky bucket's MBS of this policer that is reserved for high priority traffic";
                    }

                    leaf mbs {
                        type types-qos:plcr-burst-size;
                        description "High priority 'violate' threshold of PIR leaky bucket of this policer";
                    }

                    leaf packet-byte-offset {
                        type types-qos:egress-per-packet-offset;
                        default "0";
                        description "Size of each packet, handled by the policer, to be modified";
                    }

                    leaf profile-capped {
                        type boolean;
                        default "false";
                        description "Enforce an overall in-profile burst limit to the CIR bucket at egress policer";
                    }

                    leaf profile-out-preserve {
                        type boolean;
                        default "false";
                        description "Preserve the color of offered out-of-profile traffic at SAP-egress policer";
                    }

                    leaf stat-mode {
                        type types-qos:egress-policer-stat-mode;
                        default "minimal";
                        description "Mode of statistics collected by the policer";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                    choice rate-or-percent-rate {
                        default "rate";
                        case rate {

                            container rate {
                                description "Enter the rate context";

                                leaf pir {
                                    type types-qos:policer-pir-rate-maximum;
                                    units "kilobps";
                                    default "max";
                                    description "Administrative PIR";
                                }

                                leaf cir {
                                    type types-qos:policer-cir-rate-maximum;
                                    units "kilobps";
                                    default "0";
                                    description "Administrative CIR";
                                }

                            } // container rate

                        }
                        case percent-rate {

                            container percent-rate {
                                description "Enter the percent-rate context";

                                leaf pir {
                                    type decimal64 {
                                        range "0.01..100.00";
                                        fraction-digits 2;
                                    }
                                    description "Administrative PIR percent";
                                }

                                leaf cir {
                                    type decimal64 {
                                        range "0.00..100.00";
                                        fraction-digits 2;
                                    }
                                    default "0.00";
                                    description "Administrative CIR percent";
                                }

                                leaf reference-rate {
                                    type enumeration {
                                        enum "local-limit"                  { value 2; }
                                        enum "reference-port-limit"         { value 3; }
                                    }
                                    default "local-limit";
                                    description "Reference rate";
                                }

                            } // container percent-rate

                        }
                    }
                    choice parent-mapping {
                        case scheduler-parent {

                            container scheduler-parent {
                                presence "Enable the scheduler-parent context";
                                description "Enter the scheduler-parent context";

                                leaf scheduler-name {
                                    type types-sros:named-item;
                                    mandatory true;
                                    description "Scheduler name";
                                }

                                leaf level {
                                    type types-qos:hierarchy-level;
                                    default "1";
                                    description "Priority level for bandwidth on the parent scheduler";
                                }

                                leaf weight {
                                    type types-qos:weight;
                                    default "1";
                                    description "Policer weight at the above-CIR priority level";
                                }

                                leaf cir-level {
                                    type types-qos:cir-level;
                                    default "0";
                                    description "Port priority level for within-CIR offered load";
                                }

                                leaf cir-weight {
                                    type types-qos:cir-weight;
                                    default "1";
                                    description "Weight to use in the within-CIR port priority level";
                                }

                            } // container scheduler-parent

                        }
                        case port-parent {

                            container port-parent {
                                presence "Enable the port-parent context";
                                description "Enter the port-parent context";

                                leaf level {
                                    type types-qos:hierarchy-level;
                                    default "1";
                                    description "Port priority level for above-CIR behavior";
                                }

                                leaf weight {
                                    type types-qos:weight;
                                    default "1";
                                    description "Weight to use in the above-CIR port priority level";
                                }

                                leaf cir-level {
                                    type types-qos:cir-level;
                                    default "0";
                                    description "Port priority level for within-CIR offered load";
                                }

                                leaf cir-weight {
                                    type types-qos:cir-weight;
                                    default "0";
                                    description "Weight to use in the within-CIR port priority level";
                                }

                            } // container port-parent

                        }
                    }
                    container adaptation-rule {
                        description "Enter the adaptation-rule context";

                        leaf pir {
                            type types-qos:adaptation-rule;
                            default "closest";
                            description "Constraint used when deriving the operational PIR value";
                        }

                        leaf cir {
                            type types-qos:adaptation-rule;
                            default "closest";
                            description "Constraint used when deriving the operational CIR value";
                        }

                    } // container adaptation-rule

                    container arbiter-parent {
                        description "Enter the arbiter-parent context";

                        leaf arbiter-name {
                            type types-sros:named-item;
                            description "Arbiter name";
                        }

                        leaf level {
                            type types-qos:hierarchy-level;
                            default "1";
                            description "Level of priority while feeding to the parent";
                        }

                        leaf weight {
                            type types-qos:weight {
                                range "1..100";
                            }
                            default "1";
                            description "Weight to be used by the arbiter for feeding this policer";
                        }

                    } // container arbiter-parent

                } // list policer

                list fc {
                    key "fc-name";
                    description "Enter the fc list instance";

                    leaf fc-name {
                        type types-sros:fc-name;
                        description "Forwarding class";
                    }

                    leaf policer {
                        type leafref {
                            path "../../policer/policer-id";
                        }
                        description "Policer to forward the traffic";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                    choice dscp-or-prec {
                        case dscp {

                            container dscp {
                                description "Enter the dscp context";

                                leaf in-profile {
                                    type types-qos:dscp-name;
                                    description "DSCP name for in-profile frames";
                                }

                                leaf out-profile {
                                    type types-qos:dscp-name;
                                    description "DSCP name for out-of-profile frames";
                                }

                                leaf exceed-profile {
                                    type types-qos:dscp-name;
                                    description "DSCP name for exceed-profile frames";
                                }

                            } // container dscp

                        }
                        case prec {

                            container prec {
                                description "Enter the prec context";

                                leaf in-profile {
                                    type types-qos:precedence-value;
                                    description "Precedence value for in-profile frames";
                                }

                                leaf out-profile {
                                    type types-qos:precedence-value;
                                    description "Precedence value for out-of-profile frames";
                                }

                                leaf exceed-profile {
                                    type types-qos:precedence-value;
                                    description "Precedence for exceed-profile frames";
                                }

                            } // container prec

                        }
                    }
                    choice queue-redirection-mapping {
                        case queue {

                            leaf queue {
                                type leafref {
                                    path "../../queue/queue-id";
                                }
                                description "Queue to forward the traffic";
                            }

                        }
                        case port-redirect-group-queue {

                            container port-redirect-group-queue {
                                presence "Enable the port-redirect-group-queue context";
                                description "Enable the port-redirect-group-queue context";

                                leaf queue {
                                    type types-qos:egress-queue-id;
                                    description "Queue to forward the traffic";
                                }

                            } // container port-redirect-group-queue

                        }
                        case queue-group-queue {

                            container queue-group-queue {
                                presence "Enable the queue-group-queue context";
                                description "Enable the queue-group-queue context";

                                leaf queue-group-name {
                                    type leafref {
                                        path "../../../../queue-group-templates/egress/queue-group/egress-queue-group-name";
                                    }
                                    mandatory true;
                                    description "Queue group to forward traffic";
                                }

                                leaf queue {
                                    type leafref {
                                        path "../../../../queue-group-templates/egress/queue-group[egress-queue-group-name=current()/../queue-group-name]/queue/queue-id";
                                    }
                                    description "SAP egress queue ID";
                                }

                                leaf instance {
                                    type uint32 {
                                        range "1..65535";
                                    }
                                    description "Instance ID";
                                }

                            } // container queue-group-queue

                        }
                    }
                    container de-mark {
                        presence "Enable the de-mark context";
                        description "Enable the de-mark context";

                        leaf force {
                            type types-qos:de-value;
                            description "DE value";
                        }

                    } // container de-mark

                    container de-mark-inner {
                        presence "Enable the de-mark-inner context";
                        description "Enable the de-mark-inner context";

                        leaf force {
                            type types-qos:de-value;
                            description "DE value to set in inner VLAN tag";
                        }

                    } // container de-mark-inner

                    container de-mark-outer {
                        presence "Enable the de-mark-outer context";
                        description "Enable the de-mark-outer context";

                        leaf force {
                            type types-qos:de-value;
                            description "DE value to set in outer VLAN tag";
                        }

                    } // container de-mark-outer

                    container dot1p {
                        description "Enter the dot1p context";

                        leaf in-profile {
                            type types-qos:dot1p-priority;
                            description "Dot1p value for in-profile frames";
                        }

                        leaf out-profile {
                            type types-qos:dot1p-priority;
                            description "Dot1p value for out-of-profile frames";
                        }

                        leaf exceed-profile {
                            type types-qos:dot1p-priority;
                            description "Dot1p value for exceed-profile frames";
                        }

                    } // container dot1p

                    container dot1p-inner {
                        description "Enter the dot1p-inner context";

                        leaf in-profile {
                            type types-qos:dot1p-priority;
                            description "Inner Dot1p value for in-profile frames";
                        }

                        leaf out-profile {
                            type types-qos:dot1p-priority;
                            description "Inner Dot1p value for out-of-profile frames";
                        }

                    } // container dot1p-inner

                    container dot1p-outer {
                        description "Enter the dot1p-outer context";

                        leaf in-profile {
                            type types-qos:dot1p-priority;
                            description "Outer Dot1p value for in-profile frames";
                        }

                        leaf out-profile {
                            type types-qos:dot1p-priority;
                            description "Outer Dot1p value for out-of-profile frames";
                        }

                        leaf exceed-profile {
                            type types-qos:dot1p-priority;
                            description "Outer Dot1p value for exceed-profile frames";
                        }

                    } // container dot1p-outer

                    container hsmda {
                        status obsolete;
                        description "Enter the hsmda context";

                        choice hsmda-queue-redirection-mapping {
                            status obsolete;
                            case queue {
                                status obsolete;

                                leaf queue {
                                    status obsolete;
                                    type leafref {
                                        path "../../../hsmda-queues/queue/queue-id";
                                    }
                                    description "HSMDA queue to which traffic is forwarded";
                                }

                            }
                            case port-redirect-group-queue {
                                status obsolete;

                                container port-redirect-group-queue {
                                    status obsolete;
                                    presence "Enable the port-redirect-group-queue context";
                                    description "Enable the port-redirect-group-queue context";

                                    leaf queue {
                                        status obsolete;
                                        type leafref {
                                            path "../../../../hsmda-queues/queue/queue-id";
                                        }
                                        mandatory true;
                                        description "HSMDA queue to which traffic is forwarded";
                                    }

                                } // container port-redirect-group-queue

                            }
                        }
                    } // container hsmda

                } // list fc

                list hs-wrr-group {
                    key "group-id";
                    description "Enter the hs-wrr-group list instance";

                    leaf group-id {
                        type types-qos:hs-wrr-group-id;
                        description "HS WRR group identifier";
                    }

                    leaf hs-class-weight {
                        type types-qos:hs-class-weight;
                        default "1";
                        description "Weight of scheduling class";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                    choice rate-or-percent-rate {
                        default "rate";
                        case rate {

                            leaf rate {
                                type union {
                                    type uint32 {
                                        range "1..2000000000";
                                    }
                                    type enumeration {
                                        enum "max"                          { value -1; }
                                    }
                                }
                                units "kilobps";
                                default "max";
                                description "Administrative PIR";
                            }

                        }
                        case percent-rate {

                            leaf percent-rate {
                                type decimal64 {
                                    range "0.01..100.00";
                                    fraction-digits 2;
                                }
                                description "Administrative PIR percent";
                            }

                        }
                    }
                    container adaptation-rule {
                        description "Enter the adaptation-rule context";

                        leaf pir {
                            type types-qos:adaptation-rule;
                            default "closest";
                            description "Constraint used when deriving the operational PIR value";
                        }

                    } // container adaptation-rule

                } // list hs-wrr-group

                container ip-criteria {
                    description "Enter the ip-criteria context";

                    list entry {
                        key "entry-id";
                        description "Enter the entry list instance";

                        leaf entry-id {
                            type uint32 {
                                range "1..65535";
                            }
                            description "IP Criteria Entry Index";
                        }

                        leaf description {
                            type types-sros:description;
                            description "Text description";
                        }

                        leaf-list apply-groups {
                            type leafref {
                                path "../../../../../groups/group/name";
                            }
                            max-elements 8;
                            ordered-by user;
                            description "Apply a configuration group at this level";
                        }

                        leaf-list apply-groups-exclude {
                            type leafref {
                                path "../../../../../groups/group/name";
                            }
                            max-elements 8;
                            ordered-by user;
                            description "Exclude a configuration group at this level";
                        }

                        container match {
                            description "Enter the match context";

                            leaf protocol {
                                type types-sros:match-ip-protocol;
                                description "IP protocol to match";
                            }

                            leaf dscp {
                                type types-qos:dscp-name;
                                description "DSCP value to match in the packet";
                            }

                            leaf fragment {
                                type enumeration {
                                    enum "false"                        { value 2; }
                                    enum "true"                         { value 3; }
                                }
                                description "Matching criteria to be used for fragmented or non-fragmented packets";
                            }

                            container src-port {
                                description "Enter the src-port context";

                                choice port-match-mapping {
                                    case lt {

                                        leaf lt {
                                            type int32 {
                                                range "0..65535";
                                            }
                                            description "Value 'less than' as match condition";
                                        }

                                    }
                                    case eq {

                                        leaf eq {
                                            type int32 {
                                                range "0..65535";
                                            }
                                            description "Value 'equal to' as match condition";
                                        }

                                    }
                                    case gt {

                                        leaf gt {
                                            type int32 {
                                                range "0..65535";
                                            }
                                            description "Value 'greater than' as match condition";
                                        }

                                    }
                                    case range {

                                        container range {
                                            description "Enter the range context";

                                            leaf start {
                                                type int32 {
                                                    range "0..65535";
                                                }
                                                description "Lower bound of the port range";
                                            }

                                            leaf end {
                                                type int32 {
                                                    range "0..65535";
                                                }
                                                description "Upper bound of the port range";
                                            }

                                        } // container range

                                    }
                                }
                            } // container src-port

                            container dst-port {
                                description "Enter the dst-port context";

                                choice port-match-mapping {
                                    case lt {

                                        leaf lt {
                                            type int32 {
                                                range "0..65535";
                                            }
                                            description "Value 'less than' as match condition";
                                        }

                                    }
                                    case eq {

                                        leaf eq {
                                            type int32 {
                                                range "0..65535";
                                            }
                                            description "Value 'equal to' as match condition";
                                        }

                                    }
                                    case gt {

                                        leaf gt {
                                            type int32 {
                                                range "0..65535";
                                            }
                                            description "Value 'greater than' as match condition";
                                        }

                                    }
                                    case range {

                                        container range {
                                            description "Enter the range context";

                                            leaf start {
                                                type int32 {
                                                    range "0..65535";
                                                }
                                                description "Lower bound of the port range";
                                            }

                                            leaf end {
                                                type int32 {
                                                    range "0..65535";
                                                }
                                                description "Upper bound of the port range";
                                            }

                                        } // container range

                                    }
                                }
                            } // container dst-port

                            container src-ip {
                                description "Enter the src-ip context";

                                choice src-ip {
                                    case address-and-mask-or-prefix {

                                        leaf address {
                                            type union {
                                                type types-sros:ipv4-address;
                                                type types-sros:ipv4-prefix-with-host-bits;
                                            }
                                            description "Source IPv4 address for SAP QoS policy match criterion";
                                        }

                                        leaf mask {
                                            type types-sros:ipv4-address;
                                            description "IP address mask to match with source IP of the packet";
                                        }

                                    }
                                    case ip-prefix-list {

                                        leaf ip-prefix-list {
                                            type leafref {
                                                path "../../../../../../match-list/ip-prefix-list/prefix-list-name";
                                            }
                                            description "List of IPv4 prefixes for the match criteria";
                                        }

                                    }
                                }
                            } // container src-ip

                            container dst-ip {
                                description "Enter the dst-ip context";

                                choice dst-ip {
                                    case address-and-mask-or-prefix {

                                        leaf address {
                                            type union {
                                                type types-sros:ipv4-address;
                                                type types-sros:ipv4-prefix-with-host-bits;
                                            }
                                            description "Destination IPv4 address for SAP QoS policy match";
                                        }

                                        leaf mask {
                                            type types-sros:ipv4-address;
                                            description "IP address mask to match with source IP of the packet";
                                        }

                                    }
                                    case ip-prefix-list {

                                        leaf ip-prefix-list {
                                            type leafref {
                                                path "../../../../../../match-list/ip-prefix-list/prefix-list-name";
                                            }
                                            description "List of IPv4 prefixes for the match criteria";
                                        }

                                    }
                                }
                            } // container dst-ip

                        } // container match

                        container action {
                            description "Enter the action context";

                            leaf type {
                                type types-qos:criteria-action-type;
                                default "ignore-match";
                                description "Action for criteria entry";
                            }

                            leaf fc {
                                type types-sros:fc-name;
                                description "Forwarding class";
                            }

                            leaf profile {
                                type types-qos:egress-profile;
                                description "Default profile for the matching traffic";
                            }

                            leaf hsmda-counter-override {
                                status obsolete;
                                type uint32 {
                                    range "1..8";
                                }
                                description "HSMDA counter to use for matching packets";
                            }

                            leaf policer {
                                type leafref {
                                    path "../../../../policer/policer-id";
                                }
                                description "Policer identifier for the matched traffic";
                            }

                            leaf port-redirect-group-queue {
                                type boolean;
                                default "false";
                                description "Use the queue specified in egress access port queue-group instance";
                            }

                            leaf queue {
                                type types-qos:egress-queue-id;
                                description "Queue to use when the matched traffic is policed by the local policer";
                            }

                            leaf use-fc-mapped-queue {
                                type boolean;
                                default "false";
                                description "Redirect policer output to the configured queues";
                            }

                        } // container action

                    } // list entry

                } // container ip-criteria

                container ipv6-criteria {
                    description "Enter the ipv6-criteria context";

                    list entry {
                        key "entry-id";
                        description "Enter the entry list instance";

                        leaf entry-id {
                            type uint32 {
                                range "1..65535";
                            }
                            description "IP Criteria Entry Index";
                        }

                        leaf description {
                            type types-sros:description;
                            description "Text description";
                        }

                        leaf-list apply-groups {
                            type leafref {
                                path "../../../../../groups/group/name";
                            }
                            max-elements 8;
                            ordered-by user;
                            description "Apply a configuration group at this level";
                        }

                        leaf-list apply-groups-exclude {
                            type leafref {
                                path "../../../../../groups/group/name";
                            }
                            max-elements 8;
                            ordered-by user;
                            description "Exclude a configuration group at this level";
                        }

                        container match {
                            description "Enter the match context";

                            leaf next-header {
                                type types-sros:match-ip-protocol;
                                description "IP protocol to match";
                            }

                            leaf dscp {
                                type types-qos:dscp-name;
                                description "DSCP value to match in the packet";
                            }

                            container src-port {
                                description "Enter the src-port context";

                                choice port-match-mapping {
                                    case lt {

                                        leaf lt {
                                            type int32 {
                                                range "0..65535";
                                            }
                                            description "Value 'less than' as match condition";
                                        }

                                    }
                                    case eq {

                                        leaf eq {
                                            type int32 {
                                                range "0..65535";
                                            }
                                            description "Value 'equal to' as match condition";
                                        }

                                    }
                                    case gt {

                                        leaf gt {
                                            type int32 {
                                                range "0..65535";
                                            }
                                            description "Value 'greater than' as match condition";
                                        }

                                    }
                                    case range {

                                        container range {
                                            description "Enter the range context";

                                            leaf start {
                                                type int32 {
                                                    range "0..65535";
                                                }
                                                description "Lower bound of the port range";
                                            }

                                            leaf end {
                                                type int32 {
                                                    range "0..65535";
                                                }
                                                description "Upper bound of the port range";
                                            }

                                        } // container range

                                    }
                                }
                            } // container src-port

                            container dst-port {
                                description "Enter the dst-port context";

                                choice port-match-mapping {
                                    case lt {

                                        leaf lt {
                                            type int32 {
                                                range "0..65535";
                                            }
                                            description "Value 'less than' as match condition";
                                        }

                                    }
                                    case eq {

                                        leaf eq {
                                            type int32 {
                                                range "0..65535";
                                            }
                                            description "Value 'equal to' as match condition";
                                        }

                                    }
                                    case gt {

                                        leaf gt {
                                            type int32 {
                                                range "0..65535";
                                            }
                                            description "Value 'greater than' as match condition";
                                        }

                                    }
                                    case range {

                                        container range {
                                            description "Enter the range context";

                                            leaf start {
                                                type int32 {
                                                    range "0..65535";
                                                }
                                                description "Lower bound of the port range";
                                            }

                                            leaf end {
                                                type int32 {
                                                    range "0..65535";
                                                }
                                                description "Upper bound of the port range";
                                            }

                                        } // container range

                                    }
                                }
                            } // container dst-port

                            container src-ip {
                                description "Enter the src-ip context";

                                choice src-ip {
                                    case address-and-mask-or-prefix {

                                        leaf address {
                                            type union {
                                                type types-sros:ipv6-address;
                                                type types-sros:ipv6-prefix-with-host-bits;
                                            }
                                            description "Source IPv6 address for SAP QoS policy match";
                                        }

                                        leaf mask {
                                            type types-sros:ipv6-address;
                                            description "IP address mask to match with source IP of the packet";
                                        }

                                    }
                                    case ipv6-prefix-list {

                                        leaf ipv6-prefix-list {
                                            type leafref {
                                                path "../../../../../../match-list/ipv6-prefix-list/prefix-list-name";
                                            }
                                            description "IPv6 prefix list as match criterion for IPv6 addresses";
                                        }

                                    }
                                }
                            } // container src-ip

                            container dst-ip {
                                description "Enter the dst-ip context";

                                choice dst-ip {
                                    case address-and-mask-or-prefix {

                                        leaf address {
                                            type union {
                                                type types-sros:ipv6-address;
                                                type types-sros:ipv6-prefix-with-host-bits;
                                            }
                                            description "Destination IPv6 address for SAP QoS policy match";
                                        }

                                        leaf mask {
                                            type types-sros:ipv6-address;
                                            description "IP address mask to match with destination IP of the packet";
                                        }

                                    }
                                    case ipv6-prefix-list {

                                        leaf ipv6-prefix-list {
                                            type leafref {
                                                path "../../../../../../match-list/ipv6-prefix-list/prefix-list-name";
                                            }
                                            description "IPv6 prefix list as match criterion for IPv6 addresses";
                                        }

                                    }
                                }
                            } // container dst-ip

                        } // container match

                        container action {
                            description "Enter the action context";

                            leaf type {
                                type types-qos:criteria-action-type;
                                default "ignore-match";
                                description "Action for criteria entry";
                            }

                            leaf fc {
                                type types-sros:fc-name;
                                description "Forwarding class";
                            }

                            leaf profile {
                                type types-qos:egress-profile;
                                description "Default profile for the matching traffic";
                            }

                            leaf hsmda-counter-override {
                                status obsolete;
                                type uint32 {
                                    range "1..8";
                                }
                                description "HSMDA counter to use for matching packets";
                            }

                            leaf policer {
                                type leafref {
                                    path "../../../../policer/policer-id";
                                }
                                description "Policer identifier for the matched traffic";
                            }

                            leaf port-redirect-group-queue {
                                type boolean;
                                default "false";
                                description "Use the queue specified in egress access port queue-group instance";
                            }

                            leaf queue {
                                type types-qos:egress-queue-id;
                                description "Queue to use when the matched traffic is policed by the local policer";
                            }

                            leaf use-fc-mapped-queue {
                                type boolean;
                                default "false";
                                description "Redirect policer output to the configured queues";
                            }

                        } // container action

                    } // list entry

                } // container ipv6-criteria

                container sched-class-elevation {
                    description "Enter the sched-class-elevation context";

                    list sched-class {
                        key "class-id";
                        description "Enter the sched-class list instance";

                        leaf class-id {
                            type uint32 {
                                range "1..6";
                            }
                            description "Scheduling class associated with this SAP egress";
                        }

                        leaf weight {
                            type uint32 {
                                range "1..8";
                            }
                            default "1";
                            description "Weight of the schedule class";
                        }

                        leaf-list apply-groups {
                            type leafref {
                                path "../../../../../groups/group/name";
                            }
                            max-elements 8;
                            ordered-by user;
                            description "Apply a configuration group at this level";
                        }

                        leaf-list apply-groups-exclude {
                            type leafref {
                                path "../../../../../groups/group/name";
                            }
                            max-elements 8;
                            ordered-by user;
                            description "Exclude a configuration group at this level";
                        }

                    } // list sched-class

                } // container sched-class-elevation

            } // list sap-egress

            list scheduler-policy {
                key "scheduler-policy-name";
                max-elements 2047;
                description "Enter the scheduler-policy list instance";

                leaf scheduler-policy-name {
                    type types-sros:named-item;
                    description "Scheduler policy name";
                }

                leaf description {
                    type types-sros:description;
                    description "Text description";
                }

                leaf frame-based-accounting {
                    type boolean;
                    default "false";
                    description "Use frame-based accounting for schedulers and children within scheduler policy";
                }

                leaf-list apply-groups {
                    type leafref {
                        path "../../../groups/group/name";
                    }
                    max-elements 8;
                    ordered-by user;
                    description "Apply a configuration group at this level";
                }

                leaf-list apply-groups-exclude {
                    type leafref {
                        path "../../../groups/group/name";
                    }
                    max-elements 8;
                    ordered-by user;
                    description "Exclude a configuration group at this level";
                }

                list tier {
                    key "tier-id";
                    description "Enter the tier list instance";

                    leaf tier-id {
                        type int32 {
                            range "1..3";
                        }
                        description "Tier for scheduler-policy scheduler";
                    }

                    leaf parent-location {
                        type enumeration {
                            enum "auto"                         { value 1; }
                            enum "sub"                          { value 2; }
                            enum "vport"                        { value 3; }
                        }
                        default "auto";
                        description "Location in which the tier 1 schedulers can find their parent";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                    list scheduler {
                        key "scheduler-name";
                        description "Enter the scheduler list instance";

                        leaf scheduler-name {
                            type types-sros:named-item;
                            description "Scheduler name";
                        }

                        leaf description {
                            type types-sros:description;
                            description "Text description";
                        }

                        leaf limit-unused-bandwidth {
                            type boolean;
                            default "false";
                            description "Enable aggregate rate overrun protection";
                        }

                        leaf-list apply-groups {
                            type leafref {
                                path "../../../../../groups/group/name";
                            }
                            max-elements 8;
                            ordered-by user;
                            description "Apply a configuration group at this level";
                        }

                        leaf-list apply-groups-exclude {
                            type leafref {
                                path "../../../../../groups/group/name";
                            }
                            max-elements 8;
                            ordered-by user;
                            description "Exclude a configuration group at this level";
                        }

                        choice rate-or-percent-rate {
                            default "rate";
                            case rate {

                                container rate {
                                    description "Enter the rate context";

                                    leaf pir {
                                        type types-qos:sched-pir-rate;
                                        units "kilobps";
                                        default "max";
                                        description "Administrative PIR";
                                    }

                                    leaf cir {
                                        type types-qos:sched-cir-rate;
                                        units "kilobps";
                                        default "sum";
                                        description "Administrative CIR";
                                    }

                                } // container rate

                            }
                            case percent-rate {

                                container percent-rate {
                                    description "Enter the percent-rate context";

                                    leaf pir {
                                        type decimal64 {
                                            range "0.01..100.00";
                                            fraction-digits 2;
                                        }
                                        description "Scheduler PIR";
                                    }

                                    leaf cir {
                                        type types-qos:sched-cir-percent-rate;
                                        default "sum";
                                        description "Scheduler CIR";
                                    }

                                    leaf reference-rate {
                                        type enumeration {
                                            enum "local-limit"                  { value 2; }
                                            enum "reference-port-limit"         { value 3; }
                                        }
                                        default "reference-port-limit";
                                        description "Reference rate";
                                    }

                                } // container percent-rate

                            }
                        }
                        choice parent-mapping {
                            case scheduler-parent {

                                container scheduler-parent {
                                    presence "Enable the scheduler-parent context";
                                    description "Enable the scheduler-parent context";

                                    leaf scheduler-name {
                                        type types-sros:named-item;
                                        mandatory true;
                                        description "Scheduler name";
                                    }

                                    leaf level {
                                        type types-qos:hierarchy-level;
                                        default "1";
                                        description "Level of priority while feeding to the parent";
                                    }

                                    leaf weight {
                                        type types-qos:weight;
                                        default "1";
                                        description "Weight to be used by the scheduler for feeding this queue";
                                    }

                                    leaf cir-level {
                                        type types-qos:cir-level;
                                        default "0";
                                        description "Level of priority while feeding to the parent";
                                    }

                                    leaf cir-weight {
                                        type types-qos:cir-weight;
                                        default "1";
                                        description "Weight that is used by the scheduler until the committed rate for feeding this queue";
                                    }

                                } // container scheduler-parent

                            }
                            case port-parent {

                                container port-parent {
                                    presence "Enable the port-parent context";
                                    description "Enable the port-parent context";

                                    leaf level {
                                        type types-qos:hierarchy-level;
                                        default "1";
                                        description "Port priority that this queue uses to receive bandwidth from the port level scheduler";
                                    }

                                    leaf weight {
                                        type types-qos:weight;
                                        default "1";
                                        description "Weight that this queue uses to receive bandwidth from the port level scheduler";
                                    }

                                    leaf cir-level {
                                        type types-qos:cir-level;
                                        default "0";
                                        description "Port priority that this queue uses to receive bandwidth from the port level scheduler";
                                    }

                                    leaf cir-weight {
                                        type types-qos:cir-weight;
                                        default "0";
                                        description "Weight that this queue uses to receive bandwidth from the port level scheduler";
                                    }

                                } // container port-parent

                            }
                        }
                    } // list scheduler

                } // list tier

            } // list scheduler-policy

            list port-scheduler-policy {
                key "name";
                max-elements 1023;
                description "Enter the port-scheduler-policy list instance";

                leaf name {
                    type types-sros:named-item;
                    description "Port scheduler policy name";
                }

                leaf description {
                    type types-sros:description;
                    description "Text description";
                }

                leaf dist-lag-rate-shared {
                    type boolean;
                    default "false";
                    description "Share rates when the port is part of a LAG configured in distribute mode";
                }

                leaf monitor-threshold {
                    type uint32 {
                        range "0..100";
                    }
                    default "0";
                    description "Congestion monitoring threshold";
                }

                leaf hqos-algorithm {
                    type enumeration {
                        enum "default"                      { value 1; }
                        enum "above-offered-allowance-control" { value 2; }
                    }
                    default "default";
                    description "Port scheduler H-QoS algorithm";
                }

                leaf-list apply-groups {
                    type leafref {
                        path "../../../groups/group/name";
                    }
                    max-elements 8;
                    ordered-by user;
                    description "Apply a configuration group at this level";
                }

                leaf-list apply-groups-exclude {
                    type leafref {
                        path "../../../groups/group/name";
                    }
                    max-elements 8;
                    ordered-by user;
                    description "Exclude a configuration group at this level";
                }

                choice max-rate-or-percent-rate {
                    default "max-rate";
                    case max-rate {

                        leaf max-rate {
                            type types-qos:max-rate;
                            default "max";
                            description "Maximum frame-based bandwidth limit";
                        }

                    }
                    case max-percent-rate {

                        leaf max-percent-rate {
                            type decimal64 {
                                range "0.01..100.00";
                                fraction-digits 2;
                            }
                            description "Maximum frame-based bandwidth limit";
                        }

                    }
                }
                container orphan-overrides {
                    description "Enter the orphan-overrides context";

                    leaf level {
                        type types-qos:hierarchy-level;
                        default "1";
                        description "Port priority level for above-CIR orphan behavior";
                    }

                    leaf weight {
                        type types-qos:weight;
                        default "0";
                        description "Weight to use in the above-CIR port priority level";
                    }

                    leaf cir-level {
                        type types-qos:cir-level;
                        default "0";
                        description "Port priority level for within-CIR orphan behavior";
                    }

                    leaf cir-weight {
                        type types-qos:cir-weight;
                        default "0";
                        description "Weight to use in the within-CIR port priority level";
                    }

                } // container orphan-overrides

                list group {
                    key "group-name";
                    max-elements 8;
                    description "Enter the group list instance";

                    leaf group-name {
                        type types-sros:named-item;
                        description "Weighted scheduler group name";
                    }

                    leaf monitor-threshold {
                        type uint32 {
                            range "0..100";
                        }
                        default "0";
                        description "Congestion monitoring threshold";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                    choice rate-or-percent-rate {
                        default "rate";
                        case rate {

                            container rate {
                                description "Enter the rate context";

                                leaf pir {
                                    type types-qos:queue-pir-rate-maximum;
                                    units "kilobps";
                                    default "max";
                                    description "Administrative PIR";
                                }

                                leaf cir {
                                    type types-qos:queue-cir-rate-maximum;
                                    units "kilobps";
                                    default "max";
                                    description "Administrative CIR";
                                }

                            } // container rate

                        }
                        case percent-rate {

                            container percent-rate {
                                description "Enter the percent-rate context";

                                leaf pir {
                                    type decimal64 {
                                        range "0.01..100.00";
                                        fraction-digits 2;
                                    }
                                    description "Administrative PIR percent";
                                }

                                leaf cir {
                                    type decimal64 {
                                        range "0.00..100.00";
                                        fraction-digits 2;
                                    }
                                    default "100.00";
                                    description "Administrative CIR percent";
                                }

                            } // container percent-rate

                        }
                    }
                } // list group

                list level {
                    key "level-id";
                    description "Enter the level list instance";

                    leaf level-id {
                        type int32 {
                            range "1..8";
                        }
                        description "Priority level this port scheduler policy";
                    }

                    leaf group {
                        type leafref {
                            path "../../group/group-name";
                        }
                        description "Associated group";
                    }

                    leaf weight {
                        type types-qos:weight {
                            range "1..100";
                        }
                        default "1";
                        description "Weight of the level in the weighted scheduler group";
                    }

                    leaf monitor-threshold {
                        type uint32 {
                            range "0..100";
                        }
                        default "0";
                        description "Monitoring threshold of the configured rate";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                    choice rate-or-percent-rate {
                        default "rate";
                        case rate {

                            container rate {
                                description "Enter the rate context";

                                leaf pir {
                                    type types-qos:queue-pir-rate-maximum;
                                    units "kilobps";
                                    default "max";
                                    description "Administrative PIR";
                                }

                                leaf cir {
                                    type types-qos:queue-cir-rate-maximum;
                                    units "kilobps";
                                    default "max";
                                    description "Administrative CIR";
                                }

                            } // container rate

                        }
                        case percent-rate {

                            container percent-rate {
                                description "Enter the percent-rate context";

                                leaf pir {
                                    type decimal64 {
                                        range "0.01..100.00";
                                        fraction-digits 2;
                                    }
                                    description "Administrative PIR percent";
                                }

                                leaf cir {
                                    type decimal64 {
                                        range "0.00..100.00";
                                        fraction-digits 2;
                                    }
                                    default "100.00";
                                    description "Administrative CIR percent";
                                }

                            } // container percent-rate

                        }
                    }
                } // list level

            } // list port-scheduler-policy

            list hs-scheduler-policy {
                key "name";
                max-elements 127;
                description "Enter the hs-scheduler-policy list instance";

                leaf name {
                    type types-sros:named-item;
                    description "HS scheduler policy name";
                }

                leaf description {
                    type types-sros:description;
                    description "Text description";
                }

                leaf max-rate {
                    type union {
                        type uint32 {
                            range "1..100000";
                        }
                        type enumeration {
                            enum "max"                          { value -1; }
                        }
                    }
                    default "max";
                    description "Maximum frame-based bandwidth limit for the policy";
                }

                leaf-list apply-groups {
                    type leafref {
                        path "../../../groups/group/name";
                    }
                    max-elements 8;
                    ordered-by user;
                    description "Apply a configuration group at this level";
                }

                leaf-list apply-groups-exclude {
                    type leafref {
                        path "../../../groups/group/name";
                    }
                    max-elements 8;
                    ordered-by user;
                    description "Exclude a configuration group at this level";
                }

                list group {
                    key "group-id";
                    description "Enter the group list instance";

                    leaf group-id {
                        type int32 {
                            range "1";
                        }
                        description "Group ID for the HS scheduler policy";
                    }

                    leaf rate {
                        type union {
                            type uint32 {
                                range "1..100000";
                            }
                            type enumeration {
                                enum "max"                          { value -1; }
                            }
                        }
                        units "megabps";
                        default "max";
                        description "Group maximum rate";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                } // list group

                list scheduling-class {
                    key "class-id";
                    description "Enter the scheduling-class list instance";

                    leaf class-id {
                        type uint32 {
                            range "1..6";
                        }
                        description "Class identifier for the HS scheduler policy scheduling class";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                    choice rate-or-group {
                        default "rate";
                        case rate {

                            leaf rate {
                                type union {
                                    type uint32 {
                                        range "1..100000";
                                    }
                                    type enumeration {
                                        enum "max"                          { value -1; }
                                    }
                                }
                                default "max";
                                description "Maximum frame-based bandwidth limit";
                            }

                        }
                        case group {

                            container group {
                                presence "Enable the group context";
                                description "Enable the group context";

                                leaf group-id {
                                    type int32 {
                                        range "1";
                                    }
                                    mandatory true;
                                    description "Associated group associated with this scheduling class";
                                }

                                leaf weight {
                                    type int32 {
                                        range "1..127";
                                    }
                                    default "1";
                                    description "Weight associated with this scheduling class";
                                }

                            } // container group

                        }
                    }
                } // list scheduling-class

            } // list hs-scheduler-policy

            list hs-pool-policy {
                key "name";
                max-elements 63;
                description "Enter the hs-pool-policy list instance";

                leaf name {
                    type types-sros:named-item;
                    description "HS pool policy name";
                }

                leaf description {
                    type types-sros:description;
                    description "Text description";
                }

                leaf system-reserve {
                    type decimal64 {
                        range "1.00..30.00";
                        fraction-digits 2;
                    }
                    default "5.00";
                    description "Percentage of HS buffers reserved for internal system use";
                }

                leaf-list apply-groups {
                    type leafref {
                        path "../../../groups/group/name";
                    }
                    max-elements 8;
                    ordered-by user;
                    description "Apply a configuration group at this level";
                }

                leaf-list apply-groups-exclude {
                    type leafref {
                        path "../../../groups/group/name";
                    }
                    max-elements 8;
                    ordered-by user;
                    description "Exclude a configuration group at this level";
                }

                container root-tier {
                    description "Enter the root-tier context";

                    list root-pool {
                        key "root-pool-id";
                        description "Enter the root-pool list instance";

                        leaf root-pool-id {
                            type uint32 {
                                range "1..16";
                            }
                            description "Root pool identifier for the HS pool policy";
                        }

                        leaf allocation-weight {
                            type uint32 {
                                range "0..100";
                            }
                            description "Root pool allocation weight used to calculate pool size";
                        }

                        leaf slope-policy {
                            type leafref {
                                path "../../../../slope-policy/slope-policy-name";
                            }
                            description "Slope policy to define high, low, and exceed slopes";
                        }

                        leaf-list apply-groups {
                            type leafref {
                                path "../../../../../groups/group/name";
                            }
                            max-elements 8;
                            ordered-by user;
                            description "Apply a configuration group at this level";
                        }

                        leaf-list apply-groups-exclude {
                            type leafref {
                                path "../../../../../groups/group/name";
                            }
                            max-elements 8;
                            ordered-by user;
                            description "Exclude a configuration group at this level";
                        }

                    } // list root-pool

                } // container root-tier

                container mid-tier {
                    description "Enter the mid-tier context";

                    list mid-pool {
                        key "mid-pool-id";
                        description "Enter the mid-pool list instance";

                        leaf mid-pool-id {
                            type uint32 {
                                range "1..16";
                            }
                            description "Mid-pool identifier for the HS pool policy";
                        }

                        leaf allocation-percent {
                            type decimal64 {
                                range "0.01..100.00";
                                fraction-digits 2;
                            }
                            description "Root pool size to derive the mid-pool size";
                        }

                        leaf slope-policy {
                            type leafref {
                                path "../../../../slope-policy/slope-policy-name";
                            }
                            description "Slope policy to define high, low, and exceed slopes";
                        }

                        leaf port-bw-oversubscription-factor {
                            type uint32 {
                                range "1..10";
                            }
                            default "1";
                            description "Over subscription factor for port-class pool sizes";
                        }

                        leaf-list apply-groups {
                            type leafref {
                                path "../../../../../groups/group/name";
                            }
                            max-elements 8;
                            ordered-by user;
                            description "Apply a configuration group at this level";
                        }

                        leaf-list apply-groups-exclude {
                            type leafref {
                                path "../../../../../groups/group/name";
                            }
                            max-elements 8;
                            ordered-by user;
                            description "Exclude a configuration group at this level";
                        }

                        container parent-root-pool {
                            description "Enter the parent-root-pool context";

                            choice map-pool {
                                default "pool-id";
                                case pool-id {

                                    leaf pool-id {
                                        type leafref {
                                            path "../../../../root-tier/root-pool/root-pool-id";
                                        }
                                        description "Parent root pool to which the mid-pool is associated";
                                    }

                                }
                                case none {

                                    leaf none {
                                        type empty;
                                        description "Assign no buffers to the mid-tier pool";
                                    }

                                }
                            }
                        } // container parent-root-pool

                    } // list mid-pool

                } // container mid-tier

            } // list hs-pool-policy

            list hs-port-pool-policy {
                key "name";
                max-elements 2047;
                description "Enter the hs-port-pool-policy list instance";

                leaf name {
                    type types-sros:named-item;
                    description "HS port pool policy name";
                }

                leaf description {
                    type types-sros:description;
                    description "Text description";
                }

                leaf-list apply-groups {
                    type leafref {
                        path "../../../groups/group/name";
                    }
                    max-elements 8;
                    ordered-by user;
                    description "Apply a configuration group at this level";
                }

                leaf-list apply-groups-exclude {
                    type leafref {
                        path "../../../groups/group/name";
                    }
                    max-elements 8;
                    ordered-by user;
                    description "Exclude a configuration group at this level";
                }

                container std-port-class-pools {
                    description "Enter the std-port-class-pools context";

                    list class-pool {
                        key "std-class-pool-id";
                        description "Enter the class-pool list instance";

                        leaf std-class-pool-id {
                            type uint32 {
                                range "1..6";
                            }
                            description "Standard port class identifier for the HS port pool policy";
                        }

                        leaf slope-policy {
                            type leafref {
                                path "../../../../slope-policy/slope-policy-name";
                            }
                            description "Slope policy to define high, low, and exceed slopes";
                        }

                        leaf-list apply-groups {
                            type leafref {
                                path "../../../../../groups/group/name";
                            }
                            max-elements 8;
                            ordered-by user;
                            description "Apply a configuration group at this level";
                        }

                        leaf-list apply-groups-exclude {
                            type leafref {
                                path "../../../../../groups/group/name";
                            }
                            max-elements 8;
                            ordered-by user;
                            description "Exclude a configuration group at this level";
                        }

                        container parent-mid-pool {
                            description "Enter the parent-mid-pool context";

                            choice map-pool {
                                default "pool-id";
                                case pool-id {

                                    leaf pool-id {
                                        type uint32 {
                                            range "1..16";
                                        }
                                        description "Mid-pool ID associated with the port-class pool";
                                    }

                                }
                                case none {

                                    leaf none {
                                        type empty;
                                        description "Deactivate the port-class pool; pool size is zero";
                                    }

                                }
                            }
                        } // container parent-mid-pool

                        container allocation {
                            description "Enter the allocation context";

                            choice port-weight-or-percent {
                                default "port-bw-weight";
                                case port-bw-weight {

                                    leaf port-bw-weight {
                                        type uint32 {
                                            range "1..100";
                                        }
                                        default "1";
                                        description "Port bandwidth weight to be allocated";
                                    }

                                }
                                case explicit-percent {

                                    leaf explicit-percent {
                                        type decimal64 {
                                            range "0.01..100.00";
                                            fraction-digits 2;
                                        }
                                        description "Percentage of parent pool to be allocated";
                                    }

                                }
                            }
                        } // container allocation

                    } // list class-pool

                } // container std-port-class-pools

                container alt-port-class-pools {
                    description "Enter the alt-port-class-pools context";

                    list class-pool {
                        key "alt-class-pool-id";
                        description "Enter the class-pool list instance";

                        leaf alt-class-pool-id {
                            type uint32 {
                                range "1..6";
                            }
                            description "Class pool ID";
                        }

                        leaf slope-policy {
                            type leafref {
                                path "../../../../slope-policy/slope-policy-name";
                            }
                            description "Slope policy to define high, low, and exceed slopes";
                        }

                        leaf-list apply-groups {
                            type leafref {
                                path "../../../../../groups/group/name";
                            }
                            max-elements 8;
                            ordered-by user;
                            description "Apply a configuration group at this level";
                        }

                        leaf-list apply-groups-exclude {
                            type leafref {
                                path "../../../../../groups/group/name";
                            }
                            max-elements 8;
                            ordered-by user;
                            description "Exclude a configuration group at this level";
                        }

                        container parent-mid-pool {
                            description "Enter the parent-mid-pool context";

                            choice map-pool {
                                default "none";
                                case pool-id {

                                    leaf pool-id {
                                        type uint32 {
                                            range "1..16";
                                        }
                                        description "Mid-pool ID associated with the port-class pool";
                                    }

                                }
                                case none {

                                    leaf none {
                                        type empty;
                                        description "Deactivate the port-class pool; pool size is zero";
                                    }

                                }
                            }
                        } // container parent-mid-pool

                        container allocation {
                            description "Enter the allocation context";

                            choice port-weight-or-percent {
                                default "port-bw-weight";
                                case port-bw-weight {

                                    leaf port-bw-weight {
                                        type uint32 {
                                            range "1..100";
                                        }
                                        default "1";
                                        description "Port bandwidth weight to be allocated";
                                    }

                                }
                                case explicit-percent {

                                    leaf explicit-percent {
                                        type decimal64 {
                                            range "0.01..100.00";
                                            fraction-digits 2;
                                        }
                                        description "Percentage of parent pool to be allocated";
                                    }

                                }
                            }
                        } // container allocation

                    } // list class-pool

                } // container alt-port-class-pools

            } // list hs-port-pool-policy

            list hs-attachment-policy {
                key "name";
                max-elements 31;
                description "Enter the hs-attachment-policy list instance";

                leaf name {
                    type types-sros:named-item;
                    description "HS attachment policy name";
                }

                leaf description {
                    type types-sros:description;
                    description "Text description";
                }

                leaf low-burst-max-class {
                    type uint32 {
                        range "1..6";
                    }
                    default "6";
                    description "Low priority burst threshold";
                }

                leaf-list apply-groups {
                    type leafref {
                        path "../../../groups/group/name";
                    }
                    max-elements 8;
                    ordered-by user;
                    description "Apply a configuration group at this level";
                }

                leaf-list apply-groups-exclude {
                    type leafref {
                        path "../../../groups/group/name";
                    }
                    max-elements 8;
                    ordered-by user;
                    description "Exclude a configuration group at this level";
                }

                list wrr-group {
                    key "wrr-group-id";
                    description "Enter the wrr-group list instance";

                    leaf wrr-group-id {
                        type uint32 {
                            range "1..2";
                        }
                        description "WRR group ID for the HS attachment policy";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                    choice wrr-group-mapping {
                        default "unattached";
                        case sched-class-id {

                            leaf sched-class {
                                type int32 {
                                    range "1..6";
                                }
                                description "Scheduling class associated with the WRR group";
                            }

                        }
                        case unattached {

                            leaf unattached {
                                type empty;
                                description "Do not attach group ID to scheduling class or WRR group";
                            }

                        }
                    }
                } // list wrr-group

                list queue {
                    key "queue-id";
                    description "Enter the queue list instance";

                    leaf queue-id {
                        type uint32 {
                            range "1..8";
                        }
                        description "Queue identifier for the HS attachment policy";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                    choice hs-attach-queue-mapping {
                        default "unattached";
                        case sched-class-id {

                            leaf sched-class {
                                type int32 {
                                    range "1..6";
                                }
                                description "Scheduling class associated with the queue";
                            }

                        }
                        case wrr-group-id {

                            leaf wrr-group {
                                type int32 {
                                    range "1..2";
                                }
                                description "WRR group attached to the queue";
                            }

                        }
                        case unattached {

                            leaf unattached {
                                type empty;
                                description "Do not attach queue to scheduling class or WRR group";
                            }

                        }
                    }
                } // list queue

            } // list hs-attachment-policy

            list post-policer-mapping {
                key "name";
                max-elements 7;
                description "Enter the post-policer-mapping list instance";

                leaf name {
                    type types-sros:named-item;
                    description "Post-policer mapping policy name";
                }

                leaf description {
                    type types-sros:description;
                    description "Text description";
                }

                leaf-list apply-groups {
                    type leafref {
                        path "../../../groups/group/name";
                    }
                    max-elements 8;
                    ordered-by user;
                    description "Apply a configuration group at this level";
                }

                leaf-list apply-groups-exclude {
                    type leafref {
                        path "../../../groups/group/name";
                    }
                    max-elements 8;
                    ordered-by user;
                    description "Exclude a configuration group at this level";
                }

                list fc {
                    key "fc-name profile";
                    description "Enter the fc list instance";

                    leaf fc-name {
                        type types-sros:fc-name;
                        description "Forwarding class remapping";
                    }

                    leaf profile {
                        type types-qos:egress-profile;
                        description "Egress packet profile remapping";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                    container maps-to {
                        description "Enter the maps-to context";

                        leaf fc {
                            type types-sros:fc-name;
                            description "Forwarding class remapping";
                        }

                        leaf profile {
                            type types-qos:egress-profile;
                            description "Egress packet profile remapping";
                        }

                    } // container maps-to

                } // list fc

            } // list post-policer-mapping

            list queue-group-redirect-list {
                key "name";
                max-elements 2047;
                description "Enter the queue-group-redirect-list list instance";

                leaf name {
                    type types-sros:named-item;
                    description "Queue group redirect list name";
                }

                leaf type {
                    type enumeration {
                        enum "vxlan-vni"                    { value 1; }
                    }
                    default "vxlan-vni";
                    description "Type for queue-group redirect list";
                }

                leaf-list apply-groups {
                    type leafref {
                        path "../../../groups/group/name";
                    }
                    max-elements 8;
                    ordered-by user;
                    description "Apply a configuration group at this level";
                }

                leaf-list apply-groups-exclude {
                    type leafref {
                        path "../../../groups/group/name";
                    }
                    max-elements 8;
                    ordered-by user;
                    description "Exclude a configuration group at this level";
                }

                list match {
                    key "field-value";
                    max-elements 16;
                    description "Enter the match list instance";

                    leaf field-value {
                        type uint32 {
                            range "1..16777215";
                        }
                        description "Field value in the ingress or egress packet to match";
                    }

                    leaf instance {
                        type uint32 {
                            range "1..65535";
                        }
                        mandatory true;
                        description "Queue group instance for traffic redirection";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                } // list match

            } // list queue-group-redirect-list

            list egress-remark-policy {
                key "egress-remark-policy-name";
                max-elements 127;
                description "Enter the egress-remark-policy list instance";

                leaf egress-remark-policy-name {
                    type types-sros:named-item-64;
                    description "Name of the egress-remark-policy QoS policy";
                }

                leaf description {
                    type types-sros:description;
                    description "Text description";
                }

                leaf scope {
                    type types-qos:item-scope;
                    default "template";
                    description "Scope of the policy";
                }

                leaf fc-dot1p-map {
                    type leafref {
                        path "../../fc-dot1p-map/fc-dot1p-map-name";
                    }
                    description "Attach dot1p FC map to ingress classification policy";
                }

                leaf fc-dscp-map {
                    type leafref {
                        path "../../fc-dscp-map/fc-dscp-map-name";
                    }
                    description "Attach DSCP FC map to ingress classification policy";
                }

                leaf fc-lsp-exp-map {
                    type leafref {
                        path "../../fc-lsp-exp-map/fc-lsp-exp-map-name";
                    }
                    description "Attach LSP-EXP FC map to ingress classification policy";
                }

                leaf-list apply-groups {
                    type leafref {
                        path "../../../groups/group/name";
                    }
                    max-elements 8;
                    ordered-by user;
                    description "Apply a configuration group at this level";
                }

                leaf-list apply-groups-exclude {
                    type leafref {
                        path "../../../groups/group/name";
                    }
                    max-elements 8;
                    ordered-by user;
                    description "Exclude a configuration group at this level";
                }

                list fc {
                    key "fc-name";
                    description "Enter the fc list instance";

                    leaf fc-name {
                        type types-sros:fc-name;
                        description "Forwarding class name";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                    container de-mark {
                        presence "Enable the de-mark context";
                        description "Enter the de-mark context";

                        leaf force {
                            type types-qos:de-value;
                            description "DE value to set";
                        }

                    } // container de-mark

                    container dot1p {
                        description "Enter the dot1p context";

                        leaf in-profile {
                            type types-qos:dot1p-priority;
                            description "Unique IEEE 802.1p value to mark in-profile traffic";
                        }

                        leaf out-profile {
                            type types-qos:dot1p-priority;
                            description "Unique IEEE 802.1p value to mark out-profile traffic";
                        }

                        leaf exceed {
                            type types-qos:dot1p-priority;
                            description "Unique IEEE 802.1p value to mark exceed-profile traffic";
                        }

                        leaf inplus {
                            type types-qos:dot1p-priority;
                            description "Unique IEEE 802.1p value to mark inplus traffic";
                        }

                    } // container dot1p

                    container dscp {
                        description "Enter the dscp context";

                        leaf in-profile {
                            type types-qos:dscp-name;
                            description "DSCP name for in-profile frames";
                        }

                        leaf out-profile {
                            type types-qos:dscp-name;
                            description "DSCP value for out-of-profile frames";
                        }

                        leaf exceed {
                            type types-qos:dscp-name;
                            description "DSCP name for exceed profile frames";
                        }

                        leaf inplus {
                            type types-qos:dscp-name;
                            description "DSCP name for inplus profile frames";
                        }

                    } // container dscp

                    container lsp-exp {
                        description "Enter the lsp-exp context";

                        leaf in-profile {
                            type types-qos:lsp-exp-value;
                            description "LSP-EXP marking for in-profile frames";
                        }

                        leaf out-profile {
                            type types-qos:lsp-exp-value;
                            description "LSP-EXP value for out-of-profile frames";
                        }

                        leaf exceed {
                            type types-qos:lsp-exp-value;
                            description "LSP-EXP marking for exceed profile frames";
                        }

                        leaf inplus {
                            type types-qos:lsp-exp-value;
                            description "LSP-EXP marking for inplus profile frames";
                        }

                    } // container lsp-exp

                } // list fc

            } // list egress-remark-policy

            container match-list {
                description "Enter the match-list context";

                list ip-prefix-list {
                    key "prefix-list-name";
                    max-elements 512;
                    description "Enter the ip-prefix-list list instance";

                    leaf prefix-list-name {
                        type types-sros:named-item;
                        description "IP prefix list name";
                    }

                    leaf description {
                        type types-sros:description;
                        description "Text description";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                    list prefix {
                        key "ip-prefix";
                        max-elements 256;
                        description "Add a list entry for prefix";

                        leaf ip-prefix {
                            type types-sros:ipv4-prefix;
                            description "IPv4 address prefix";
                        }

                    } // list prefix

                } // list ip-prefix-list

                list ipv6-prefix-list {
                    key "prefix-list-name";
                    max-elements 128;
                    description "Enter the ipv6-prefix-list list instance";

                    leaf prefix-list-name {
                        type types-sros:named-item;
                        description "IP prefix list name";
                    }

                    leaf description {
                        type types-sros:description;
                        description "Text description";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                    list prefix {
                        key "ipv6-prefix";
                        max-elements 128;
                        description "Add a list entry for prefix";

                        leaf ipv6-prefix {
                            type types-sros:ipv6-prefix;
                            description "Ipv6 address prefix";
                        }

                    } // list prefix

                } // list ipv6-prefix-list

                list port-list {
                    key "port-list-name";
                    max-elements 16;
                    description "Enter the port-list list instance";

                    leaf port-list-name {
                        type types-sros:named-item;
                        description "Port list name";
                    }

                    leaf description {
                        type types-sros:description;
                        description "Text description";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                    list port {
                        key "value";
                        description "Add a list entry for port";

                        leaf value {
                            type int32 {
                                range "0..65535";
                            }
                            description "Port number";
                        }

                    } // list port

                    list range {
                        key "start end";
                        description "Add a list entry for range";

                        leaf start {
                            type int32 {
                                range "0..65534";
                            }
                            description "Lower bound for the port range";
                        }

                        leaf end {
                            type int32 {
                                range "1..65535";
                            }
                            description "Upper bound for the port range";
                        }

                    } // list range

                } // list port-list

            } // container match-list

            list fp-resource-policy {
                key "fp-resource-policy-name";
                max-elements 16;
                description "Enter the fp-resource-policy list instance";

                leaf fp-resource-policy-name {
                    type types-qos:fp-resource-policy-name;
                    description "FP resource policy name";
                }

                leaf description {
                    type types-sros:description;
                    description "Text description";
                }

                leaf-list apply-groups {
                    type leafref {
                        path "../../../groups/group/name";
                    }
                    max-elements 8;
                    ordered-by user;
                    description "Apply a configuration group at this level";
                }

                leaf-list apply-groups-exclude {
                    type leafref {
                        path "../../../groups/group/name";
                    }
                    max-elements 8;
                    ordered-by user;
                    description "Exclude a configuration group at this level";
                }

                container queues {
                    description "Enter the queues context";

                    leaf ingress-percent-of-total {
                        type decimal64 {
                            range "4.00..97.00";
                            fraction-digits 2;
                        }
                        sros-ext:card-auto-reset-on-modify;
                        description "Percentage of total ingress queues allocated";
                    }

                } // container queues

                container aggregate-shapers {
                    description "Enter the aggregate-shapers context";

                    leaf auto-creation {
                        type boolean;
                        sros-ext:card-auto-reset-on-modify;
                        default "false";
                        description "Enables auto-creation of hardware aggregate shapers";
                    }

                    container hw-agg-shapers {
                        description "Enter the hw-agg-shapers context";

                        leaf subscribers {
                            type boolean;
                            sros-ext:card-auto-reset-on-modify;
                            default "false";
                            description "Enables hardware aggregate shapers for subscribers";
                        }

                    } // container hw-agg-shapers

                } // container aggregate-shapers

                container ports {
                    description "Enter the ports context";

                    leaf hqos-mode {
                        type enumeration {
                            enum "port-scheduler"               { value 1; }
                            enum "hw-agg-shaping"               { value 2; }
                        }
                        sros-ext:card-auto-reset-on-modify;
                        default "port-scheduler";
                        description "Default HQOS mode of the port";
                    }

                } // container ports

            } // list fp-resource-policy

            container packet-byte-offset {
                description "Enter the packet-byte-offset context";

                leaf admin-state {
                    type types-sros:admin-state;
                    default "disable";
                    description "Administrative state of packet byte offset";
                }

                leaf-list apply-groups {
                    type leafref {
                        path "../../../groups/group/name";
                    }
                    max-elements 8;
                    ordered-by user;
                    description "Apply a configuration group at this level";
                }

                leaf-list apply-groups-exclude {
                    type leafref {
                        path "../../../groups/group/name";
                    }
                    max-elements 8;
                    ordered-by user;
                    description "Exclude a configuration group at this level";
                }

            } // container packet-byte-offset

            list hw-agg-shaper-scheduler-policy {
                key "name";
                max-elements 127;
                description "Enter the hw-agg-shaper-scheduler-policy list instance";

                leaf name {
                    type types-sros:named-item-64;
                    description "Name of the hardware aggregate shaper scheduler policy";
                }

                leaf description {
                    type types-sros:description;
                    description "Description of the hardware aggregate shaper scheduler policy";
                }

                leaf congestion-threshold {
                    type uint32 {
                        range "0..100";
                    }
                    default "90";
                    description "Congestion threshold of the scheduler";
                }

                leaf monitor-threshold {
                    type uint32 {
                        range "0..100";
                    }
                    default "0";
                    description "Monitor threshold for the scheduler";
                }

                leaf-list apply-groups {
                    type leafref {
                        path "../../../groups/group/name";
                    }
                    max-elements 8;
                    ordered-by user;
                    description "Apply a configuration group at this level";
                }

                leaf-list apply-groups-exclude {
                    type leafref {
                        path "../../../groups/group/name";
                    }
                    max-elements 8;
                    ordered-by user;
                    description "Exclude a configuration group at this level";
                }

                choice max-rate-or-percent-rate {
                    default "max-rate";
                    case max-rate {

                        leaf max-rate {
                            type types-qos:shaper-max-rate;
                            units "kilobps";
                            default "max";
                            description "Maximum frame-based bandwidth limit";
                        }

                    }
                    case max-percent-rate {

                        leaf max-percent-rate {
                            type decimal64 {
                                range "0.01..100.00";
                                fraction-digits 2;
                            }
                            description "Maximum frame-based bandwidth percentage";
                        }

                    }
                }
                list group {
                    key "group-name";
                    max-elements 6;
                    description "Add a list entry for group";

                    leaf group-name {
                        type types-sros:named-item;
                        description "Name of the HW aggregate shaper scheduler policy group";
                    }

                } // list group

                list sched-class {
                    key "class-id";
                    description "Enter the sched-class list instance";

                    leaf class-id {
                        type int32 {
                            range "1..6";
                        }
                        description "Scheduling class ID for the scheduler policy";
                    }

                    leaf group {
                        type leafref {
                            path "../../group/group-name";
                        }
                        description "Group associated with the scheduling class";
                    }

                    leaf weight {
                        type types-qos:weight {
                            range "1..8";
                        }
                        default "1";
                        description "Weight associated with the group";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                } // list sched-class

            } // list hw-agg-shaper-scheduler-policy

            list dot1p-fc-map {
                key "dot1p-fc-map-name";
                max-elements 511;
                description "Enter the dot1p-fc-map list instance";

                leaf dot1p-fc-map-name {
                    type types-sros:named-item-64;
                    description "Dot1p-fc-map name";
                }

                leaf-list apply-groups {
                    type leafref {
                        path "../../../groups/group/name";
                    }
                    max-elements 8;
                    ordered-by user;
                    description "Apply a configuration group at this level";
                }

                leaf-list apply-groups-exclude {
                    type leafref {
                        path "../../../groups/group/name";
                    }
                    max-elements 8;
                    ordered-by user;
                    description "Exclude a configuration group at this level";
                }

                container default-action {
                    description "Enter the default-action context";

                    leaf fc {
                        type types-sros:fc-name;
                        default "be";
                        description "Default FC name";
                    }

                    leaf profile {
                        type types-qos:profile-de;
                        default "out";
                        description "Default profile state for ingress traffic";
                    }

                } // container default-action

                list dot1p {
                    key "dot1p-value";
                    description "Enter the dot1p list instance";

                    leaf dot1p-value {
                        type types-qos:dot1p-priority;
                        description "Dot1p value to match in the packet";
                    }

                    leaf fc {
                        type types-sros:fc-name;
                        description "Forwarding class";
                    }

                    leaf profile {
                        type types-qos:profile-de;
                        description "Default profile for ingress traffic";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                } // list dot1p

            } // list dot1p-fc-map

            list dscp-fc-map {
                key "dscp-fc-map-name";
                max-elements 511;
                description "Enter the dscp-fc-map list instance";

                leaf dscp-fc-map-name {
                    type types-sros:named-item-64;
                    description "DSCP name to associate with the FC";
                }

                leaf-list apply-groups {
                    type leafref {
                        path "../../../groups/group/name";
                    }
                    max-elements 8;
                    ordered-by user;
                    description "Apply a configuration group at this level";
                }

                leaf-list apply-groups-exclude {
                    type leafref {
                        path "../../../groups/group/name";
                    }
                    max-elements 8;
                    ordered-by user;
                    description "Exclude a configuration group at this level";
                }

                container default-action {
                    description "Enter the default-action context";

                    leaf fc {
                        type types-sros:fc-name;
                        default "be";
                        description "Default FC to classify ingress traffic";
                    }

                    leaf profile {
                        type types-qos:profile;
                        default "out";
                        description "Default profile for ingress traffic";
                    }

                } // container default-action

                list dscp {
                    key "dscp-name";
                    description "Enter the dscp list instance";

                    leaf dscp-name {
                        type types-qos:dscp-name;
                        description "Name of the DSCP to associate with the FC";
                    }

                    leaf fc {
                        type types-sros:fc-name;
                        description "FC to associate with the DSCP";
                    }

                    leaf profile {
                        type types-qos:profile;
                        default "in";
                        description "Default profile to use for ingress traffic";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                } // list dscp

            } // list dscp-fc-map

            list lsp-exp-fc-map {
                key "lsp-exp-fc-map-name";
                max-elements 511;
                description "Enter the lsp-exp-fc-map list instance";

                leaf lsp-exp-fc-map-name {
                    type types-sros:named-item-64;
                    description "Name of the lsp-exp-fc-map";
                }

                leaf-list apply-groups {
                    type leafref {
                        path "../../../groups/group/name";
                    }
                    max-elements 8;
                    ordered-by user;
                    description "Apply a configuration group at this level";
                }

                leaf-list apply-groups-exclude {
                    type leafref {
                        path "../../../groups/group/name";
                    }
                    max-elements 8;
                    ordered-by user;
                    description "Exclude a configuration group at this level";
                }

                container default-action {
                    description "Enter the default-action context";

                    leaf fc {
                        type types-sros:fc-name;
                        default "be";
                        description "Specifies the default forwarding class to be used while classifying the ingress traffic.";
                    }

                    leaf profile {
                        type types-qos:profile;
                        default "out";
                        description "Specifies the default profile to be used for the ingressing traffic.";
                    }

                } // container default-action

                list lsp-exp {
                    key "lsp-exp-value";
                    description "Enter the lsp-exp list instance";

                    leaf lsp-exp-value {
                        type types-qos:lsp-exp-value;
                        description "LSP-EXP bit value for which mapping is performed";
                    }

                    leaf fc {
                        type types-sros:fc-name;
                        description "FC to associate with the DSCP";
                    }

                    leaf profile {
                        type types-qos:profile;
                        default "in";
                        description "Default profile to use for ingress traffic";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                } // list lsp-exp

            } // list lsp-exp-fc-map

            list fc-dot1p-map {
                key "fc-dot1p-map-name";
                description "Enter the fc-dot1p-map list instance";

                leaf fc-dot1p-map-name {
                    type types-sros:named-item-64;
                    description "Name of the fc-dot1p-map";
                }

                leaf-list apply-groups {
                    type leafref {
                        path "../../../groups/group/name";
                    }
                    max-elements 8;
                    ordered-by user;
                    description "Apply a configuration group at this level";
                }

                leaf-list apply-groups-exclude {
                    type leafref {
                        path "../../../groups/group/name";
                    }
                    max-elements 8;
                    ordered-by user;
                    description "Exclude a configuration group at this level";
                }

                list fc {
                    key "fc-name";
                    description "Enter the fc list instance";

                    leaf fc-name {
                        type types-sros:fc-name;
                        description "Forwarding class name";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                    container de-mark {
                        presence "Enable the de-mark context";
                        description "Enter the de-mark context";

                        leaf force {
                            type types-qos:de-value;
                            description "DE value";
                        }

                    } // container de-mark

                    container dot1p {
                        description "Enter the dot1p context";

                        leaf in-profile {
                            type types-qos:dot1p-priority;
                            description "Dot1p value for in-profile frames";
                        }

                        leaf out-profile {
                            type types-qos:dot1p-priority;
                            description "Dot1p value for out-of-profile frames";
                        }

                    } // container dot1p

                    container dot1p-inner {
                        description "Enter the dot1p-inner context";

                        leaf in-profile {
                            type types-qos:dot1p-priority;
                            description "Specifies Inner Dot1p value for in-profile frames.";
                        }

                        leaf out-profile {
                            type types-qos:dot1p-priority;
                            description "Specifies Inner Dot1p value for out-of-profile frames.";
                        }

                    } // container dot1p-inner

                    container dot1p-outer {
                        description "Enter the dot1p-outer context";

                        leaf in-profile {
                            type types-qos:dot1p-priority;
                            description "Specifies Outer Dot1p value for in-profile frames.";
                        }

                        leaf out-profile {
                            type types-qos:dot1p-priority;
                            description "Specifies Outer Dot1p value for out-of-profile frames.";
                        }

                    } // container dot1p-outer

                    container de-mark-inner {
                        presence "Enable the de-mark-inner context";
                        description "Enter the de-mark-inner context";

                        leaf force {
                            type types-qos:de-value;
                            description "Inner DE marking value";
                        }

                    } // container de-mark-inner

                    container de-mark-outer {
                        presence "Enable the de-mark-outer context";
                        description "Enter the de-mark-outer context";

                        leaf force {
                            type types-qos:de-value;
                            description "Outer DE marking value";
                        }

                    } // container de-mark-outer

                } // list fc

            } // list fc-dot1p-map

            list fc-dscp-map {
                key "fc-dscp-map-name";
                description "Enter the fc-dscp-map list instance";

                leaf fc-dscp-map-name {
                    type types-sros:named-item-64;
                    description "Name of the fc-dscp-map";
                }

                leaf-list apply-groups {
                    type leafref {
                        path "../../../groups/group/name";
                    }
                    max-elements 8;
                    ordered-by user;
                    description "Apply a configuration group at this level";
                }

                leaf-list apply-groups-exclude {
                    type leafref {
                        path "../../../groups/group/name";
                    }
                    max-elements 8;
                    ordered-by user;
                    description "Exclude a configuration group at this level";
                }

                list fc {
                    key "fc-name";
                    description "Enter the fc list instance";

                    leaf fc-name {
                        type types-sros:fc-name;
                        description "Forwarding class name";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                    container dscp {
                        description "Enter the dscp context";

                        leaf in-profile {
                            type types-qos:dscp-name;
                            description "DSCP value for in-profile frames";
                        }

                        leaf out-profile {
                            type types-qos:dscp-name;
                            description "DSCP value for out-of-profile frames";
                        }

                    } // container dscp

                } // list fc

            } // list fc-dscp-map

            list fc-lsp-exp-map {
                key "fc-lsp-exp-map-name";
                description "Enter the fc-lsp-exp-map list instance";

                leaf fc-lsp-exp-map-name {
                    type types-sros:named-item-64;
                    description "Name of the fc-lsp-exp-map";
                }

                leaf-list apply-groups {
                    type leafref {
                        path "../../../groups/group/name";
                    }
                    max-elements 8;
                    ordered-by user;
                    description "Apply a configuration group at this level";
                }

                leaf-list apply-groups-exclude {
                    type leafref {
                        path "../../../groups/group/name";
                    }
                    max-elements 8;
                    ordered-by user;
                    description "Exclude a configuration group at this level";
                }

                list fc {
                    key "fc-name";
                    description "Enter the fc list instance";

                    leaf fc-name {
                        type types-sros:fc-name;
                        description "Forwarding class name";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                    container lsp-exp {
                        description "Enter the lsp-exp context";

                        leaf in-profile {
                            type types-qos:lsp-exp-value;
                            description "LSP-EXP marking for in-profile frames";
                        }

                        leaf out-profile {
                            type types-qos:lsp-exp-value;
                            description "LSP-EXP value for out-of-profile frames";
                        }

                    } // container lsp-exp

                } // list fc

            } // list fc-lsp-exp-map

        } // container qos

    } // grouping conf-qos

}
