submodule nokia-conf-port-network {

    yang-version "1.1";

    belongs-to nokia-conf { prefix "conf"; }

    import nokia-sros-yang-extensions     { prefix "sros-ext"; }
    import nokia-types-sros               { prefix "types-sros"; }

    include nokia-conf-groups;
    include nokia-conf-qos;


    sros-ext:sros-major-release "rel22";

    organization "Nokia";

    contact
        "Nokia SR OS Support
         Web: <http://www.nokia.com>";

    description
        "Nokia YANG Data model to configure network port parameters on SR OS based routers.

         Copyright 2016 Nokia. All rights reserved. Reproduction of this document
         is authorized on the condition that the foregoing copyright notice is included.

         This nokia-conf-port-network YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";

    revision "2022-01-07";

    grouping conf-port-network {
        container network {
            description "Enter the network context";

            leaf-list apply-groups {
                type leafref {
                    path "../../../groups/group/name";
                }
                max-elements 8;
                ordered-by user;
                description "Apply a configuration group at this level";
            }

            leaf-list apply-groups-exclude {
                type leafref {
                    path "../../../groups/group/name";
                }
                max-elements 8;
                ordered-by user;
                description "Exclude a configuration group at this level";
            }

            container egress {
                description "Enter the egress context";

                list pool {
                    key "name";
                    description "Enter the pool list instance";

                    leaf name {
                        type types-sros:named-item;
                        description "Pool name";
                    }

                    leaf amber-alarm-threshold {
                        type uint32 {
                            range "1..1000";
                        }
                        units "percent";
                        description "Threshold for the amber alarm on oversubscription";
                    }

                    leaf red-alarm-threshold {
                        type uint32 {
                            range "1..1000";
                        }
                        units "percent";
                        description "Threshold for the red alarm on oversubscription";
                    }

                    leaf slope-policy {
                        type leafref {
                            path "../../../../../qos/slope-policy/slope-policy-name";
                        }
                        description "Policy for the RED slope and TAF values";
                    }

                    leaf-list apply-groups {
                        type leafref {
                            path "../../../../../groups/group/name";
                        }
                        max-elements 8;
                        ordered-by user;
                        description "Apply a configuration group at this level";
                    }

                    leaf-list apply-groups-exclude {
                        type leafref {
                            path "../../../../../groups/group/name";
                        }
                        max-elements 8;
                        ordered-by user;
                        description "Exclude a configuration group at this level";
                    }

                    container resv-cbs {
                        description "Enter the resv-cbs context";

                        leaf cbs {
                            type union {
                                type int32 {
                                    range "0..100";
                                }
                                type enumeration {
                                    enum "auto"                         { value -1; }
                                }
                            }
                            units "percent";
                            default "auto";
                            description "Percentage of the pool buffer space reserved for CBS";
                        }

                        container amber-alarm-action {
                            description "Enter the amber-alarm-action context";

                            leaf step {
                                type uint32 {
                                    range "1..100";
                                }
                                units "percent";
                                description "Step-size percentage for reserved CBS of the pool";
                            }

                            leaf max {
                                type uint32 {
                                    range "1..100";
                                }
                                units "percent";
                                description "Maximum percentage for reserved CBS of the pool";
                            }

                        } // container amber-alarm-action

                    } // container resv-cbs

                } // list pool

            } // container egress

        } // container network

    } // grouping conf-port-network

}
