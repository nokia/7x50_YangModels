submodule nokia-state-isa {

    yang-version "1.1";

    belongs-to nokia-state { prefix "state"; }

    import ietf-yang-types                { prefix "yang"; }
    import nokia-sros-yang-extensions     { prefix "sros-ext"; }
    import nokia-types-esa                { prefix "types-esa"; }
    import nokia-types-isa                { prefix "types-isa"; }
    import nokia-types-l2tp               { prefix "types-l2tp"; }
    import nokia-types-nat                { prefix "types-nat"; }
    import nokia-types-redundancy         { prefix "types-redundancy"; }
    import nokia-types-sros               { prefix "types-sros"; }

    include nokia-state-card;
    include nokia-state-esa;
    include nokia-state-isa-application-assurance-group;
    include nokia-state-isa-video-group;
    include nokia-state-service;


    sros-ext:sros-major-release "rel22";

    organization "Nokia";

    contact
        "Nokia SR OS Support
         Web: <http://www.nokia.com>";

    description
        "Nokia YANG Data model with operational state for ISA configuration on SR OS based routers.

         Copyright 2016 Nokia. All rights reserved. Reproduction of this document
         is authorized on the condition that the foregoing copyright notice is included.

         This nokia-state-isa YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";

    revision "2021-12-23";

    grouping state-isa {
        container isa {
            description "Enter the isa context";

            list tunnel-group {
                key "id";
                description "Enter the tunnel-group list instance";

                leaf id {
                    type types-redundancy:tunnel-group-id;
                    description "Tunnel group ID";
                }

                leaf oper-state {
                    type types-sros:oper-state;
                    description "The operational status of ISA tunnel group.";
                }

                leaf active-isa {
                    type types-isa:slot-mda;
                    description "The active ISA that is being used for this module group.";
                }

                leaf tunnel-count {
                    type uint32;
                    description "The number of IPsec tunnels being used for this module group.";
                }

                leaf max-tunnel {
                    type uint32;
                    description "The maximum number of IPsec tunnels available for this module group.";
                }

                leaf oper-flags {
                    type bits {
                        bit admin-down                     { position 0; }
                        bit no-active                      { position 1; }
                        bit no-resources                   { position 2; }
                        bit mc-admin-down                  { position 3; }
                    }
                    description "The operational flags to determine the ISA tunnel group.";
                }

                leaf ip-tunnel-count {
                    type uint32;
                    description "The number of IP tunnels being used for this module group.";
                }

                leaf ip-max-tunnel {
                    type uint32;
                    description "The maximum number of IP tunnels available for this module group.";
                }

                choice redundancy {
                    description "Redundancy mode for ISAs in this tunnel group";
                    case multi-active {

                        container multi-active {
                            description "Enter the multi-active context";

                            choice group-members {
                                description "MDA or ESA-VM members of this tunnel group";
                                case isa {

                                    list isa {
                                        key "isa-id";
                                        description "Enter the isa list instance";

                                        leaf isa-id {
                                            type types-isa:slot-mda;
                                            description "ISA ID associated with the multi-active tunnel group";
                                        }

                                        leaf tunnel-group-in-use {
                                            type boolean;
                                            description "Activate this ISA in the Integrated Service Adaptor (ISA) tunnel group. The value is only meaningful when multi-active is true.";
                                        }

                                    } // list isa

                                }
                                case esa {

                                    list esa {
                                        key "esa-id vm";
                                        description "Enter the esa list instance";

                                        leaf esa-id {
                                            type leafref {
                                                path "../../../../../esa/esa-id";
                                            }
                                            description "ESA ID";
                                        }

                                        leaf vm {
                                            type leafref {
                                                path "../../../../../esa[esa-id=current()/../esa-id]/vm/vm-id";
                                            }
                                            description "VM ID";
                                        }

                                        leaf tunnel-group-in-use {
                                            type boolean;
                                            description "Activate this ISA in the Integrated Service Adaptor (ISA) tunnel group. The value is only meaningful when multi-active is true.";
                                        }

                                    } // list esa

                                }
                            }
                        } // container multi-active

                    }
                }
                container statistics {
                    description "Enter the statistics context";

                    container ip-tunnel {
                        description "Enter the ip-tunnel context";

                        container number-of-tunnels {
                            description "Enter the number-of-tunnels context";

                            container current {
                                description "Enter the current context";

                                leaf gre {
                                    type yang:counter64;
                                    description "Number of GRE tunnels.";
                                }

                                leaf ip {
                                    type yang:counter64;
                                    description "Number of IP tunnels.";
                                }

                                leaf l2tpv3 {
                                    type yang:counter64;
                                    description "Number of L2TPv3 tunnels.";
                                }

                                leaf start-time {
                                    type yang:date-and-time;
                                    description "The time when the sampling interval started.";
                                }

                            } // container current

                        } // container number-of-tunnels

                        container throughput {
                            description "Enter the throughput context";

                            container gre {
                                description "Enter the gre context";

                                container current {
                                    description "Enter the current context";

                                    leaf start-time {
                                        type yang:date-and-time;
                                        description "The time when the sampling interval started.";
                                    }

                                    leaf sampling-duration {
                                        type types-sros:time-duration;
                                        description "The duration of the corresponding sampling interval.";
                                    }

                                    container packets {
                                        description "Enter the packets context";

                                        leaf encapsulated {
                                            type yang:counter64;
                                            units "packets per second";
                                            description "Encapsulated GRE tunnel throughput.";
                                        }

                                        leaf decapsulated {
                                            type yang:counter64;
                                            units "packets per second";
                                            description "Decapsulated GRE tunnel throughput.";
                                        }

                                        leaf total {
                                            type yang:counter64;
                                            units "packets per second";
                                            description "Encapsulated and decapsulated GRE tunnel throughput.";
                                        }

                                    } // container packets

                                    container bytes {
                                        description "Enter the bytes context";

                                        leaf encapsulated {
                                            type yang:counter64;
                                            units "megabps";
                                            description "Encapsulated GRE tunnel throughput.";
                                        }

                                        leaf decapsulated {
                                            type yang:counter64;
                                            units "megabps";
                                            description "Decapsulated GRE tunnel throughput.";
                                        }

                                        leaf total {
                                            type yang:counter64;
                                            units "megabps";
                                            description "Encapsulated and decapsulated GRE tunnel throughput.";
                                        }

                                    } // container bytes

                                } // container current

                                list historical {
                                    key "index";
                                    description "Enter the historical list instance";

                                    leaf index {
                                        type uint32 {
                                            range "2..max";
                                        }
                                        description "The index of the finished sampling interval period for this statistic. It starts with '2' and is ordered by start time of intervals so that smaller index indicate more recent intervals.";
                                    }

                                    leaf start-time {
                                        type yang:date-and-time;
                                        description "The time when the sampling interval started.";
                                    }

                                    leaf sampling-duration {
                                        type types-sros:time-duration;
                                        description "The duration of the corresponding sampling interval.";
                                    }

                                    container packets {
                                        description "Enter the packets context";

                                        leaf encapsulated {
                                            type yang:counter64;
                                            units "packets per second";
                                            description "Encapsulated GRE tunnel throughput.";
                                        }

                                        leaf decapsulated {
                                            type yang:counter64;
                                            units "packets per second";
                                            description "Decapsulated GRE tunnel throughput.";
                                        }

                                        leaf total {
                                            type yang:counter64;
                                            units "packets per second";
                                            description "Encapsulated and decapsulated GRE tunnel throughput.";
                                        }

                                    } // container packets

                                    container bytes {
                                        description "Enter the bytes context";

                                        leaf encapsulated {
                                            type yang:counter64;
                                            units "megabps";
                                            description "Encapsulated GRE tunnel throughput.";
                                        }

                                        leaf decapsulated {
                                            type yang:counter64;
                                            units "megabps";
                                            description "Decapsulated GRE tunnel throughput.";
                                        }

                                        leaf total {
                                            type yang:counter64;
                                            units "megabps";
                                            description "Encapsulated and decapsulated GRE tunnel throughput.";
                                        }

                                    } // container bytes

                                } // list historical

                            } // container gre

                            container ip {
                                description "Enter the ip context";

                                container current {
                                    description "Enter the current context";

                                    leaf start-time {
                                        type yang:date-and-time;
                                        description "The time when the sampling interval started.";
                                    }

                                    leaf sampling-duration {
                                        type types-sros:time-duration;
                                        description "The duration of the corresponding sampling interval.";
                                    }

                                    container packets {
                                        description "Enter the packets context";

                                        leaf encapsulated {
                                            type yang:counter64;
                                            units "packets per second";
                                            description "Encapsulated IP tunnel throughput.";
                                        }

                                        leaf decapsulated {
                                            type yang:counter64;
                                            units "packets per second";
                                            description "Decapsulated IP tunnel throughput.";
                                        }

                                        leaf total {
                                            type yang:counter64;
                                            units "packets per second";
                                            description "Encapsulated and decapsulated IP tunnel throughput.";
                                        }

                                    } // container packets

                                    container bytes {
                                        description "Enter the bytes context";

                                        leaf encapsulated {
                                            type yang:counter64;
                                            units "megabps";
                                            description "Encapsulated IP tunnel throughput.";
                                        }

                                        leaf decapsulated {
                                            type yang:counter64;
                                            units "megabps";
                                            description "Decapsulated IP tunnel throughput.";
                                        }

                                        leaf total {
                                            type yang:counter64;
                                            units "megabps";
                                            description "Encapsulated and decapsulated IP tunnel throughput.";
                                        }

                                    } // container bytes

                                } // container current

                                list historical {
                                    key "index";
                                    description "Enter the historical list instance";

                                    leaf index {
                                        type uint32 {
                                            range "2..max";
                                        }
                                        description "The index of the finished sampling interval period for this statistic. It starts with '2' and is ordered by start time of intervals so that smaller index indicate more recent intervals.";
                                    }

                                    leaf start-time {
                                        type yang:date-and-time;
                                        description "The time when the sampling interval started.";
                                    }

                                    leaf sampling-duration {
                                        type types-sros:time-duration;
                                        description "The duration of the corresponding sampling interval.";
                                    }

                                    container packets {
                                        description "Enter the packets context";

                                        leaf encapsulated {
                                            type yang:counter64;
                                            units "packets per second";
                                            description "Encapsulated IP tunnel throughput.";
                                        }

                                        leaf decapsulated {
                                            type yang:counter64;
                                            units "packets per second";
                                            description "Decapsulated IP tunnel throughput.";
                                        }

                                        leaf total {
                                            type yang:counter64;
                                            units "packets per second";
                                            description "Encapsulated and decapsulated IP tunnel throughput.";
                                        }

                                    } // container packets

                                    container bytes {
                                        description "Enter the bytes context";

                                        leaf encapsulated {
                                            type yang:counter64;
                                            units "megabps";
                                            description "Encapsulated IP tunnel throughput.";
                                        }

                                        leaf decapsulated {
                                            type yang:counter64;
                                            units "megabps";
                                            description "Decapsulated IP tunnel throughput.";
                                        }

                                        leaf total {
                                            type yang:counter64;
                                            units "megabps";
                                            description "Encapsulated and decapsulated IP tunnel throughput.";
                                        }

                                    } // container bytes

                                } // list historical

                            } // container ip

                            container l2tpv3 {
                                description "Enter the l2tpv3 context";

                                container current {
                                    description "Enter the current context";

                                    leaf start-time {
                                        type yang:date-and-time;
                                        description "The time when the sampling interval started.";
                                    }

                                    leaf sampling-duration {
                                        type types-sros:time-duration;
                                        description "The duration of the corresponding sampling interval.";
                                    }

                                    container packets {
                                        description "Enter the packets context";

                                        leaf encapsulated {
                                            type yang:counter64;
                                            units "packets per second";
                                            description "Encapsulated L2TPv3 tunnel throughput.";
                                        }

                                        leaf decapsulated {
                                            type yang:counter64;
                                            units "packets per second";
                                            description "Decapsulated L2TPv3 tunnel throughput.";
                                        }

                                        leaf total {
                                            type yang:counter64;
                                            units "packets per second";
                                            description "Encapsulated and decapsulated L2TPv3 tunnel throughput.";
                                        }

                                    } // container packets

                                    container bytes {
                                        description "Enter the bytes context";

                                        leaf encapsulated {
                                            type yang:counter64;
                                            units "megabps";
                                            description "Encapsulated L2TPv3 tunnel throughput.";
                                        }

                                        leaf decapsulated {
                                            type yang:counter64;
                                            units "megabps";
                                            description "Decapsulated L2TPv3 tunnel throughput.";
                                        }

                                        leaf total {
                                            type yang:counter64;
                                            units "megabps";
                                            description "Encapsulated and decapsulated L2TPv3 tunnel throughput.";
                                        }

                                    } // container bytes

                                } // container current

                                list historical {
                                    key "index";
                                    description "Enter the historical list instance";

                                    leaf index {
                                        type uint32 {
                                            range "2..max";
                                        }
                                        description "The index of the finished sampling interval period for this statistic. It starts with '2' and is ordered by start time of intervals so that smaller index indicate more recent intervals.";
                                    }

                                    leaf start-time {
                                        type yang:date-and-time;
                                        description "The time when the sampling interval started.";
                                    }

                                    leaf sampling-duration {
                                        type types-sros:time-duration;
                                        description "The duration of the corresponding sampling interval.";
                                    }

                                    container packets {
                                        description "Enter the packets context";

                                        leaf encapsulated {
                                            type yang:counter64;
                                            units "packets per second";
                                            description "Encapsulated L2TPv3 tunnel throughput.";
                                        }

                                        leaf decapsulated {
                                            type yang:counter64;
                                            units "packets per second";
                                            description "Decapsulated L2TPv3 tunnel throughput.";
                                        }

                                        leaf total {
                                            type yang:counter64;
                                            units "packets per second";
                                            description "Encapsulated and decapsulated L2TPv3 tunnel throughput.";
                                        }

                                    } // container packets

                                    container bytes {
                                        description "Enter the bytes context";

                                        leaf encapsulated {
                                            type yang:counter64;
                                            units "megabps";
                                            description "Encapsulated L2TPv3 tunnel throughput.";
                                        }

                                        leaf decapsulated {
                                            type yang:counter64;
                                            units "megabps";
                                            description "Decapsulated L2TPv3 tunnel throughput.";
                                        }

                                        leaf total {
                                            type yang:counter64;
                                            units "megabps";
                                            description "Encapsulated and decapsulated L2TPv3 tunnel throughput.";
                                        }

                                    } // container bytes

                                } // list historical

                            } // container l2tpv3

                        } // container throughput

                    } // container ip-tunnel

                    container ipsec {
                        description "Enter the ipsec context";

                        container number-of-tunnels {
                            description "Enter the number-of-tunnels context";

                            container current {
                                description "Enter the current context";

                                leaf static-lan-to-lan {
                                    type yang:counter64;
                                    description "Number of IPsec static LAN-to-LAN (SL2L) tunnels.";
                                }

                                leaf dynamic-lan-to-lan {
                                    type yang:counter64;
                                    description "Number of IPsec dynamic LAN-to-LAN (DL2L) tunnels.";
                                }

                                leaf remote-access {
                                    type yang:counter64;
                                    description "Number of IPsec remote access (RA) tunnels.";
                                }

                                leaf total {
                                    type yang:counter64;
                                    description "Total number of IPsec tunnels.";
                                }

                                leaf start-time {
                                    type yang:date-and-time;
                                    description "The time when the sampling interval started.";
                                }

                            } // container current

                            list historical {
                                key "index";
                                description "Enter the historical list instance";

                                leaf index {
                                    type uint32 {
                                        range "2..max";
                                    }
                                    description "The index of the finished sampling interval period for this statistic. It starts with '2' and is ordered by start time of intervals so that smaller index indicate more recent intervals.";
                                }

                                leaf static-lan-to-lan {
                                    type yang:counter64;
                                    description "Number of IPsec static LAN-to-LAN (SL2L) tunnels.";
                                }

                                leaf dynamic-lan-to-lan {
                                    type yang:counter64;
                                    description "Number of IPsec dynamic LAN-to-LAN (DL2L) tunnels.";
                                }

                                leaf remote-access {
                                    type yang:counter64;
                                    description "Number of IPsec remote access (RA) tunnels.";
                                }

                                leaf total {
                                    type yang:counter64;
                                    description "Total number of IPsec tunnels.";
                                }

                                leaf start-time {
                                    type yang:date-and-time;
                                    description "The time when the sampling interval started.";
                                }

                            } // list historical

                        } // container number-of-tunnels

                        container throughput {
                            description "Enter the throughput context";

                            container current {
                                description "Enter the current context";

                                leaf start-time {
                                    type yang:date-and-time;
                                    description "The time when the sampling interval started.";
                                }

                                leaf sampling-duration {
                                    type types-sros:time-duration;
                                    description "The duration of the corresponding sampling interval.";
                                }

                                container packets {
                                    description "Enter the packets context";

                                    leaf encrypted {
                                        type yang:counter64;
                                        units "packets per second";
                                        description "Encrypted IPsec traffic throughput.";
                                    }

                                    leaf decrypted {
                                        type yang:counter64;
                                        units "packets per second";
                                        description "Decrypted IPsec traffic throughput.";
                                    }

                                    leaf total {
                                        type yang:counter64;
                                        units "packets per second";
                                        description "Encrypted and decrypted IPsec traffic throughput.";
                                    }

                                } // container packets

                                container bytes {
                                    description "Enter the bytes context";

                                    leaf encrypted {
                                        type yang:counter64;
                                        units "megabps";
                                        description "Encrypted IPsec traffic throughput.";
                                    }

                                    leaf decrypted {
                                        type yang:counter64;
                                        units "megabps";
                                        description "Decrypted IPsec traffic throughput.";
                                    }

                                    leaf total {
                                        type yang:counter64;
                                        units "megabps";
                                        description "Encrypted and decrypted IPsec traffic throughput.";
                                    }

                                } // container bytes

                            } // container current

                            list historical {
                                key "index";
                                description "Enter the historical list instance";

                                leaf index {
                                    type uint32 {
                                        range "2..max";
                                    }
                                    description "The index of the finished sampling interval period for this statistic. It starts with '2' and is ordered by start time of intervals so that smaller index indicate more recent intervals.";
                                }

                                leaf start-time {
                                    type yang:date-and-time;
                                    description "The time when the sampling interval started.";
                                }

                                leaf sampling-duration {
                                    type types-sros:time-duration;
                                    description "The duration of the corresponding sampling interval.";
                                }

                                container packets {
                                    description "Enter the packets context";

                                    leaf encrypted {
                                        type yang:counter64;
                                        units "packets per second";
                                        description "Encrypted IPsec traffic throughput.";
                                    }

                                    leaf decrypted {
                                        type yang:counter64;
                                        units "packets per second";
                                        description "Decrypted IPsec traffic throughput.";
                                    }

                                    leaf total {
                                        type yang:counter64;
                                        units "packets per second";
                                        description "Encrypted and decrypted IPsec traffic throughput.";
                                    }

                                } // container packets

                                container bytes {
                                    description "Enter the bytes context";

                                    leaf encrypted {
                                        type yang:counter64;
                                        units "megabps";
                                        description "Encrypted IPsec traffic throughput.";
                                    }

                                    leaf decrypted {
                                        type yang:counter64;
                                        units "megabps";
                                        description "Decrypted IPsec traffic throughput.";
                                    }

                                    leaf total {
                                        type yang:counter64;
                                        units "megabps";
                                        description "Encrypted and decrypted IPsec traffic throughput.";
                                    }

                                } // container bytes

                            } // list historical

                        } // container throughput

                        container tunnel-setup-rate {
                            description "Enter the tunnel-setup-rate context";

                            container current {
                                description "Enter the current context";

                                leaf static-lan-to-lan {
                                    type decimal64 {
                                        fraction-digits 2;
                                    }
                                    units "tunnels per second";
                                    description "Static LAN-to-LAN (SL2L) tunnel setup rate.";
                                }

                                leaf total {
                                    type decimal64 {
                                        fraction-digits 2;
                                    }
                                    units "tunnels per second";
                                    description "Total IPsec tunnel setup rate.";
                                }

                                leaf dynamic-lan-to-lan {
                                    type decimal64 {
                                        fraction-digits 2;
                                    }
                                    units "tunnels per second";
                                    description "Dynamic LAN-to-LAN (DL2L) tunnel setup rate.";
                                }

                                leaf remote-access {
                                    type decimal64 {
                                        fraction-digits 2;
                                    }
                                    units "tunnels per second";
                                    description "Remote access (RA) tunnel setup rate.";
                                }

                                leaf start-time {
                                    type yang:date-and-time;
                                    description "The time when the sampling interval started.";
                                }

                                leaf sampling-duration {
                                    type types-sros:time-duration;
                                    description "The duration of the corresponding sampling interval.";
                                }

                            } // container current

                            list historical {
                                key "index";
                                description "Enter the historical list instance";

                                leaf index {
                                    type uint32 {
                                        range "2..max";
                                    }
                                    description "The index of the finished sampling interval period for this statistic. It starts with '2' and is ordered by start time of intervals so that smaller index indicate more recent intervals.";
                                }

                                leaf static-lan-to-lan {
                                    type decimal64 {
                                        fraction-digits 2;
                                    }
                                    units "tunnels per second";
                                    description "Static LAN-to-LAN (SL2L) tunnel setup rate.";
                                }

                                leaf total {
                                    type decimal64 {
                                        fraction-digits 2;
                                    }
                                    units "tunnels per second";
                                    description "Total IPsec tunnel setup rate.";
                                }

                                leaf dynamic-lan-to-lan {
                                    type decimal64 {
                                        fraction-digits 2;
                                    }
                                    units "tunnels per second";
                                    description "Dynamic LAN-to-LAN (DL2L) tunnel setup rate.";
                                }

                                leaf remote-access {
                                    type decimal64 {
                                        fraction-digits 2;
                                    }
                                    units "tunnels per second";
                                    description "Remote access (RA) tunnel setup rate.";
                                }

                                leaf start-time {
                                    type yang:date-and-time;
                                    description "The time when the sampling interval started.";
                                }

                                leaf sampling-duration {
                                    type types-sros:time-duration;
                                    description "The duration of the corresponding sampling interval.";
                                }

                            } // list historical

                        } // container tunnel-setup-rate

                        container ike-exchange-failure-rate {
                            description "Enter the ike-exchange-failure-rate context";

                            container current {
                                description "Enter the current context";

                                leaf start-time {
                                    type yang:date-and-time;
                                    description "The time when the sampling interval started.";
                                }

                                leaf sampling-duration {
                                    type types-sros:time-duration;
                                    description "The duration of the corresponding sampling interval.";
                                }

                                container auth-failure {
                                    description "Enter the auth-failure context";

                                    leaf count {
                                        type decimal64 {
                                            fraction-digits 2;
                                        }
                                        units "failures per second";
                                        description "IKE exchange failure rate - authentication.";
                                    }

                                    leaf first-failure {
                                        type yang:date-and-time;
                                        description "The time when the first IKE exchange failure happened in the corresponding sampling interval.";
                                    }

                                    leaf first-failure-description {
                                        type types-sros:long-description;
                                        description "The description of the place where the first IKE exchange failure happened.";
                                    }

                                    leaf last-failure {
                                        type yang:date-and-time;
                                        description "The time when the last IKE exchange failure happened in the corresponding sampling interval.";
                                    }

                                    leaf last-failure-description {
                                        type types-sros:long-description;
                                        description "The description of the place where the last IKE exchange failure happened.";
                                    }

                                } // container auth-failure

                                container non-proposal-chosen {
                                    description "Enter the non-proposal-chosen context";

                                    leaf count {
                                        type decimal64 {
                                            fraction-digits 2;
                                        }
                                        units "failures per second";
                                        description "IKE exchange failure rate - non-proposal chosen.";
                                    }

                                    leaf first-failure {
                                        type yang:date-and-time;
                                        description "The time when the first IKE exchange failure happened in the corresponding sampling interval.";
                                    }

                                    leaf first-failure-description {
                                        type types-sros:long-description;
                                        description "The description of the place where the first IKE exchange failure happened.";
                                    }

                                    leaf last-failure {
                                        type yang:date-and-time;
                                        description "The time when the last IKE exchange failure happened in the corresponding sampling interval.";
                                    }

                                    leaf last-failure-description {
                                        type types-sros:long-description;
                                        description "The description of the place where the last IKE exchange failure happened.";
                                    }

                                } // container non-proposal-chosen

                                container internal-address-assignment {
                                    description "Enter the internal-address-assignment context";

                                    leaf count {
                                        type decimal64 {
                                            fraction-digits 2;
                                        }
                                        units "failures per second";
                                        description "IKE exchange failure rate - address assignment.";
                                    }

                                    leaf first-failure {
                                        type yang:date-and-time;
                                        description "The time when the first IKE exchange failure happened in the corresponding sampling interval.";
                                    }

                                    leaf first-failure-description {
                                        type types-sros:long-description;
                                        description "The description of the place where the first IKE exchange failure happened.";
                                    }

                                    leaf last-failure {
                                        type yang:date-and-time;
                                        description "The time when the last IKE exchange failure happened in the corresponding sampling interval.";
                                    }

                                    leaf last-failure-description {
                                        type types-sros:long-description;
                                        description "The description of the place where the last IKE exchange failure happened.";
                                    }

                                } // container internal-address-assignment

                                container invalid-ts {
                                    description "Enter the invalid-ts context";

                                    leaf count {
                                        type decimal64 {
                                            fraction-digits 2;
                                        }
                                        units "failures per second";
                                        description "IKE exchange failure rate - invalid traffic selector.";
                                    }

                                    leaf first-failure {
                                        type yang:date-and-time;
                                        description "The time when the first IKE exchange failure happened in the corresponding sampling interval.";
                                    }

                                    leaf first-failure-description {
                                        type types-sros:long-description;
                                        description "The description of the place where the first IKE exchange failure happened.";
                                    }

                                    leaf last-failure {
                                        type yang:date-and-time;
                                        description "The time when the last IKE exchange failure happened in the corresponding sampling interval.";
                                    }

                                    leaf last-failure-description {
                                        type types-sros:long-description;
                                        description "The description of the place where the last IKE exchange failure happened.";
                                    }

                                } // container invalid-ts

                                container invalid-ke {
                                    description "Enter the invalid-ke context";

                                    leaf count {
                                        type decimal64 {
                                            fraction-digits 2;
                                        }
                                        units "failures per second";
                                        description "IKE exchange failure rate - invalid key exchange.";
                                    }

                                    leaf first-failure {
                                        type yang:date-and-time;
                                        description "The time when the first IKE exchange failure happened in the corresponding sampling interval.";
                                    }

                                    leaf first-failure-description {
                                        type types-sros:long-description;
                                        description "The description of the place where the first IKE exchange failure happened.";
                                    }

                                    leaf last-failure {
                                        type yang:date-and-time;
                                        description "The time when the last IKE exchange failure happened in the corresponding sampling interval.";
                                    }

                                    leaf last-failure-description {
                                        type types-sros:long-description;
                                        description "The description of the place where the last IKE exchange failure happened.";
                                    }

                                } // container invalid-ke

                                container dpd-timeout {
                                    description "Enter the dpd-timeout context";

                                    leaf count {
                                        type decimal64 {
                                            fraction-digits 2;
                                        }
                                        units "failures per second";
                                        description "IKE exchange failure rate - DPD timeout.";
                                    }

                                    leaf first-failure {
                                        type yang:date-and-time;
                                        description "The time when the first IKE exchange failure happened in the corresponding sampling interval.";
                                    }

                                    leaf first-failure-description {
                                        type types-sros:long-description;
                                        description "The description of the place where the first IKE exchange failure happened.";
                                    }

                                    leaf last-failure {
                                        type yang:date-and-time;
                                        description "The time when the last IKE exchange failure happened in the corresponding sampling interval.";
                                    }

                                    leaf last-failure-description {
                                        type types-sros:long-description;
                                        description "The description of the place where the last IKE exchange failure happened.";
                                    }

                                } // container dpd-timeout

                                container other {
                                    description "Enter the other context";

                                    leaf count {
                                        type decimal64 {
                                            fraction-digits 2;
                                        }
                                        units "failures per second";
                                        description "IKE exchange failure rate - other failure reasons.";
                                    }

                                    leaf first-failure {
                                        type yang:date-and-time;
                                        description "The time when the first IKE exchange failure happened in the corresponding sampling interval.";
                                    }

                                    leaf first-failure-description {
                                        type types-sros:long-description;
                                        description "The description of the place where the first IKE exchange failure happened.";
                                    }

                                    leaf last-failure {
                                        type yang:date-and-time;
                                        description "The time when the last IKE exchange failure happened in the corresponding sampling interval.";
                                    }

                                    leaf last-failure-description {
                                        type types-sros:long-description;
                                        description "The description of the place where the last IKE exchange failure happened.";
                                    }

                                } // container other

                            } // container current

                            list historical {
                                key "index";
                                description "Enter the historical list instance";

                                leaf index {
                                    type uint32 {
                                        range "2..max";
                                    }
                                    description "The index of the finished sampling interval period for this statistic. It starts with '2' and is ordered by start time of intervals so that smaller index indicate more recent intervals.";
                                }

                                leaf start-time {
                                    type yang:date-and-time;
                                    description "The time when the sampling interval started.";
                                }

                                leaf sampling-duration {
                                    type types-sros:time-duration;
                                    description "The duration of the corresponding sampling interval.";
                                }

                                container auth-failure {
                                    description "Enter the auth-failure context";

                                    leaf count {
                                        type decimal64 {
                                            fraction-digits 2;
                                        }
                                        units "failures per second";
                                        description "IKE exchange failure rate - authentication.";
                                    }

                                    leaf first-failure {
                                        type yang:date-and-time;
                                        description "The time when the first IKE exchange failure happened in the corresponding sampling interval.";
                                    }

                                    leaf first-failure-description {
                                        type types-sros:long-description;
                                        description "The description of the place where the first IKE exchange failure happened.";
                                    }

                                    leaf last-failure {
                                        type yang:date-and-time;
                                        description "The time when the last IKE exchange failure happened in the corresponding sampling interval.";
                                    }

                                    leaf last-failure-description {
                                        type types-sros:long-description;
                                        description "The description of the place where the last IKE exchange failure happened.";
                                    }

                                } // container auth-failure

                                container non-proposal-chosen {
                                    description "Enter the non-proposal-chosen context";

                                    leaf count {
                                        type decimal64 {
                                            fraction-digits 2;
                                        }
                                        units "failures per second";
                                        description "IKE exchange failure rate - non-proposal chosen.";
                                    }

                                    leaf first-failure {
                                        type yang:date-and-time;
                                        description "The time when the first IKE exchange failure happened in the corresponding sampling interval.";
                                    }

                                    leaf first-failure-description {
                                        type types-sros:long-description;
                                        description "The description of the place where the first IKE exchange failure happened.";
                                    }

                                    leaf last-failure {
                                        type yang:date-and-time;
                                        description "The time when the last IKE exchange failure happened in the corresponding sampling interval.";
                                    }

                                    leaf last-failure-description {
                                        type types-sros:long-description;
                                        description "The description of the place where the last IKE exchange failure happened.";
                                    }

                                } // container non-proposal-chosen

                                container internal-address-assignment {
                                    description "Enter the internal-address-assignment context";

                                    leaf count {
                                        type decimal64 {
                                            fraction-digits 2;
                                        }
                                        units "failures per second";
                                        description "IKE exchange failure rate - address assignment.";
                                    }

                                    leaf first-failure {
                                        type yang:date-and-time;
                                        description "The time when the first IKE exchange failure happened in the corresponding sampling interval.";
                                    }

                                    leaf first-failure-description {
                                        type types-sros:long-description;
                                        description "The description of the place where the first IKE exchange failure happened.";
                                    }

                                    leaf last-failure {
                                        type yang:date-and-time;
                                        description "The time when the last IKE exchange failure happened in the corresponding sampling interval.";
                                    }

                                    leaf last-failure-description {
                                        type types-sros:long-description;
                                        description "The description of the place where the last IKE exchange failure happened.";
                                    }

                                } // container internal-address-assignment

                                container invalid-ts {
                                    description "Enter the invalid-ts context";

                                    leaf count {
                                        type decimal64 {
                                            fraction-digits 2;
                                        }
                                        units "failures per second";
                                        description "IKE exchange failure rate - invalid traffic selector.";
                                    }

                                    leaf first-failure {
                                        type yang:date-and-time;
                                        description "The time when the first IKE exchange failure happened in the corresponding sampling interval.";
                                    }

                                    leaf first-failure-description {
                                        type types-sros:long-description;
                                        description "The description of the place where the first IKE exchange failure happened.";
                                    }

                                    leaf last-failure {
                                        type yang:date-and-time;
                                        description "The time when the last IKE exchange failure happened in the corresponding sampling interval.";
                                    }

                                    leaf last-failure-description {
                                        type types-sros:long-description;
                                        description "The description of the place where the last IKE exchange failure happened.";
                                    }

                                } // container invalid-ts

                                container invalid-ke {
                                    description "Enter the invalid-ke context";

                                    leaf count {
                                        type decimal64 {
                                            fraction-digits 2;
                                        }
                                        units "failures per second";
                                        description "IKE exchange failure rate - invalid key exchange.";
                                    }

                                    leaf first-failure {
                                        type yang:date-and-time;
                                        description "The time when the first IKE exchange failure happened in the corresponding sampling interval.";
                                    }

                                    leaf first-failure-description {
                                        type types-sros:long-description;
                                        description "The description of the place where the first IKE exchange failure happened.";
                                    }

                                    leaf last-failure {
                                        type yang:date-and-time;
                                        description "The time when the last IKE exchange failure happened in the corresponding sampling interval.";
                                    }

                                    leaf last-failure-description {
                                        type types-sros:long-description;
                                        description "The description of the place where the last IKE exchange failure happened.";
                                    }

                                } // container invalid-ke

                                container dpd-timeout {
                                    description "Enter the dpd-timeout context";

                                    leaf count {
                                        type decimal64 {
                                            fraction-digits 2;
                                        }
                                        units "failures per second";
                                        description "IKE exchange failure rate - DPD timeout.";
                                    }

                                    leaf first-failure {
                                        type yang:date-and-time;
                                        description "The time when the first IKE exchange failure happened in the corresponding sampling interval.";
                                    }

                                    leaf first-failure-description {
                                        type types-sros:long-description;
                                        description "The description of the place where the first IKE exchange failure happened.";
                                    }

                                    leaf last-failure {
                                        type yang:date-and-time;
                                        description "The time when the last IKE exchange failure happened in the corresponding sampling interval.";
                                    }

                                    leaf last-failure-description {
                                        type types-sros:long-description;
                                        description "The description of the place where the last IKE exchange failure happened.";
                                    }

                                } // container dpd-timeout

                                container other {
                                    description "Enter the other context";

                                    leaf count {
                                        type decimal64 {
                                            fraction-digits 2;
                                        }
                                        units "failures per second";
                                        description "IKE exchange failure rate - other failure reasons.";
                                    }

                                    leaf first-failure {
                                        type yang:date-and-time;
                                        description "The time when the first IKE exchange failure happened in the corresponding sampling interval.";
                                    }

                                    leaf first-failure-description {
                                        type types-sros:long-description;
                                        description "The description of the place where the first IKE exchange failure happened.";
                                    }

                                    leaf last-failure {
                                        type yang:date-and-time;
                                        description "The time when the last IKE exchange failure happened in the corresponding sampling interval.";
                                    }

                                    leaf last-failure-description {
                                        type types-sros:long-description;
                                        description "The description of the place where the last IKE exchange failure happened.";
                                    }

                                } // container other

                            } // list historical

                        } // container ike-exchange-failure-rate

                    } // container ipsec

                } // container statistics

            } // list tunnel-group

            list nat-group {
                key "id";
                description "Enter the nat-group list instance";

                leaf id {
                    type uint32 {
                        range "1..4";
                    }
                    description "NAT group ID";
                }

                leaf oper-state {
                    type types-sros:oper-state;
                    description "The value of tmnxNatIsaGrpOperState indicates the operational status of this NAT ISA group";
                }

                leaf degraded {
                    type boolean;
                    description "indicates if this NAT ISA group is degraded, while operationally still in service";
                }

                container redundancy {
                    description "Enter the redundancy context";

                    choice redundancy-mode {
                        case inter-chassis {

                            container inter-chassis {
                                description "Enter the inter-chassis context";

                                leaf state {
                                    type enumeration {
                                        enum "disabled"                     { value 0; }
                                        enum "initial-wait-for-peer"        { value 2; }
                                        enum "wait-for-peer"                { value 3; }
                                        enum "peer-timed-out"               { value 4; }
                                        enum "active"                       { value 5; }
                                        enum "standby"                      { value 6; }
                                        enum "cleaning-up"                  { value 7; }
                                    }
                                    description "The state of the inter-chassis redundancy synchronization of this ISA NAT group";
                                }

                                leaf state-changes {
                                    type yang:counter32;
                                    description "The number of times the state has changed";
                                }

                                leaf state-last-changed {
                                    type yang:date-and-time;
                                    description "Time of the last state change";
                                }

                                leaf in-control {
                                    type boolean;
                                    description "Indication that this system is in control of the inter-chassis redundancy sychronization, not the peer";
                                }

                                leaf health {
                                    type uint32;
                                    description "The actual health of the ISA NAT group on this system";
                                }

                                leaf peer-health {
                                    type uint32;
                                    description "The actual health of the ISA NAT group on the peer";
                                }

                                leaf peer-preferred {
                                    type boolean;
                                    description "Indicates if the peer is configured as preferred";
                                }

                                list monitor-port {
                                    key "port-id";
                                    description "Enter the monitor-port list instance";

                                    leaf port-id {
                                        type types-sros:port-named;
                                        description "Port ID";
                                    }

                                    leaf actual-health-drop {
                                        type uint32;
                                        description "The actual health drop of the ISA NAT group caused by this monitor port or operational group";
                                    }

                                } // list monitor-port

                                list monitor-oper-group {
                                    key "oper-group";
                                    description "Enter the monitor-oper-group list instance";

                                    leaf oper-group {
                                        type leafref {
                                            path "../../../../../../service/oper-group/name";
                                        }
                                        description "Operational group name";
                                    }

                                    leaf actual-health-drop {
                                        type uint32;
                                        description "The actual health drop of the ISA NAT group caused by this monitor port or operational group";
                                    }

                                } // list monitor-oper-group

                                container statistics {
                                    description "Enter the statistics context";

                                    leaf transmitted-frames {
                                        type yang:counter64;
                                        description "Number of frames transmitted to the peer";
                                    }

                                    leaf transmission-failures {
                                        type yang:counter64;
                                        description "Number of transmission failures";
                                    }

                                    leaf received-frames {
                                        type yang:counter64;
                                        description "Number of frames received from the peer";
                                    }

                                    leaf receive-failures-wrong-peer {
                                        type yang:counter64;
                                        description "Number of frames dropped because not sent by the configured peer";
                                    }

                                    leaf keepalive-timeouts {
                                        type yang:counter64;
                                        description "Number of times a keepalive timeout occurred";
                                    }

                                } // container statistics

                            } // container inter-chassis

                        }
                    }
                } // container redundancy

                list member {
                    key "id";
                    description "Enter the member list instance";

                    leaf id {
                        type types-nat:bb-group-member;
                        description "Nat-group member identifier";
                    }

                    leaf state {
                        type enumeration {
                            enum "inactive"                     { value 1; }
                            enum "active"                       { value 2; }
                            enum "needs-reset"                  { value 3; }
                            enum "resetting"                    { value 4; }
                            enum "needs-reconcile"              { value 5; }
                            enum "reconciling"                  { value 6; }
                            enum "needs-audit"                  { value 7; }
                            enum "auditing"                     { value 8; }
                            enum "failed-bypass"                { value 9; }
                            enum "active-bypass"                { value 10; }
                        }
                        description "The state of the MDA or ESA-VM associated with this member";
                    }

                    leaf associated-mda {
                        type types-isa:slot-mda;
                        description "MDA on which this member resides";
                    }

                    leaf allocated-resources {
                        type uint32 {
                            range "0..100";
                        }
                        description "the ratio of allocated resources to total resources on this NAT ISA member";
                    }

                    leaf reserved-outside-ip-addresses {
                        type yang:gauge32;
                        description "The number of outside IP addresses reserved for the MDA or ESA-VM associated with this member";
                    }

                    leaf outside-port-blocks {
                        type yang:gauge32;
                        description "The number of outside port blocks reserved for the MDA or ESA-VM associated with this member";
                    }

                    leaf session-usage {
                        type types-isa:nat-usage-level;
                        description "The session usage of the MDA or ESA-VM associated with this member";
                    }

                    leaf high-session-usage {
                        type boolean;
                        description "Indicates if the session usage of the MDA or ESA-VM associated with this member is high according to the values of watermark definitions";
                    }

                    leaf prioritized-sessions {
                        type yang:gauge32;
                        description "The current number of active prioritized sessions of the MDA or ESA-VM associated with this member";
                    }

                    container associated-esa-vm {
                        description "Enter the associated-esa-vm context";

                        leaf esa {
                            type types-esa:esa-id;
                            description "ESA on which this member resides";
                        }

                        leaf vm {
                            type types-esa:vm-id;
                            description "ESA-VM on which this member resides";
                        }

                    } // container associated-esa-vm

                    container inter-chassis-redundancy {
                        description "Enter the inter-chassis-redundancy context";

                        leaf state {
                            type enumeration {
                                enum "disabled"                     { value 0; }
                                enum "waiting-selection"            { value 1; }
                                enum "cleaning-up"                  { value 2; }
                                enum "negotiating"                  { value 3; }
                                enum "active"                       { value 4; }
                                enum "standby"                      { value 5; }
                            }
                            description "The state of the inter-chassis redundancy synchronization of this ISA NAT group member";
                        }

                        leaf peer-state {
                            type enumeration {
                                enum "active"                       { value 1; }
                                enum "standby"                      { value 2; }
                            }
                            description "The state of the peer for this ISA NAT group member";
                        }

                        leaf local-ip-address {
                            type types-sros:ipv4-unicast-address;
                            description "IP address used by this system for this member";
                        }

                        leaf remote-ip-address {
                            type types-sros:ipv4-unicast-address;
                            description "IP address used by the peer for this member";
                        }

                        leaf last-failed {
                            type yang:date-and-time;
                            description "Time of the last failure";
                        }

                        leaf failure-reason {
                            type string {
                                length "0..255";
                            }
                            description "Reason of the last failure";
                        }

                        leaf unsupported-flows {
                            type yang:gauge64;
                            description "The number of unsupported flows (e.g. ALG pinholes)";
                        }

                        leaf tracked-flows {
                            type yang:gauge64;
                            description "The number of flows tracked for synchronization";
                        }

                        leaf tracked-flows-not-synced {
                            type yang:gauge64;
                            description "The number of tracked flows not yet synchronized";
                        }

                        leaf tracked-flows-pending {
                            type yang:gauge64;
                            description "The number of tracked flows for which synchronization is requested but not yet confirmed";
                        }

                        leaf flows-synced {
                            type yang:gauge64;
                            description "The number of tracked flows for which synchronization is confirmed";
                        }

                        leaf flows-marked-to-delete {
                            type yang:gauge64;
                            description "The number of flows that are deleted on the active node and synchronization not yet requested";
                        }

                        leaf flows-delete-pending {
                            type yang:gauge64;
                            description "The number of flows that are deleted on the active node for which synchronization is requested but not yet confirmed";
                        }

                    } // container inter-chassis-redundancy

                    container statistics {
                        description "Enter the statistics context";

                        container inter-chassis-redundancy {
                            description "Enter the inter-chassis-redundancy context";

                            leaf transmitted-frames {
                                type yang:counter64;
                                description "Number of frames transmitted to the peer";
                            }

                            leaf retransmitted-frames {
                                type yang:counter64;
                                description "Number of frames retransmitted to the peer";
                            }

                            leaf transmitted-flow-creates {
                                type yang:counter64;
                                description "Number of transmitted flow create messages";
                            }

                            leaf transmitted-flow-deletes {
                                type yang:counter64;
                                description "Number of transmitted flow delete messages";
                            }

                            leaf transmitted-alg-frames {
                                type yang:counter64;
                                description "Number of transmitted Application Level Gateway (ALG) frames";
                            }

                            leaf received-frames {
                                type yang:counter64;
                                description "Number of frames received from the peer";
                            }

                            leaf received-flow-creates {
                                type yang:counter64;
                                description "Number of flow create messages received";
                            }

                            leaf received-flow-deletes {
                                type yang:counter64;
                                description "Number of flow delete messages received";
                            }

                            leaf received-alg-frames {
                                type yang:counter64;
                                description "Number of ALG frames received";
                            }

                            leaf dropped-flow-creates-no-policy {
                                type yang:counter64;
                                description "Number of flow create messages dropped because the nat-policy could not be found";
                            }

                            leaf dropped-flow-creates-no-port-block {
                                type yang:counter64;
                                description "Number of flow create messages dropped because the port block could not be found";
                            }

                            leaf received-fragments {
                                type yang:counter64;
                                description "Number of fragments received";
                            }

                        } // container inter-chassis-redundancy

                    } // container statistics

                    container resources {
                        description "Enter the resources context";

                        container port-ranges {
                            description "Enter the port-ranges context";

                            container configured {
                                description "Enter the configured context";

                                leaf value {
                                    type yang:gauge64;
                                    description "Actual consumed value";
                                }

                                leaf max {
                                    type uint64;
                                    description "The max value this resource can have, depending on the configuration";
                                }

                                leaf peak {
                                    type yang:gauge64;
                                    description "The peak value for the resource";
                                }

                                leaf peak-timestamp {
                                    type types-sros:date-time;
                                    description "The timestamp when the peak value was observed";
                                }

                            } // container configured

                            container used {
                                description "Enter the used context";

                                leaf value {
                                    type yang:gauge64;
                                    description "Actual consumed value";
                                }

                                leaf max {
                                    type uint64;
                                    description "The max value this resource can have, depending on the configuration";
                                }

                                leaf peak {
                                    type yang:gauge64;
                                    description "The peak value for the resource";
                                }

                                leaf peak-timestamp {
                                    type types-sros:date-time;
                                    description "The timestamp when the peak value was observed";
                                }

                            } // container used

                            container retained {
                                description "Enter the retained context";

                                leaf value {
                                    type yang:gauge64;
                                    description "Actual consumed value";
                                }

                                leaf max {
                                    type uint64;
                                    description "The max value this resource can have, depending on the configuration";
                                }

                                leaf peak {
                                    type yang:gauge64;
                                    description "The peak value for the resource";
                                }

                                leaf peak-timestamp {
                                    type types-sros:date-time;
                                    description "The timestamp when the peak value was observed";
                                }

                            } // container retained

                        } // container port-ranges

                        container ports {
                            description "Enter the ports context";

                            leaf value {
                                type yang:gauge64;
                                description "Actual consumed value";
                            }

                            leaf max {
                                type uint64;
                                description "The max value this resource can have, depending on the configuration";
                            }

                            leaf peak {
                                type yang:gauge64;
                                description "The peak value for the resource";
                            }

                            leaf peak-timestamp {
                                type types-sros:date-time;
                                description "The timestamp when the peak value was observed";
                            }

                        } // container ports

                        container ip-addresses {
                            description "Enter the ip-addresses context";

                            leaf value {
                                type yang:gauge64;
                                description "Actual consumed value";
                            }

                            leaf max {
                                type uint64;
                                description "The max value this resource can have, depending on the configuration";
                            }

                            leaf peak {
                                type yang:gauge64;
                                description "The peak value for the resource";
                            }

                            leaf peak-timestamp {
                                type types-sros:date-time;
                                description "The timestamp when the peak value was observed";
                            }

                        } // container ip-addresses

                        container one-to-one-ip-addresses {
                            description "Enter the one-to-one-ip-addresses context";

                            leaf value {
                                type yang:gauge64;
                                description "Actual consumed value";
                            }

                            leaf max {
                                type uint64;
                                description "The max value this resource can have, depending on the configuration";
                            }

                            leaf peak {
                                type yang:gauge64;
                                description "The peak value for the resource";
                            }

                            leaf peak-timestamp {
                                type types-sros:date-time;
                                description "The timestamp when the peak value was observed";
                            }

                        } // container one-to-one-ip-addresses

                        container large-scale-hosts {
                            description "Enter the large-scale-hosts context";

                            leaf value {
                                type yang:gauge64;
                                description "Actual consumed value";
                            }

                            leaf max {
                                type uint64;
                                description "The max value this resource can have, depending on the configuration";
                            }

                            leaf peak {
                                type yang:gauge64;
                                description "The peak value for the resource";
                            }

                            leaf peak-timestamp {
                                type types-sros:date-time;
                                description "The timestamp when the peak value was observed";
                            }

                        } // container large-scale-hosts

                        container l2-aware {
                            description "Enter the l2-aware context";

                            container subscribers {
                                description "Enter the subscribers context";

                                leaf value {
                                    type yang:gauge64;
                                    description "Actual consumed value";
                                }

                                leaf max {
                                    type uint64;
                                    description "The max value this resource can have, depending on the configuration";
                                }

                                leaf peak {
                                    type yang:gauge64;
                                    description "The peak value for the resource";
                                }

                                leaf peak-timestamp {
                                    type types-sros:date-time;
                                    description "The timestamp when the peak value was observed";
                                }

                            } // container subscribers

                            container hosts {
                                description "Enter the hosts context";

                                leaf value {
                                    type yang:gauge64;
                                    description "Actual consumed value";
                                }

                                leaf max {
                                    type uint64;
                                    description "The max value this resource can have, depending on the configuration";
                                }

                                leaf peak {
                                    type yang:gauge64;
                                    description "The peak value for the resource";
                                }

                                leaf peak-timestamp {
                                    type types-sros:date-time;
                                    description "The timestamp when the peak value was observed";
                                }

                            } // container hosts

                        } // container l2-aware

                    } // container resources

                } // list member

                list mda {
                    key "mda-id";
                    description "Enter the mda list instance";

                    leaf mda-id {
                        type types-isa:slot-mda;
                        description "MDA ID for ISA NAT group";
                    }

                    leaf layer-2-hosts-bypassed {
                        type uint32;
                        description "number of Layer-2 aware NAT hosts being bypassed for this ISA MDA";
                    }

                    leaf oper-state {
                        type types-isa:nat-member-operational-state;
                        description "the operational state of this NAT ISA MDA";
                    }

                    leaf allocated-resources {
                        type uint32 {
                            range "0..100";
                        }
                        description "the ratio of allocated resources to total resources on this NAT ISA MDA";
                    }

                    leaf peak-values-last-reset {
                        type yang:date-and-time;
                        description "Moment when the peak values were last reset (applicable to both NAT ISA MDA and member resources)";
                    }

                    container resources {
                        description "Enter the resources context";

                        container flows {
                            description "Enter the flows context";

                            leaf value {
                                type yang:gauge64;
                                description "Actual consumed value";
                            }

                            leaf max {
                                type uint64;
                                description "The max value this resource can have, depending on the configuration";
                            }

                            leaf peak {
                                type yang:gauge64;
                                description "The peak value for the resource";
                            }

                            leaf peak-timestamp {
                                type types-sros:date-time;
                                description "The timestamp when the peak value was observed";
                            }

                        } // container flows

                        container policies {
                            description "Enter the policies context";

                            leaf value {
                                type yang:gauge64;
                                description "Actual consumed value";
                            }

                            leaf max {
                                type uint64;
                                description "The max value this resource can have, depending on the configuration";
                            }

                            leaf peak {
                                type yang:gauge64;
                                description "The peak value for the resource";
                            }

                            leaf peak-timestamp {
                                type types-sros:date-time;
                                description "The timestamp when the peak value was observed";
                            }

                        } // container policies

                        container subscriber-cache-entries {
                            description "Enter the subscriber-cache-entries context";

                            leaf value {
                                type yang:gauge64;
                                description "Actual consumed value";
                            }

                            leaf max {
                                type uint64;
                                description "The max value this resource can have, depending on the configuration";
                            }

                            leaf peak {
                                type yang:gauge64;
                                description "The peak value for the resource";
                            }

                            leaf peak-timestamp {
                                type types-sros:date-time;
                                description "The timestamp when the peak value was observed";
                            }

                        } // container subscriber-cache-entries

                        container delayed-icmps {
                            description "Enter the delayed-icmps context";

                            leaf value {
                                type yang:gauge64;
                                description "Actual consumed value";
                            }

                            leaf max {
                                type uint64;
                                description "The max value this resource can have, depending on the configuration";
                            }

                            leaf peak {
                                type yang:gauge64;
                                description "The peak value for the resource";
                            }

                            leaf peak-timestamp {
                                type types-sros:date-time;
                                description "The timestamp when the peak value was observed";
                            }

                        } // container delayed-icmps

                        container alg-session {
                            description "Enter the alg-session context";

                            leaf value {
                                type yang:gauge64;
                                description "Actual consumed value";
                            }

                            leaf max {
                                type uint64;
                                description "The max value this resource can have, depending on the configuration";
                            }

                            leaf peak {
                                type yang:gauge64;
                                description "The peak value for the resource";
                            }

                            leaf peak-timestamp {
                                type types-sros:date-time;
                                description "The timestamp when the peak value was observed";
                            }

                        } // container alg-session

                        container fragment-lists {
                            description "Enter the fragment-lists context";

                            container upstream {
                                description "Enter the upstream context";

                                leaf value {
                                    type yang:gauge64;
                                    description "Actual consumed value";
                                }

                                leaf max {
                                    type uint64;
                                    description "The max value this resource can have, depending on the configuration";
                                }

                                leaf peak {
                                    type yang:gauge64;
                                    description "The peak value for the resource";
                                }

                                leaf peak-timestamp {
                                    type types-sros:date-time;
                                    description "The timestamp when the peak value was observed";
                                }

                            } // container upstream

                            container downstream {
                                description "Enter the downstream context";

                                leaf value {
                                    type yang:gauge64;
                                    description "Actual consumed value";
                                }

                                leaf max {
                                    type uint64;
                                    description "The max value this resource can have, depending on the configuration";
                                }

                                leaf peak {
                                    type yang:gauge64;
                                    description "The peak value for the resource";
                                }

                                leaf peak-timestamp {
                                    type types-sros:date-time;
                                    description "The timestamp when the peak value was observed";
                                }

                            } // container downstream

                        } // container fragment-lists

                        container fragment-holes {
                            description "Enter the fragment-holes context";

                            container upstream {
                                description "Enter the upstream context";

                                leaf value {
                                    type yang:gauge64;
                                    description "Actual consumed value";
                                }

                                leaf max {
                                    type uint64;
                                    description "The max value this resource can have, depending on the configuration";
                                }

                                leaf peak {
                                    type yang:gauge64;
                                    description "The peak value for the resource";
                                }

                                leaf peak-timestamp {
                                    type types-sros:date-time;
                                    description "The timestamp when the peak value was observed";
                                }

                            } // container upstream

                            container downstream {
                                description "Enter the downstream context";

                                leaf value {
                                    type yang:gauge64;
                                    description "Actual consumed value";
                                }

                                leaf max {
                                    type uint64;
                                    description "The max value this resource can have, depending on the configuration";
                                }

                                leaf peak {
                                    type yang:gauge64;
                                    description "The peak value for the resource";
                                }

                                leaf peak-timestamp {
                                    type types-sros:date-time;
                                    description "The timestamp when the peak value was observed";
                                }

                            } // container downstream

                        } // container fragment-holes

                        container fragment-bufs {
                            description "Enter the fragment-bufs context";

                            container upstream {
                                description "Enter the upstream context";

                                leaf value {
                                    type yang:gauge64;
                                    description "Actual consumed value";
                                }

                                leaf max {
                                    type uint64;
                                    description "The max value this resource can have, depending on the configuration";
                                }

                                leaf peak {
                                    type yang:gauge64;
                                    description "The peak value for the resource";
                                }

                                leaf peak-timestamp {
                                    type types-sros:date-time;
                                    description "The timestamp when the peak value was observed";
                                }

                            } // container upstream

                            container downstream {
                                description "Enter the downstream context";

                                leaf value {
                                    type yang:gauge64;
                                    description "Actual consumed value";
                                }

                                leaf max {
                                    type uint64;
                                    description "The max value this resource can have, depending on the configuration";
                                }

                                leaf peak {
                                    type yang:gauge64;
                                    description "The peak value for the resource";
                                }

                                leaf peak-timestamp {
                                    type types-sros:date-time;
                                    description "The timestamp when the peak value was observed";
                                }

                            } // container downstream

                        } // container fragment-bufs

                        container upnp {
                            description "Enter the upnp context";

                            container mappings {
                                description "Enter the mappings context";

                                leaf value {
                                    type yang:gauge64;
                                    description "Actual consumed value";
                                }

                                leaf max {
                                    type uint64;
                                    description "The max value this resource can have, depending on the configuration";
                                }

                                leaf peak {
                                    type yang:gauge64;
                                    description "The peak value for the resource";
                                }

                                leaf peak-timestamp {
                                    type types-sros:date-time;
                                    description "The timestamp when the peak value was observed";
                                }

                            } // container mappings

                            container sessions {
                                description "Enter the sessions context";

                                leaf value {
                                    type yang:gauge64;
                                    description "Actual consumed value";
                                }

                                leaf max {
                                    type uint64;
                                    description "The max value this resource can have, depending on the configuration";
                                }

                                leaf peak {
                                    type yang:gauge64;
                                    description "The peak value for the resource";
                                }

                                leaf peak-timestamp {
                                    type types-sros:date-time;
                                    description "The timestamp when the peak value was observed";
                                }

                            } // container sessions

                        } // container upnp

                        container pppoe-sessions {
                            description "Enter the pppoe-sessions context";

                            leaf value {
                                type yang:gauge64;
                                description "Actual consumed value";
                            }

                            leaf max {
                                type uint64;
                                description "The max value this resource can have, depending on the configuration";
                            }

                            leaf peak {
                                type yang:gauge64;
                                description "The peak value for the resource";
                            }

                            leaf peak-timestamp {
                                type types-sros:date-time;
                                description "The timestamp when the peak value was observed";
                            }

                        } // container pppoe-sessions

                    } // container resources

                    container statistics {
                        description "Enter the statistics context";

                        container ip-forwarding {
                            description "Enter the ip-forwarding context";

                            leaf fragments {
                                type yang:counter64;
                                description "Fragments handled";
                            }

                            leaf reassembled-packets {
                                type yang:counter64;
                                description "Frames reassembled";
                            }

                            leaf forwarded-packets {
                                type yang:counter64;
                                description "Frames forwarded";
                            }

                            container receive-errors {
                                description "Enter the receive-errors context";

                                leaf l2-error {
                                    type yang:counter64;
                                    description "L2 parse error";
                                }

                                leaf l3-not-ip {
                                    type yang:counter64;
                                    description "L3 is not IPv4 or IPv6";
                                }

                                leaf ip-invalid-checksum {
                                    type yang:counter64;
                                    description "IPv4 invalid checksum";
                                }

                                leaf ip-malformed-header {
                                    type yang:counter64;
                                    description "IP malformed header";
                                }

                                leaf ip-malformed-packet {
                                    type yang:counter64;
                                    description "IP malformed packet";
                                }

                                leaf ip-zero-ttl {
                                    type yang:counter64;
                                    description "IP zero ttl";
                                }

                                leaf ip-opts-or-ext-headers {
                                    type yang:counter64;
                                    description "IPv4 options or IPv6 extension headers";
                                }

                                leaf ip-fragment-unsupported {
                                    type yang:counter64;
                                    description "IP fragment unsupported";
                                }

                                leaf ip-error {
                                    type yang:counter64;
                                    description "IP parse error";
                                }

                                leaf tcp-udp-malformed-header {
                                    type yang:counter64;
                                    description "TCP/UDP malformed header";
                                }

                                leaf tcp-udp-invalid-checksum {
                                    type yang:counter64;
                                    description "TCP/UDP invalid checksum";
                                }

                                leaf other {
                                    type yang:counter64;
                                    description "Other parse error";
                                }

                            } // container receive-errors

                            container reassembly-errors {
                                description "Enter the reassembly-errors context";

                                leaf too-many-fragmented-packets {
                                    type yang:counter64;
                                    description "Too many fragmented packets";
                                }

                                leaf too-many-fragment-buffers {
                                    type yang:counter64;
                                    description "Too many fragment buffers";
                                }

                                leaf too-many-fragment-holes {
                                    type yang:counter64;
                                    description "Too many fragment holes";
                                }

                                leaf fragment-filtered {
                                    type yang:counter64;
                                    description "Fragments filtered";
                                }

                                leaf fragment-not-supported {
                                    type yang:counter64;
                                    description "Fragment not supported";
                                }

                                leaf fragment-list-expired {
                                    type yang:counter64;
                                    description "Fragment list expired";
                                }

                                leaf fragment-list-cleanup-in-progress {
                                    type yang:counter64;
                                    description "Fragment list cleanup in progress";
                                }

                                leaf reassembly-failed {
                                    type yang:counter64;
                                    description "Reassembly failed";
                                }

                            } // container reassembly-errors

                        } // container ip-forwarding

                        container pppoe-client {
                            description "Enter the pppoe-client context";

                            leaf rx-error-l2 {
                                type yang:counter64;
                                description "Number of packets received with layer 2 parse errors";
                            }

                            leaf rx-error-invalid-headers {
                                type yang:counter64;
                                description "Number of packets received with invalid PPPoE headers";
                            }

                            leaf rx-error-invalid-magic {
                                type yang:counter64;
                                description "Number of LCP echo-request or echo-reply packets received with an invalid magic number";
                            }

                            leaf rx-error-no-session {
                                type yang:counter64;
                                description "Number of LCP echo or data packets received without an associated session";
                            }

                            leaf rx-discovery {
                                type yang:counter64;
                                description "Number of PPPoE discovery packets received";
                            }

                            leaf rx-ppp-control {
                                type yang:counter64;
                                description "Number of PPP control packets received";
                            }

                            leaf rx-lcp-echo-request {
                                type yang:counter64;
                                description "Number of LCP echo-request packets received";
                            }

                            leaf rx-lcp-echo-reply {
                                type yang:counter64;
                                description "Number of LCP echo-reply packets received";
                            }

                            leaf tx-lcp-echo-request {
                                type yang:counter64;
                                description "Number of LCP echo-request packets transmitted";
                            }

                            leaf tx-lcp-echo-reply {
                                type yang:counter64;
                                description "Number of LCP echo-reply packets transmitted";
                            }

                        } // container pppoe-client

                        container nat {
                            description "Enter the nat context";

                            container dropped {
                                description "Enter the dropped context";

                                container general {
                                    description "Enter the general context";

                                    leaf arp {
                                        type yang:counter64;
                                        description "ARP frames are ignored";
                                    }

                                    leaf checksum-calculation-error {
                                        type yang:counter64;
                                        description "Error while calculating L4 checksum before transmitting";
                                    }

                                    leaf send-error {
                                        type yang:counter64;
                                        description "Packet send error";
                                    }

                                    leaf no-copy-buffer {
                                        type yang:counter64;
                                        description "No buffer to copy frame";
                                    }

                                    leaf mtu-exceeded {
                                        type yang:counter64;
                                        description "Egress MTU exceeded";
                                    }

                                    leaf multicast {
                                        type yang:counter64;
                                        description "Multicast dropped";
                                    }

                                } // container general

                                container receive-errors {
                                    description "Enter the receive-errors context";

                                    leaf l2-error {
                                        type yang:counter64;
                                        description "L2 parse error";
                                    }

                                    leaf l3-not-ip {
                                        type yang:counter64;
                                        description "L3 is not IPv4 or IPv6";
                                    }

                                    leaf ip-invalid-checksum {
                                        type yang:counter64;
                                        description "IPv4 invalid checksum";
                                    }

                                    leaf ip-malformed-header {
                                        type yang:counter64;
                                        description "IP malformed header";
                                    }

                                    leaf ip-malformed-packet {
                                        type yang:counter64;
                                        description "IP malformed packet";
                                    }

                                    leaf ip-zero-ttl {
                                        type yang:counter64;
                                        description "IP zero ttl";
                                    }

                                    leaf ip-opts-or-ext-headers {
                                        type yang:counter64;
                                        description "IPv4 options or IPv6 extension headers";
                                    }

                                    leaf ip-parse-error {
                                        type yang:counter64;
                                        description "IP parse error";
                                    }

                                    leaf ipv6-fragments-unsupported {
                                        type yang:counter64;
                                        description "IPv6 fragments unsupported";
                                    }

                                    leaf ipv6-extension-header-parse-error {
                                        type yang:counter64;
                                        description "IPv6 extension headers parse error";
                                    }

                                    leaf dslite-unsupported-next-header {
                                        type yang:counter64;
                                        description "Dual-stack-lite next header unsupported";
                                    }

                                    leaf l4-unsupported-protocol {
                                        type yang:counter64;
                                        description "Unsupported L4 protocol";
                                    }

                                    leaf tcp-udp-malformed-header {
                                        type yang:counter64;
                                        description "TCP/UDP malformed header";
                                    }

                                    leaf tcp-udp-invalid-checksum {
                                        type yang:counter64;
                                        description "TCP/UDP invalid checksum";
                                    }

                                    leaf icmp-embedded-ipv6-extension-header-parse-error {
                                        type yang:counter64;
                                        description "ICMP embedded IPv6 extension header parse error";
                                    }

                                    leaf other-parse-error {
                                        type yang:counter64;
                                        description "Other parse error";
                                    }

                                } // container receive-errors

                                container flow {
                                    description "Enter the flow context";

                                    leaf no-matching-flow {
                                        type yang:counter64;
                                        description "No matching flow";
                                    }

                                    leaf forwarding-blocked {
                                        type yang:counter64;
                                        description "Management core has blocked new flow creation or forwarding. Reasons include policies or port-blocks being released.";
                                    }

                                    leaf tcp-resetting {
                                        type yang:counter64;
                                        description "TCP flow is in reset state but not yet cleaned up";
                                    }

                                } // container flow

                                container flow-creation-failed {
                                    description "Enter the flow-creation-failed context";

                                    leaf no-resources {
                                        type yang:counter64;
                                        description "No resources";
                                    }

                                    leaf no-host-resources {
                                        type yang:counter64;
                                        description "Could not create host";
                                    }

                                    leaf no-ip-or-port-resources {
                                        type yang:counter64;
                                        description "Could not allocate ip or port-range";
                                    }

                                    leaf max-flows-exceeded {
                                        type yang:counter64;
                                        description "Max number of flows exceeded";
                                    }

                                    leaf ipv6-downstream-prohibited {
                                        type yang:counter64;
                                        description "IPv6 downstream traffic prohibited";
                                    }

                                    leaf address-dependent-filtering {
                                        type yang:counter64;
                                        description "Address dependent filtering";
                                    }

                                    leaf firewall-address-dependent-filtering {
                                        type yang:counter64;
                                        description "Firewall address dependent filtering";
                                    }

                                    leaf transient-no-policy {
                                        type yang:counter64;
                                        description "Policy could temporarily not be used";
                                    }

                                    leaf unmatched-policy {
                                        type yang:counter64;
                                        description "Matched policy not in use by subscriber";
                                    }

                                    leaf conflicting-policies {
                                        type yang:counter64;
                                        description "Conflicting policies";
                                    }

                                    leaf port-range-log-failed {
                                        type yang:counter64;
                                        description "Logging of port range allocation failed";
                                    }

                                    leaf flow-log-failed {
                                        type yang:counter64;
                                        description "Logging of flow creation failed";
                                    }

                                    leaf multiple-host-or-subscriber-ip {
                                        type yang:counter64;
                                        description "No multiple host or subscriber IPs allowed";
                                    }

                                    leaf destination-nat-destination-mismatch {
                                        type yang:counter64;
                                        description "Destination NAT destination IP mismatch";
                                    }

                                    leaf destination-nat-foreign-mismatch {
                                        type yang:counter64;
                                        description "Destination NAT foreign IP mismatch";
                                    }

                                    leaf ambiguous-flow-key {
                                        type yang:counter64;
                                        description "Ambiguous flow key";
                                    }

                                    leaf requested-port-not-in-host-range {
                                        type yang:counter64;
                                        description "Requested port not in host port range";
                                    }

                                    leaf destination-not-routable {
                                        type yang:counter64;
                                        description "Destination IP is not routable";
                                    }

                                    leaf dslite-unknown-aftr {
                                        type yang:counter64;
                                        description "Dual-stack-lite unknown AFTR address";
                                    }

                                    leaf pppoe-uplink-down {
                                        type yang:counter64;
                                        description "PPPoE uplink down";
                                    }

                                    leaf subscriber-id-unknown {
                                        type yang:counter64;
                                        description "Subscriber-id unknown";
                                    }

                                    leaf tcp-unexpected-rst {
                                        type yang:counter64;
                                        description "No flow creation on TCP RST";
                                    }

                                    leaf tcp-unexpected-fin {
                                        type yang:counter64;
                                        description "No flow creation on TCP FIN";
                                    }

                                    leaf tcp-unexpected-flags {
                                        type yang:counter64;
                                        description "No flow creation for invalid flags combinations";
                                    }

                                    leaf portrange-outside-ip-conflict {
                                        type yang:counter64;
                                        description "conflict between forced port range and outside IP of existing flow";
                                    }

                                    leaf requested-outside-port-conflict {
                                        type yang:counter64;
                                        description "conflict between requested outside port and outside port of existing flow";
                                    }

                                } // container flow-creation-failed

                                container icmp {
                                    description "Enter the icmp context";

                                    leaf unsupported-type-v4 {
                                        type yang:counter64;
                                        description "ICMP type unsupported";
                                    }

                                    leaf unsupported-type-v6 {
                                        type yang:counter64;
                                        description "ICMPv6 type unsupported";
                                    }

                                    leaf unsupported-type-for-translation {
                                        type yang:counter64;
                                        description "ICMP type unsupported for 4 to 6 translation";
                                    }

                                    leaf unsupported-length-for-translation {
                                        type yang:counter64;
                                        description "ICMP length error for 4 to 6 translation";
                                    }

                                    leaf unsupported-local {
                                        type yang:counter64;
                                        description "ICMP to l2aware-host gateway address unsupported";
                                    }

                                    leaf invalid-checksum {
                                        type yang:counter64;
                                        description "ICMP/ICMPv6 invalid checksum";
                                    }

                                    leaf embedded-invalid-checksum {
                                        type yang:counter64;
                                        description "ICMP invalid embedded IP checksum";
                                    }

                                    leaf unsupported-embedded-l3 {
                                        type yang:counter64;
                                        description "ICMP/ICMPv6 invalid embedded IP";
                                    }

                                    leaf unsupported-embedded-l4 {
                                        type yang:counter64;
                                        description "ICMP/ICMPv6 invalid embedded L4";
                                    }

                                    leaf too-short {
                                        type yang:counter64;
                                        description "ICMP/ICMPv6 too short";
                                    }

                                    leaf invalid-length {
                                        type yang:counter64;
                                        description "ICMP/ICMPv6 invalid length";
                                    }

                                    leaf fragmented {
                                        type yang:counter64;
                                        description "ICMP/ICMPv6 fragmentation";
                                    }

                                    leaf icmp6-packet-too-big {
                                        type yang:counter64;
                                        description "ICMP6 Packet-Too-Big with mtu < 1280";
                                    }

                                } // container icmp

                                container nat64 {
                                    description "Enter the nat64 context";

                                    leaf disabled {
                                        type yang:counter64;
                                        description "NAT64 disabled";
                                    }

                                    leaf invalid-source-address {
                                        type yang:counter64;
                                        description "NAT64 invalid source address";
                                    }

                                    leaf fragment-zero-checksum {
                                        type yang:counter64;
                                        description "NAT64 fragment has zero checksum";
                                    }

                                    leaf ipv4-zero-checksum {
                                        type yang:counter64;
                                        description "NAT64 IPv4 zero checksum";
                                    }

                                    leaf icmp-fragment-unsupported {
                                        type yang:counter64;
                                        description "NAT64 ICMP fragments unsupported";
                                    }

                                    leaf unknown-next-header {
                                        type yang:counter64;
                                        description "NAT64 unknown next header";
                                    }

                                    leaf embedded-ipv4-options {
                                        type yang:counter64;
                                        description "NAT64 ICMP embedded IPv4 options";
                                    }

                                } // container nat64

                                container fragments {
                                    description "Enter the fragments context";

                                    leaf too-many-fragmented-packets {
                                        type yang:counter64;
                                        description "Too many fragmented packets";
                                    }

                                    leaf too-many-fragment-buffers {
                                        type yang:counter64;
                                        description "Fragmentation buffers exhausted";
                                    }

                                    leaf too-many-fragment-holes {
                                        type yang:counter64;
                                        description "Too many fragment holes";
                                    }

                                    leaf too-many-fragments-per-packet {
                                        type yang:counter64;
                                        description "Too many fragments for IP packet";
                                    }

                                    leaf too-many-fragment-lists-for-flow {
                                        type yang:counter64;
                                        description "Too many fragment lists for flow";
                                    }

                                    leaf fragment-list-expired {
                                        type yang:counter64;
                                        description "Fragment list expired";
                                    }

                                    leaf fragment-list-cleanup-in-progress {
                                        type yang:counter64;
                                        description "Fragment list cleanup in progress";
                                    }

                                    leaf reassembly-failed {
                                        type yang:counter64;
                                        description "Reassembly failed";
                                    }

                                } // container fragments

                                container radius {
                                    description "Enter the radius context";

                                    leaf error {
                                        type yang:counter64;
                                        description "Error while processing RADIUS packet";
                                    }

                                    leaf no-send-resources {
                                        type yang:counter64;
                                        description "No resources to send RADIUS packet";
                                    }

                                } // container radius

                                container upnp {
                                    description "Enter the upnp context";

                                    leaf ssdp {
                                        type yang:counter64;
                                        description "SSDP dropped";
                                    }

                                    leaf control {
                                        type yang:counter64;
                                        description "UPnP control dropped";
                                    }

                                } // container upnp

                                container service-chaining {
                                    description "Enter the service-chaining context";

                                    leaf tx-error {
                                        type yang:counter64;
                                        description "Transmit error";
                                    }

                                    leaf rx-error {
                                        type yang:counter64;
                                        description "Receive error";
                                    }

                                    leaf rx-unsupported {
                                        type yang:counter64;
                                        description "Unhandled frames";
                                    }

                                    leaf filter-action-drop {
                                        type yang:counter64;
                                        description "Frames dropped by vas-filter";
                                    }

                                } // container service-chaining

                                container inter-chassis-sync {
                                    description "Enter the inter-chassis-sync context";

                                    leaf standby-drop {
                                        type yang:counter64;
                                        description "Standby drop";
                                    }

                                } // container inter-chassis-sync

                            } // container dropped

                            container flow {
                                description "Enter the flow context";

                                leaf new-flow {
                                    type yang:counter64;
                                    description "New flow created";
                                }

                                leaf found-flow {
                                    type yang:counter64;
                                    description "Frame matched existing flow";
                                }

                                leaf tcp-closed {
                                    type yang:counter64;
                                    description "Flow terminated by TCP session close";
                                }

                                container timeouts {
                                    description "Enter the timeouts context";

                                    leaf tcp-expired {
                                        type yang:counter64;
                                        description "TCP flow expired";
                                    }

                                    leaf udp-expired {
                                        type yang:counter64;
                                        description "UDP flow expired";
                                    }

                                    leaf icmp-expired {
                                        type yang:counter64;
                                        description "ICMP/ICMPv6 flow expired";
                                    }

                                    leaf gre-expired {
                                        type yang:counter64;
                                        description "GRE flow expired";
                                    }

                                    leaf ipv6-any-l4-expired {
                                        type yang:counter64;
                                        description "Any IPv6 L4 flow expired";
                                    }

                                } // container timeouts

                            } // container flow

                            container icmp {
                                description "Enter the icmp context";

                                leaf to-local {
                                    type yang:counter64;
                                    description "ICMP to local address";
                                }

                            } // container icmp

                            container dslite {
                                description "Enter the dslite context";

                                leaf forward {
                                    type yang:counter64;
                                    description "IPv6 dual-stack-lite frame forwarded";
                                }

                            } // container dslite

                            container fragmentation {
                                description "Enter the fragmentation context";

                                leaf ipv4 {
                                    type yang:counter64;
                                    description "IPv4 frame was fragmented";
                                }

                                leaf ipv6 {
                                    type yang:counter64;
                                    description "IPv6 frame was fragmented";
                                }

                            } // container fragmentation

                            container reassembly {
                                description "Enter the reassembly context";

                                leaf packets {
                                    type yang:counter64;
                                    description "Reassembled frames";
                                }

                            } // container reassembly

                            container flow-log {
                                description "Enter the flow-log context";

                                leaf logged-flow-create {
                                    type yang:counter64;
                                    description "Flow create logged";
                                }

                                leaf logged-flow-delete {
                                    type yang:counter64;
                                    description "Flow delete logged";
                                }

                                leaf tx-packet {
                                    type yang:counter64;
                                    description "Transmitted flow log frames";
                                }

                                leaf rate-limit-drop {
                                    type yang:counter64;
                                    description "Flow log frames dropped by rate limiting";
                                }

                            } // container flow-log

                            container radius {
                                description "Enter the radius context";

                                leaf to-local {
                                    type yang:counter64;
                                    description "Frame handled by local radius client";
                                }

                            } // container radius

                            container subscriber-id-cache {
                                description "Enter the subscriber-id-cache context";

                                leaf cached {
                                    type yang:counter64;
                                    description "Subscriber-id cached";
                                }

                                leaf delayed {
                                    type yang:counter64;
                                    description "Subscriber-id delayed";
                                }

                                leaf cache-timeout {
                                    type yang:counter64;
                                    description "Subscriber-id timeout";
                                }

                            } // container subscriber-id-cache

                            container fragments {
                                description "Enter the fragments context";

                                leaf rx-large-scale {
                                    type yang:counter64;
                                    description "Fragments received on large-scale nat interface";
                                }

                                leaf rx-dual-stack-lite {
                                    type yang:counter64;
                                    description "Fragments received on dual-stack-lite interface";
                                }

                                leaf rx-l2aware {
                                    type yang:counter64;
                                    description "Fragments received on l2aware interface";
                                }

                                leaf rx-outside {
                                    type yang:counter64;
                                    description "Fragments received on outside interface";
                                }

                                leaf tx-large-scale {
                                    type yang:counter64;
                                    description "Fragments transmitted on large-scale nat interface";
                                }

                                leaf tx-dual-stack-lite {
                                    type yang:counter64;
                                    description "Fragments transmitted on dual-stack-lite interface";
                                }

                                leaf tx-l2aware {
                                    type yang:counter64;
                                    description "Fragments transmitted on l2aware interface";
                                }

                                leaf tx-nat64 {
                                    type yang:counter64;
                                    description "Fragments transmitted on nat64 interface";
                                }

                                leaf tx-outside {
                                    type yang:counter64;
                                    description "Fragments transmitted on outside interface";
                                }

                            } // container fragments

                            container upnp {
                                description "Enter the upnp context";

                                leaf ssdp-rx {
                                    type yang:counter64;
                                    description "SSDP frames received";
                                }

                                leaf ssdp-tx {
                                    type yang:counter64;
                                    description "SSDP frames transmitted";
                                }

                                leaf control-rx {
                                    type yang:counter64;
                                    description "UPnP control frames received";
                                }

                                leaf control-tx {
                                    type yang:counter64;
                                    description "UPnP control frames transmitted";
                                }

                                leaf rate-limited-request {
                                    type yang:counter64;
                                    description "UPnP query rate limited";
                                }

                                leaf pinhole-without-default-policy {
                                    type yang:counter64;
                                    description "Attempt to create pinhole without default policy";
                                }

                                leaf pinhole-without-source-nat {
                                    type yang:counter64;
                                    description "Attempt to create pinhole with source-nat disabled";
                                }

                            } // container upnp

                            container service-chaining {
                                description "Enter the service-chaining context";

                                leaf rx {
                                    type yang:counter64;
                                    description "Service-chaining frames received";
                                }

                                leaf tx {
                                    type yang:counter64;
                                    description "Service-chaining frames transmitted";
                                }

                            } // container service-chaining

                        } // container nat

                    } // container statistics

                    container performance {
                        description "Enter the performance context";

                        container last-hour {
                            description "Enter the last-hour context";

                            list minutes-ago {
                                key "index";
                                description "Enter the minutes-ago list instance";

                                leaf index {
                                    type uint32;
                                    description "Numerical index value generated by the system.";
                                }

                                leaf timestamp {
                                    type yang:date-and-time;
                                    description "Time at which the measurement was taken";
                                }

                                leaf waiting {
                                    type decimal64 {
                                        range "0..100";
                                        fraction-digits 2;
                                    }
                                    units "percent";
                                    description "Relative time spent waiting in the measured period.";
                                }

                                leaf idling {
                                    type decimal64 {
                                        range "0..100";
                                        fraction-digits 2;
                                    }
                                    units "percent";
                                    description "Relative time spent idling in the measured period.";
                                }

                                leaf working {
                                    type decimal64 {
                                        range "0..100";
                                        fraction-digits 2;
                                    }
                                    units "percent";
                                    description "Relative time spent working in the measured period.";
                                }

                                leaf jobs {
                                    type uint32;
                                    description "The number of jobs performed in the measured period.";
                                }

                                leaf throughput {
                                    type uint64;
                                    units "bytes";
                                    description "The amount of data processed in the measured period.";
                                }

                            } // list minutes-ago

                        } // container last-hour

                        container last-day {
                            description "Enter the last-day context";

                            list hours-ago {
                                key "index";
                                description "Enter the hours-ago list instance";

                                leaf index {
                                    type uint32;
                                    description "Numerical index value generated by the system.";
                                }

                                leaf timestamp {
                                    type yang:date-and-time;
                                    description "Time at which the measurement was taken";
                                }

                                leaf waiting {
                                    type decimal64 {
                                        range "0..100";
                                        fraction-digits 2;
                                    }
                                    units "percent";
                                    description "Relative time spent waiting in the measured period.";
                                }

                                leaf idling {
                                    type decimal64 {
                                        range "0..100";
                                        fraction-digits 2;
                                    }
                                    units "percent";
                                    description "Relative time spent idling in the measured period.";
                                }

                                leaf working {
                                    type decimal64 {
                                        range "0..100";
                                        fraction-digits 2;
                                    }
                                    units "percent";
                                    description "Relative time spent working in the measured period.";
                                }

                                leaf jobs {
                                    type uint32;
                                    description "The number of jobs performed in the measured period.";
                                }

                                leaf throughput {
                                    type uint64;
                                    units "bytes";
                                    description "The amount of data processed in the measured period.";
                                }

                            } // list hours-ago

                        } // container last-day

                        container last-month {
                            description "Enter the last-month context";

                            list days-ago {
                                key "index";
                                description "Enter the days-ago list instance";

                                leaf index {
                                    type uint32;
                                    description "Numerical index value generated by the system.";
                                }

                                leaf timestamp {
                                    type yang:date-and-time;
                                    description "Time at which the measurement was taken";
                                }

                                leaf waiting {
                                    type decimal64 {
                                        range "0..100";
                                        fraction-digits 2;
                                    }
                                    units "percent";
                                    description "Relative time spent waiting in the measured period.";
                                }

                                leaf idling {
                                    type decimal64 {
                                        range "0..100";
                                        fraction-digits 2;
                                    }
                                    units "percent";
                                    description "Relative time spent idling in the measured period.";
                                }

                                leaf working {
                                    type decimal64 {
                                        range "0..100";
                                        fraction-digits 2;
                                    }
                                    units "percent";
                                    description "Relative time spent working in the measured period.";
                                }

                                leaf jobs {
                                    type uint32;
                                    description "The number of jobs performed in the measured period.";
                                }

                                leaf throughput {
                                    type uint64;
                                    units "bytes";
                                    description "The amount of data processed in the measured period.";
                                }

                            } // list days-ago

                        } // container last-month

                    } // container performance

                } // list mda

                list esa {
                    key "esa-id vm";
                    description "Enter the esa list instance";

                    leaf esa-id {
                        type leafref {
                            path "../../../../esa/esa-id";
                        }
                        description "Provisioned ESA ID";
                    }

                    leaf vm {
                        type leafref {
                            path "../../../../esa[esa-id=current()/../esa-id]/vm/vm-id";
                        }
                        description "VM ID for the provisioned BB ISA";
                    }

                    leaf layer-2-hosts-bypassed {
                        type uint32;
                        description "number of Layer-2 aware NAT hosts being bypassed for this ESA-VM";
                    }

                    leaf oper-state {
                        type types-isa:nat-member-operational-state;
                        description "the operational state of this NAT ESA-VM";
                    }

                    leaf allocated-resources {
                        type uint32 {
                            range "0..100";
                        }
                        description "the ratio of allocated resources to total resources on this NAT ESA-VM";
                    }

                    leaf peak-values-last-reset {
                        type yang:date-and-time;
                        description "Moment when the peak values were last reset (applicable to both NAT ESA-VM and member resources)";
                    }

                    container resources {
                        description "Enter the resources context";

                        container flows {
                            description "Enter the flows context";

                            leaf value {
                                type yang:gauge64;
                                description "Actual consumed value";
                            }

                            leaf max {
                                type uint64;
                                description "The max value this resource can have, depending on the configuration";
                            }

                            leaf peak {
                                type yang:gauge64;
                                description "The peak value for the resource";
                            }

                            leaf peak-timestamp {
                                type types-sros:date-time;
                                description "The timestamp when the peak value was observed";
                            }

                        } // container flows

                        container policies {
                            description "Enter the policies context";

                            leaf value {
                                type yang:gauge64;
                                description "Actual consumed value";
                            }

                            leaf max {
                                type uint64;
                                description "The max value this resource can have, depending on the configuration";
                            }

                            leaf peak {
                                type yang:gauge64;
                                description "The peak value for the resource";
                            }

                            leaf peak-timestamp {
                                type types-sros:date-time;
                                description "The timestamp when the peak value was observed";
                            }

                        } // container policies

                        container subscriber-cache-entries {
                            description "Enter the subscriber-cache-entries context";

                            leaf value {
                                type yang:gauge64;
                                description "Actual consumed value";
                            }

                            leaf max {
                                type uint64;
                                description "The max value this resource can have, depending on the configuration";
                            }

                            leaf peak {
                                type yang:gauge64;
                                description "The peak value for the resource";
                            }

                            leaf peak-timestamp {
                                type types-sros:date-time;
                                description "The timestamp when the peak value was observed";
                            }

                        } // container subscriber-cache-entries

                        container delayed-icmps {
                            description "Enter the delayed-icmps context";

                            leaf value {
                                type yang:gauge64;
                                description "Actual consumed value";
                            }

                            leaf max {
                                type uint64;
                                description "The max value this resource can have, depending on the configuration";
                            }

                            leaf peak {
                                type yang:gauge64;
                                description "The peak value for the resource";
                            }

                            leaf peak-timestamp {
                                type types-sros:date-time;
                                description "The timestamp when the peak value was observed";
                            }

                        } // container delayed-icmps

                        container alg-session {
                            description "Enter the alg-session context";

                            leaf value {
                                type yang:gauge64;
                                description "Actual consumed value";
                            }

                            leaf max {
                                type uint64;
                                description "The max value this resource can have, depending on the configuration";
                            }

                            leaf peak {
                                type yang:gauge64;
                                description "The peak value for the resource";
                            }

                            leaf peak-timestamp {
                                type types-sros:date-time;
                                description "The timestamp when the peak value was observed";
                            }

                        } // container alg-session

                        container fragment-lists {
                            description "Enter the fragment-lists context";

                            container upstream {
                                description "Enter the upstream context";

                                leaf value {
                                    type yang:gauge64;
                                    description "Actual consumed value";
                                }

                                leaf max {
                                    type uint64;
                                    description "The max value this resource can have, depending on the configuration";
                                }

                                leaf peak {
                                    type yang:gauge64;
                                    description "The peak value for the resource";
                                }

                                leaf peak-timestamp {
                                    type types-sros:date-time;
                                    description "The timestamp when the peak value was observed";
                                }

                            } // container upstream

                            container downstream {
                                description "Enter the downstream context";

                                leaf value {
                                    type yang:gauge64;
                                    description "Actual consumed value";
                                }

                                leaf max {
                                    type uint64;
                                    description "The max value this resource can have, depending on the configuration";
                                }

                                leaf peak {
                                    type yang:gauge64;
                                    description "The peak value for the resource";
                                }

                                leaf peak-timestamp {
                                    type types-sros:date-time;
                                    description "The timestamp when the peak value was observed";
                                }

                            } // container downstream

                        } // container fragment-lists

                        container fragment-holes {
                            description "Enter the fragment-holes context";

                            container upstream {
                                description "Enter the upstream context";

                                leaf value {
                                    type yang:gauge64;
                                    description "Actual consumed value";
                                }

                                leaf max {
                                    type uint64;
                                    description "The max value this resource can have, depending on the configuration";
                                }

                                leaf peak {
                                    type yang:gauge64;
                                    description "The peak value for the resource";
                                }

                                leaf peak-timestamp {
                                    type types-sros:date-time;
                                    description "The timestamp when the peak value was observed";
                                }

                            } // container upstream

                            container downstream {
                                description "Enter the downstream context";

                                leaf value {
                                    type yang:gauge64;
                                    description "Actual consumed value";
                                }

                                leaf max {
                                    type uint64;
                                    description "The max value this resource can have, depending on the configuration";
                                }

                                leaf peak {
                                    type yang:gauge64;
                                    description "The peak value for the resource";
                                }

                                leaf peak-timestamp {
                                    type types-sros:date-time;
                                    description "The timestamp when the peak value was observed";
                                }

                            } // container downstream

                        } // container fragment-holes

                        container fragment-bufs {
                            description "Enter the fragment-bufs context";

                            container upstream {
                                description "Enter the upstream context";

                                leaf value {
                                    type yang:gauge64;
                                    description "Actual consumed value";
                                }

                                leaf max {
                                    type uint64;
                                    description "The max value this resource can have, depending on the configuration";
                                }

                                leaf peak {
                                    type yang:gauge64;
                                    description "The peak value for the resource";
                                }

                                leaf peak-timestamp {
                                    type types-sros:date-time;
                                    description "The timestamp when the peak value was observed";
                                }

                            } // container upstream

                            container downstream {
                                description "Enter the downstream context";

                                leaf value {
                                    type yang:gauge64;
                                    description "Actual consumed value";
                                }

                                leaf max {
                                    type uint64;
                                    description "The max value this resource can have, depending on the configuration";
                                }

                                leaf peak {
                                    type yang:gauge64;
                                    description "The peak value for the resource";
                                }

                                leaf peak-timestamp {
                                    type types-sros:date-time;
                                    description "The timestamp when the peak value was observed";
                                }

                            } // container downstream

                        } // container fragment-bufs

                        container upnp {
                            description "Enter the upnp context";

                            container mappings {
                                description "Enter the mappings context";

                                leaf value {
                                    type yang:gauge64;
                                    description "Actual consumed value";
                                }

                                leaf max {
                                    type uint64;
                                    description "The max value this resource can have, depending on the configuration";
                                }

                                leaf peak {
                                    type yang:gauge64;
                                    description "The peak value for the resource";
                                }

                                leaf peak-timestamp {
                                    type types-sros:date-time;
                                    description "The timestamp when the peak value was observed";
                                }

                            } // container mappings

                            container sessions {
                                description "Enter the sessions context";

                                leaf value {
                                    type yang:gauge64;
                                    description "Actual consumed value";
                                }

                                leaf max {
                                    type uint64;
                                    description "The max value this resource can have, depending on the configuration";
                                }

                                leaf peak {
                                    type yang:gauge64;
                                    description "The peak value for the resource";
                                }

                                leaf peak-timestamp {
                                    type types-sros:date-time;
                                    description "The timestamp when the peak value was observed";
                                }

                            } // container sessions

                        } // container upnp

                        container pppoe-sessions {
                            description "Enter the pppoe-sessions context";

                            leaf value {
                                type yang:gauge64;
                                description "Actual consumed value";
                            }

                            leaf max {
                                type uint64;
                                description "The max value this resource can have, depending on the configuration";
                            }

                            leaf peak {
                                type yang:gauge64;
                                description "The peak value for the resource";
                            }

                            leaf peak-timestamp {
                                type types-sros:date-time;
                                description "The timestamp when the peak value was observed";
                            }

                        } // container pppoe-sessions

                    } // container resources

                    container statistics {
                        description "Enter the statistics context";

                        container ip-forwarding {
                            description "Enter the ip-forwarding context";

                            leaf fragments {
                                type yang:counter64;
                                description "Fragments handled";
                            }

                            leaf reassembled-packets {
                                type yang:counter64;
                                description "Frames reassembled";
                            }

                            leaf forwarded-packets {
                                type yang:counter64;
                                description "Frames forwarded";
                            }

                            container receive-errors {
                                description "Enter the receive-errors context";

                                leaf l2-error {
                                    type yang:counter64;
                                    description "L2 parse error";
                                }

                                leaf l3-not-ip {
                                    type yang:counter64;
                                    description "L3 is not IPv4 or IPv6";
                                }

                                leaf ip-invalid-checksum {
                                    type yang:counter64;
                                    description "IPv4 invalid checksum";
                                }

                                leaf ip-malformed-header {
                                    type yang:counter64;
                                    description "IP malformed header";
                                }

                                leaf ip-malformed-packet {
                                    type yang:counter64;
                                    description "IP malformed packet";
                                }

                                leaf ip-zero-ttl {
                                    type yang:counter64;
                                    description "IP zero ttl";
                                }

                                leaf ip-opts-or-ext-headers {
                                    type yang:counter64;
                                    description "IPv4 options or IPv6 extension headers";
                                }

                                leaf ip-fragment-unsupported {
                                    type yang:counter64;
                                    description "IP fragment unsupported";
                                }

                                leaf ip-error {
                                    type yang:counter64;
                                    description "IP parse error";
                                }

                                leaf tcp-udp-malformed-header {
                                    type yang:counter64;
                                    description "TCP/UDP malformed header";
                                }

                                leaf tcp-udp-invalid-checksum {
                                    type yang:counter64;
                                    description "TCP/UDP invalid checksum";
                                }

                                leaf other {
                                    type yang:counter64;
                                    description "Other parse error";
                                }

                            } // container receive-errors

                            container reassembly-errors {
                                description "Enter the reassembly-errors context";

                                leaf too-many-fragmented-packets {
                                    type yang:counter64;
                                    description "Too many fragmented packets";
                                }

                                leaf too-many-fragment-buffers {
                                    type yang:counter64;
                                    description "Too many fragment buffers";
                                }

                                leaf too-many-fragment-holes {
                                    type yang:counter64;
                                    description "Too many fragment holes";
                                }

                                leaf fragment-filtered {
                                    type yang:counter64;
                                    description "Fragments filtered";
                                }

                                leaf fragment-not-supported {
                                    type yang:counter64;
                                    description "Fragment not supported";
                                }

                                leaf fragment-list-expired {
                                    type yang:counter64;
                                    description "Fragment list expired";
                                }

                                leaf fragment-list-cleanup-in-progress {
                                    type yang:counter64;
                                    description "Fragment list cleanup in progress";
                                }

                                leaf reassembly-failed {
                                    type yang:counter64;
                                    description "Reassembly failed";
                                }

                            } // container reassembly-errors

                        } // container ip-forwarding

                        container pppoe-client {
                            description "Enter the pppoe-client context";

                            leaf rx-error-l2 {
                                type yang:counter64;
                                description "Number of packets received with layer 2 parse errors";
                            }

                            leaf rx-error-invalid-headers {
                                type yang:counter64;
                                description "Number of packets received with invalid PPPoE headers";
                            }

                            leaf rx-error-invalid-magic {
                                type yang:counter64;
                                description "Number of LCP echo-request or echo-reply packets received with an invalid magic number";
                            }

                            leaf rx-error-no-session {
                                type yang:counter64;
                                description "Number of LCP echo or data packets received without an associated session";
                            }

                            leaf rx-discovery {
                                type yang:counter64;
                                description "Number of PPPoE discovery packets received";
                            }

                            leaf rx-ppp-control {
                                type yang:counter64;
                                description "Number of PPP control packets received";
                            }

                            leaf rx-lcp-echo-request {
                                type yang:counter64;
                                description "Number of LCP echo-request packets received";
                            }

                            leaf rx-lcp-echo-reply {
                                type yang:counter64;
                                description "Number of LCP echo-reply packets received";
                            }

                            leaf tx-lcp-echo-request {
                                type yang:counter64;
                                description "Number of LCP echo-request packets transmitted";
                            }

                            leaf tx-lcp-echo-reply {
                                type yang:counter64;
                                description "Number of LCP echo-reply packets transmitted";
                            }

                        } // container pppoe-client

                        container nat {
                            description "Enter the nat context";

                            container dropped {
                                description "Enter the dropped context";

                                container general {
                                    description "Enter the general context";

                                    leaf arp {
                                        type yang:counter64;
                                        description "ARP frames are ignored";
                                    }

                                    leaf checksum-calculation-error {
                                        type yang:counter64;
                                        description "Error while calculating L4 checksum before transmitting";
                                    }

                                    leaf send-error {
                                        type yang:counter64;
                                        description "Packet send error";
                                    }

                                    leaf no-copy-buffer {
                                        type yang:counter64;
                                        description "No buffer to copy frame";
                                    }

                                    leaf mtu-exceeded {
                                        type yang:counter64;
                                        description "Egress MTU exceeded";
                                    }

                                    leaf multicast {
                                        type yang:counter64;
                                        description "Multicast dropped";
                                    }

                                } // container general

                                container receive-errors {
                                    description "Enter the receive-errors context";

                                    leaf l2-error {
                                        type yang:counter64;
                                        description "L2 parse error";
                                    }

                                    leaf l3-not-ip {
                                        type yang:counter64;
                                        description "L3 is not IPv4 or IPv6";
                                    }

                                    leaf ip-invalid-checksum {
                                        type yang:counter64;
                                        description "IPv4 invalid checksum";
                                    }

                                    leaf ip-malformed-header {
                                        type yang:counter64;
                                        description "IP malformed header";
                                    }

                                    leaf ip-malformed-packet {
                                        type yang:counter64;
                                        description "IP malformed packet";
                                    }

                                    leaf ip-zero-ttl {
                                        type yang:counter64;
                                        description "IP zero ttl";
                                    }

                                    leaf ip-opts-or-ext-headers {
                                        type yang:counter64;
                                        description "IPv4 options or IPv6 extension headers";
                                    }

                                    leaf ip-parse-error {
                                        type yang:counter64;
                                        description "IP parse error";
                                    }

                                    leaf ipv6-fragments-unsupported {
                                        type yang:counter64;
                                        description "IPv6 fragments unsupported";
                                    }

                                    leaf ipv6-extension-header-parse-error {
                                        type yang:counter64;
                                        description "IPv6 extension headers parse error";
                                    }

                                    leaf dslite-unsupported-next-header {
                                        type yang:counter64;
                                        description "Dual-stack-lite next header unsupported";
                                    }

                                    leaf l4-unsupported-protocol {
                                        type yang:counter64;
                                        description "Unsupported L4 protocol";
                                    }

                                    leaf tcp-udp-malformed-header {
                                        type yang:counter64;
                                        description "TCP/UDP malformed header";
                                    }

                                    leaf tcp-udp-invalid-checksum {
                                        type yang:counter64;
                                        description "TCP/UDP invalid checksum";
                                    }

                                    leaf icmp-embedded-ipv6-extension-header-parse-error {
                                        type yang:counter64;
                                        description "ICMP embedded IPv6 extension header parse error";
                                    }

                                    leaf other-parse-error {
                                        type yang:counter64;
                                        description "Other parse error";
                                    }

                                } // container receive-errors

                                container flow {
                                    description "Enter the flow context";

                                    leaf no-matching-flow {
                                        type yang:counter64;
                                        description "No matching flow";
                                    }

                                    leaf forwarding-blocked {
                                        type yang:counter64;
                                        description "Management core has blocked new flow creation or forwarding. Reasons include policies or port-blocks being released.";
                                    }

                                    leaf tcp-resetting {
                                        type yang:counter64;
                                        description "TCP flow is in reset state but not yet cleaned up";
                                    }

                                } // container flow

                                container flow-creation-failed {
                                    description "Enter the flow-creation-failed context";

                                    leaf no-resources {
                                        type yang:counter64;
                                        description "No resources";
                                    }

                                    leaf no-host-resources {
                                        type yang:counter64;
                                        description "Could not create host";
                                    }

                                    leaf no-ip-or-port-resources {
                                        type yang:counter64;
                                        description "Could not allocate ip or port-range";
                                    }

                                    leaf max-flows-exceeded {
                                        type yang:counter64;
                                        description "Max number of flows exceeded";
                                    }

                                    leaf ipv6-downstream-prohibited {
                                        type yang:counter64;
                                        description "IPv6 downstream traffic prohibited";
                                    }

                                    leaf address-dependent-filtering {
                                        type yang:counter64;
                                        description "Address dependent filtering";
                                    }

                                    leaf firewall-address-dependent-filtering {
                                        type yang:counter64;
                                        description "Firewall address dependent filtering";
                                    }

                                    leaf transient-no-policy {
                                        type yang:counter64;
                                        description "Policy could temporarily not be used";
                                    }

                                    leaf unmatched-policy {
                                        type yang:counter64;
                                        description "Matched policy not in use by subscriber";
                                    }

                                    leaf conflicting-policies {
                                        type yang:counter64;
                                        description "Conflicting policies";
                                    }

                                    leaf port-range-log-failed {
                                        type yang:counter64;
                                        description "Logging of port range allocation failed";
                                    }

                                    leaf flow-log-failed {
                                        type yang:counter64;
                                        description "Logging of flow creation failed";
                                    }

                                    leaf multiple-host-or-subscriber-ip {
                                        type yang:counter64;
                                        description "No multiple host or subscriber IPs allowed";
                                    }

                                    leaf destination-nat-destination-mismatch {
                                        type yang:counter64;
                                        description "Destination NAT destination IP mismatch";
                                    }

                                    leaf destination-nat-foreign-mismatch {
                                        type yang:counter64;
                                        description "Destination NAT foreign IP mismatch";
                                    }

                                    leaf ambiguous-flow-key {
                                        type yang:counter64;
                                        description "Ambiguous flow key";
                                    }

                                    leaf requested-port-not-in-host-range {
                                        type yang:counter64;
                                        description "Requested port not in host port range";
                                    }

                                    leaf destination-not-routable {
                                        type yang:counter64;
                                        description "Destination IP is not routable";
                                    }

                                    leaf dslite-unknown-aftr {
                                        type yang:counter64;
                                        description "Dual-stack-lite unknown AFTR address";
                                    }

                                    leaf pppoe-uplink-down {
                                        type yang:counter64;
                                        description "PPPoE uplink down";
                                    }

                                    leaf subscriber-id-unknown {
                                        type yang:counter64;
                                        description "Subscriber-id unknown";
                                    }

                                    leaf tcp-unexpected-rst {
                                        type yang:counter64;
                                        description "No flow creation on TCP RST";
                                    }

                                    leaf tcp-unexpected-fin {
                                        type yang:counter64;
                                        description "No flow creation on TCP FIN";
                                    }

                                    leaf tcp-unexpected-flags {
                                        type yang:counter64;
                                        description "No flow creation for invalid flags combinations";
                                    }

                                    leaf portrange-outside-ip-conflict {
                                        type yang:counter64;
                                        description "conflict between forced port range and outside IP of existing flow";
                                    }

                                    leaf requested-outside-port-conflict {
                                        type yang:counter64;
                                        description "conflict between requested outside port and outside port of existing flow";
                                    }

                                } // container flow-creation-failed

                                container icmp {
                                    description "Enter the icmp context";

                                    leaf unsupported-type-v4 {
                                        type yang:counter64;
                                        description "ICMP type unsupported";
                                    }

                                    leaf unsupported-type-v6 {
                                        type yang:counter64;
                                        description "ICMPv6 type unsupported";
                                    }

                                    leaf unsupported-type-for-translation {
                                        type yang:counter64;
                                        description "ICMP type unsupported for 4 to 6 translation";
                                    }

                                    leaf unsupported-length-for-translation {
                                        type yang:counter64;
                                        description "ICMP length error for 4 to 6 translation";
                                    }

                                    leaf unsupported-local {
                                        type yang:counter64;
                                        description "ICMP to l2aware-host gateway address unsupported";
                                    }

                                    leaf invalid-checksum {
                                        type yang:counter64;
                                        description "ICMP/ICMPv6 invalid checksum";
                                    }

                                    leaf embedded-invalid-checksum {
                                        type yang:counter64;
                                        description "ICMP invalid embedded IP checksum";
                                    }

                                    leaf unsupported-embedded-l3 {
                                        type yang:counter64;
                                        description "ICMP/ICMPv6 invalid embedded IP";
                                    }

                                    leaf unsupported-embedded-l4 {
                                        type yang:counter64;
                                        description "ICMP/ICMPv6 invalid embedded L4";
                                    }

                                    leaf too-short {
                                        type yang:counter64;
                                        description "ICMP/ICMPv6 too short";
                                    }

                                    leaf invalid-length {
                                        type yang:counter64;
                                        description "ICMP/ICMPv6 invalid length";
                                    }

                                    leaf fragmented {
                                        type yang:counter64;
                                        description "ICMP/ICMPv6 fragmentation";
                                    }

                                    leaf icmp6-packet-too-big {
                                        type yang:counter64;
                                        description "ICMP6 Packet-Too-Big with mtu < 1280";
                                    }

                                } // container icmp

                                container nat64 {
                                    description "Enter the nat64 context";

                                    leaf disabled {
                                        type yang:counter64;
                                        description "NAT64 disabled";
                                    }

                                    leaf invalid-source-address {
                                        type yang:counter64;
                                        description "NAT64 invalid source address";
                                    }

                                    leaf fragment-zero-checksum {
                                        type yang:counter64;
                                        description "NAT64 fragment has zero checksum";
                                    }

                                    leaf ipv4-zero-checksum {
                                        type yang:counter64;
                                        description "NAT64 IPv4 zero checksum";
                                    }

                                    leaf icmp-fragment-unsupported {
                                        type yang:counter64;
                                        description "NAT64 ICMP fragments unsupported";
                                    }

                                    leaf unknown-next-header {
                                        type yang:counter64;
                                        description "NAT64 unknown next header";
                                    }

                                    leaf embedded-ipv4-options {
                                        type yang:counter64;
                                        description "NAT64 ICMP embedded IPv4 options";
                                    }

                                } // container nat64

                                container fragments {
                                    description "Enter the fragments context";

                                    leaf too-many-fragmented-packets {
                                        type yang:counter64;
                                        description "Too many fragmented packets";
                                    }

                                    leaf too-many-fragment-buffers {
                                        type yang:counter64;
                                        description "Fragmentation buffers exhausted";
                                    }

                                    leaf too-many-fragment-holes {
                                        type yang:counter64;
                                        description "Too many fragment holes";
                                    }

                                    leaf too-many-fragments-per-packet {
                                        type yang:counter64;
                                        description "Too many fragments for IP packet";
                                    }

                                    leaf too-many-fragment-lists-for-flow {
                                        type yang:counter64;
                                        description "Too many fragment lists for flow";
                                    }

                                    leaf fragment-list-expired {
                                        type yang:counter64;
                                        description "Fragment list expired";
                                    }

                                    leaf fragment-list-cleanup-in-progress {
                                        type yang:counter64;
                                        description "Fragment list cleanup in progress";
                                    }

                                    leaf reassembly-failed {
                                        type yang:counter64;
                                        description "Reassembly failed";
                                    }

                                } // container fragments

                                container radius {
                                    description "Enter the radius context";

                                    leaf error {
                                        type yang:counter64;
                                        description "Error while processing RADIUS packet";
                                    }

                                    leaf no-send-resources {
                                        type yang:counter64;
                                        description "No resources to send RADIUS packet";
                                    }

                                } // container radius

                                container upnp {
                                    description "Enter the upnp context";

                                    leaf ssdp {
                                        type yang:counter64;
                                        description "SSDP dropped";
                                    }

                                    leaf control {
                                        type yang:counter64;
                                        description "UPnP control dropped";
                                    }

                                } // container upnp

                                container service-chaining {
                                    description "Enter the service-chaining context";

                                    leaf tx-error {
                                        type yang:counter64;
                                        description "Transmit error";
                                    }

                                    leaf rx-error {
                                        type yang:counter64;
                                        description "Receive error";
                                    }

                                    leaf rx-unsupported {
                                        type yang:counter64;
                                        description "Unhandled frames";
                                    }

                                    leaf filter-action-drop {
                                        type yang:counter64;
                                        description "Frames dropped by vas-filter";
                                    }

                                } // container service-chaining

                                container inter-chassis-sync {
                                    description "Enter the inter-chassis-sync context";

                                    leaf standby-drop {
                                        type yang:counter64;
                                        description "Standby drop";
                                    }

                                } // container inter-chassis-sync

                            } // container dropped

                            container flow {
                                description "Enter the flow context";

                                leaf new-flow {
                                    type yang:counter64;
                                    description "New flow created";
                                }

                                leaf found-flow {
                                    type yang:counter64;
                                    description "Frame matched existing flow";
                                }

                                leaf tcp-closed {
                                    type yang:counter64;
                                    description "Flow terminated by TCP session close";
                                }

                                container timeouts {
                                    description "Enter the timeouts context";

                                    leaf tcp-expired {
                                        type yang:counter64;
                                        description "TCP flow expired";
                                    }

                                    leaf udp-expired {
                                        type yang:counter64;
                                        description "UDP flow expired";
                                    }

                                    leaf icmp-expired {
                                        type yang:counter64;
                                        description "ICMP/ICMPv6 flow expired";
                                    }

                                    leaf gre-expired {
                                        type yang:counter64;
                                        description "GRE flow expired";
                                    }

                                    leaf ipv6-any-l4-expired {
                                        type yang:counter64;
                                        description "Any IPv6 L4 flow expired";
                                    }

                                } // container timeouts

                            } // container flow

                            container icmp {
                                description "Enter the icmp context";

                                leaf to-local {
                                    type yang:counter64;
                                    description "ICMP to local address";
                                }

                            } // container icmp

                            container dslite {
                                description "Enter the dslite context";

                                leaf forward {
                                    type yang:counter64;
                                    description "IPv6 dual-stack-lite frame forwarded";
                                }

                            } // container dslite

                            container fragmentation {
                                description "Enter the fragmentation context";

                                leaf ipv4 {
                                    type yang:counter64;
                                    description "IPv4 frame was fragmented";
                                }

                                leaf ipv6 {
                                    type yang:counter64;
                                    description "IPv6 frame was fragmented";
                                }

                            } // container fragmentation

                            container reassembly {
                                description "Enter the reassembly context";

                                leaf packets {
                                    type yang:counter64;
                                    description "Reassembled frames";
                                }

                            } // container reassembly

                            container flow-log {
                                description "Enter the flow-log context";

                                leaf logged-flow-create {
                                    type yang:counter64;
                                    description "Flow create logged";
                                }

                                leaf logged-flow-delete {
                                    type yang:counter64;
                                    description "Flow delete logged";
                                }

                                leaf tx-packet {
                                    type yang:counter64;
                                    description "Transmitted flow log frames";
                                }

                                leaf rate-limit-drop {
                                    type yang:counter64;
                                    description "Flow log frames dropped by rate limiting";
                                }

                            } // container flow-log

                            container radius {
                                description "Enter the radius context";

                                leaf to-local {
                                    type yang:counter64;
                                    description "Frame handled by local radius client";
                                }

                            } // container radius

                            container subscriber-id-cache {
                                description "Enter the subscriber-id-cache context";

                                leaf cached {
                                    type yang:counter64;
                                    description "Subscriber-id cached";
                                }

                                leaf delayed {
                                    type yang:counter64;
                                    description "Subscriber-id delayed";
                                }

                                leaf cache-timeout {
                                    type yang:counter64;
                                    description "Subscriber-id timeout";
                                }

                            } // container subscriber-id-cache

                            container fragments {
                                description "Enter the fragments context";

                                leaf rx-large-scale {
                                    type yang:counter64;
                                    description "Fragments received on large-scale nat interface";
                                }

                                leaf rx-dual-stack-lite {
                                    type yang:counter64;
                                    description "Fragments received on dual-stack-lite interface";
                                }

                                leaf rx-l2aware {
                                    type yang:counter64;
                                    description "Fragments received on l2aware interface";
                                }

                                leaf rx-outside {
                                    type yang:counter64;
                                    description "Fragments received on outside interface";
                                }

                                leaf tx-large-scale {
                                    type yang:counter64;
                                    description "Fragments transmitted on large-scale nat interface";
                                }

                                leaf tx-dual-stack-lite {
                                    type yang:counter64;
                                    description "Fragments transmitted on dual-stack-lite interface";
                                }

                                leaf tx-l2aware {
                                    type yang:counter64;
                                    description "Fragments transmitted on l2aware interface";
                                }

                                leaf tx-nat64 {
                                    type yang:counter64;
                                    description "Fragments transmitted on nat64 interface";
                                }

                                leaf tx-outside {
                                    type yang:counter64;
                                    description "Fragments transmitted on outside interface";
                                }

                            } // container fragments

                            container upnp {
                                description "Enter the upnp context";

                                leaf ssdp-rx {
                                    type yang:counter64;
                                    description "SSDP frames received";
                                }

                                leaf ssdp-tx {
                                    type yang:counter64;
                                    description "SSDP frames transmitted";
                                }

                                leaf control-rx {
                                    type yang:counter64;
                                    description "UPnP control frames received";
                                }

                                leaf control-tx {
                                    type yang:counter64;
                                    description "UPnP control frames transmitted";
                                }

                                leaf rate-limited-request {
                                    type yang:counter64;
                                    description "UPnP query rate limited";
                                }

                                leaf pinhole-without-default-policy {
                                    type yang:counter64;
                                    description "Attempt to create pinhole without default policy";
                                }

                                leaf pinhole-without-source-nat {
                                    type yang:counter64;
                                    description "Attempt to create pinhole with source-nat disabled";
                                }

                            } // container upnp

                            container service-chaining {
                                description "Enter the service-chaining context";

                                leaf rx {
                                    type yang:counter64;
                                    description "Service-chaining frames received";
                                }

                                leaf tx {
                                    type yang:counter64;
                                    description "Service-chaining frames transmitted";
                                }

                            } // container service-chaining

                        } // container nat

                    } // container statistics

                    container performance {
                        description "Enter the performance context";

                        container last-hour {
                            description "Enter the last-hour context";

                            list minutes-ago {
                                key "index";
                                description "Enter the minutes-ago list instance";

                                leaf index {
                                    type uint32;
                                    description "Numerical index value generated by the system.";
                                }

                                leaf timestamp {
                                    type yang:date-and-time;
                                    description "Time at which the measurement was taken";
                                }

                                leaf waiting {
                                    type decimal64 {
                                        range "0..100";
                                        fraction-digits 2;
                                    }
                                    units "percent";
                                    description "Relative time spent waiting in the measured period.";
                                }

                                leaf idling {
                                    type decimal64 {
                                        range "0..100";
                                        fraction-digits 2;
                                    }
                                    units "percent";
                                    description "Relative time spent idling in the measured period.";
                                }

                                leaf working {
                                    type decimal64 {
                                        range "0..100";
                                        fraction-digits 2;
                                    }
                                    units "percent";
                                    description "Relative time spent working in the measured period.";
                                }

                                leaf jobs {
                                    type uint32;
                                    description "The number of jobs performed in the measured period.";
                                }

                                leaf throughput {
                                    type uint64;
                                    units "bytes";
                                    description "The amount of data processed in the measured period.";
                                }

                            } // list minutes-ago

                        } // container last-hour

                        container last-day {
                            description "Enter the last-day context";

                            list hours-ago {
                                key "index";
                                description "Enter the hours-ago list instance";

                                leaf index {
                                    type uint32;
                                    description "Numerical index value generated by the system.";
                                }

                                leaf timestamp {
                                    type yang:date-and-time;
                                    description "Time at which the measurement was taken";
                                }

                                leaf waiting {
                                    type decimal64 {
                                        range "0..100";
                                        fraction-digits 2;
                                    }
                                    units "percent";
                                    description "Relative time spent waiting in the measured period.";
                                }

                                leaf idling {
                                    type decimal64 {
                                        range "0..100";
                                        fraction-digits 2;
                                    }
                                    units "percent";
                                    description "Relative time spent idling in the measured period.";
                                }

                                leaf working {
                                    type decimal64 {
                                        range "0..100";
                                        fraction-digits 2;
                                    }
                                    units "percent";
                                    description "Relative time spent working in the measured period.";
                                }

                                leaf jobs {
                                    type uint32;
                                    description "The number of jobs performed in the measured period.";
                                }

                                leaf throughput {
                                    type uint64;
                                    units "bytes";
                                    description "The amount of data processed in the measured period.";
                                }

                            } // list hours-ago

                        } // container last-day

                        container last-month {
                            description "Enter the last-month context";

                            list days-ago {
                                key "index";
                                description "Enter the days-ago list instance";

                                leaf index {
                                    type uint32;
                                    description "Numerical index value generated by the system.";
                                }

                                leaf timestamp {
                                    type yang:date-and-time;
                                    description "Time at which the measurement was taken";
                                }

                                leaf waiting {
                                    type decimal64 {
                                        range "0..100";
                                        fraction-digits 2;
                                    }
                                    units "percent";
                                    description "Relative time spent waiting in the measured period.";
                                }

                                leaf idling {
                                    type decimal64 {
                                        range "0..100";
                                        fraction-digits 2;
                                    }
                                    units "percent";
                                    description "Relative time spent idling in the measured period.";
                                }

                                leaf working {
                                    type decimal64 {
                                        range "0..100";
                                        fraction-digits 2;
                                    }
                                    units "percent";
                                    description "Relative time spent working in the measured period.";
                                }

                                leaf jobs {
                                    type uint32;
                                    description "The number of jobs performed in the measured period.";
                                }

                                leaf throughput {
                                    type uint64;
                                    units "bytes";
                                    description "The amount of data processed in the measured period.";
                                }

                            } // list days-ago

                        } // container last-month

                    } // container performance

                } // list esa

            } // list nat-group

            list wlan-gw-group {
                key "id";
                description "Enter the wlan-gw-group list instance";

                leaf id {
                    type types-isa:wlan-gw-group-id;
                    description "WLAN-GW ISA group ID";
                }

                leaf oper-state {
                    type types-sros:oper-state;
                    description "Operational status of a WLAN-GW group";
                }

                leaf degraded {
                    type boolean;
                    description "Indicates if the WLAN-GW group is degraded, while operationally still in service.";
                }

                list iom {
                    key "slot-number";
                    description "Enter the iom list instance";

                    leaf slot-number {
                        type leafref {
                            path "../../../../card/slot-number";
                        }
                        description "IOM slot to use in the WLAN-GW group";
                    }

                    leaf oper-state {
                        type types-isa:wlan-gw-isa-iom-oper-state;
                        description "Operational status of a WLAN-GW group IOM";
                    }

                    list mda {
                        key "mda-id";
                        description "Enter the mda list instance";

                        leaf mda-id {
                            type types-isa:slot-mda;
                            description "MDA slot value";
                        }

                        leaf oper-state {
                            type types-isa:nat-member-operational-state;
                            description "Operational status of a WLAN-GW group MDA";
                        }

                        container nat {
                            description "Enter the nat context";

                            leaf peak-values-last-reset {
                                type yang:date-and-time;
                                description "Moment when the peak values were last reset";
                            }

                            container resources {
                                description "Enter the resources context";

                                container flows {
                                    description "Enter the flows context";

                                    leaf value {
                                        type yang:gauge64;
                                        description "Actual consumed value";
                                    }

                                    leaf max {
                                        type uint64;
                                        description "The max value this resource can have, depending on the configuration";
                                    }

                                    leaf peak {
                                        type yang:gauge64;
                                        description "The peak value for the resource";
                                    }

                                    leaf peak-timestamp {
                                        type types-sros:date-time;
                                        description "The timestamp when the peak value was observed";
                                    }

                                } // container flows

                                container policies {
                                    description "Enter the policies context";

                                    leaf value {
                                        type yang:gauge64;
                                        description "Actual consumed value";
                                    }

                                    leaf max {
                                        type uint64;
                                        description "The max value this resource can have, depending on the configuration";
                                    }

                                    leaf peak {
                                        type yang:gauge64;
                                        description "The peak value for the resource";
                                    }

                                    leaf peak-timestamp {
                                        type types-sros:date-time;
                                        description "The timestamp when the peak value was observed";
                                    }

                                } // container policies

                                container subscriber-cache-entries {
                                    description "Enter the subscriber-cache-entries context";

                                    leaf value {
                                        type yang:gauge64;
                                        description "Actual consumed value";
                                    }

                                    leaf max {
                                        type uint64;
                                        description "The max value this resource can have, depending on the configuration";
                                    }

                                    leaf peak {
                                        type yang:gauge64;
                                        description "The peak value for the resource";
                                    }

                                    leaf peak-timestamp {
                                        type types-sros:date-time;
                                        description "The timestamp when the peak value was observed";
                                    }

                                } // container subscriber-cache-entries

                                container delayed-icmps {
                                    description "Enter the delayed-icmps context";

                                    leaf value {
                                        type yang:gauge64;
                                        description "Actual consumed value";
                                    }

                                    leaf max {
                                        type uint64;
                                        description "The max value this resource can have, depending on the configuration";
                                    }

                                    leaf peak {
                                        type yang:gauge64;
                                        description "The peak value for the resource";
                                    }

                                    leaf peak-timestamp {
                                        type types-sros:date-time;
                                        description "The timestamp when the peak value was observed";
                                    }

                                } // container delayed-icmps

                                container alg-session {
                                    description "Enter the alg-session context";

                                    leaf value {
                                        type yang:gauge64;
                                        description "Actual consumed value";
                                    }

                                    leaf max {
                                        type uint64;
                                        description "The max value this resource can have, depending on the configuration";
                                    }

                                    leaf peak {
                                        type yang:gauge64;
                                        description "The peak value for the resource";
                                    }

                                    leaf peak-timestamp {
                                        type types-sros:date-time;
                                        description "The timestamp when the peak value was observed";
                                    }

                                } // container alg-session

                                container fragment-lists {
                                    description "Enter the fragment-lists context";

                                    container upstream {
                                        description "Enter the upstream context";

                                        leaf value {
                                            type yang:gauge64;
                                            description "Actual consumed value";
                                        }

                                        leaf max {
                                            type uint64;
                                            description "The max value this resource can have, depending on the configuration";
                                        }

                                        leaf peak {
                                            type yang:gauge64;
                                            description "The peak value for the resource";
                                        }

                                        leaf peak-timestamp {
                                            type types-sros:date-time;
                                            description "The timestamp when the peak value was observed";
                                        }

                                    } // container upstream

                                    container downstream {
                                        description "Enter the downstream context";

                                        leaf value {
                                            type yang:gauge64;
                                            description "Actual consumed value";
                                        }

                                        leaf max {
                                            type uint64;
                                            description "The max value this resource can have, depending on the configuration";
                                        }

                                        leaf peak {
                                            type yang:gauge64;
                                            description "The peak value for the resource";
                                        }

                                        leaf peak-timestamp {
                                            type types-sros:date-time;
                                            description "The timestamp when the peak value was observed";
                                        }

                                    } // container downstream

                                } // container fragment-lists

                                container fragment-holes {
                                    description "Enter the fragment-holes context";

                                    container upstream {
                                        description "Enter the upstream context";

                                        leaf value {
                                            type yang:gauge64;
                                            description "Actual consumed value";
                                        }

                                        leaf max {
                                            type uint64;
                                            description "The max value this resource can have, depending on the configuration";
                                        }

                                        leaf peak {
                                            type yang:gauge64;
                                            description "The peak value for the resource";
                                        }

                                        leaf peak-timestamp {
                                            type types-sros:date-time;
                                            description "The timestamp when the peak value was observed";
                                        }

                                    } // container upstream

                                    container downstream {
                                        description "Enter the downstream context";

                                        leaf value {
                                            type yang:gauge64;
                                            description "Actual consumed value";
                                        }

                                        leaf max {
                                            type uint64;
                                            description "The max value this resource can have, depending on the configuration";
                                        }

                                        leaf peak {
                                            type yang:gauge64;
                                            description "The peak value for the resource";
                                        }

                                        leaf peak-timestamp {
                                            type types-sros:date-time;
                                            description "The timestamp when the peak value was observed";
                                        }

                                    } // container downstream

                                } // container fragment-holes

                                container fragment-bufs {
                                    description "Enter the fragment-bufs context";

                                    container upstream {
                                        description "Enter the upstream context";

                                        leaf value {
                                            type yang:gauge64;
                                            description "Actual consumed value";
                                        }

                                        leaf max {
                                            type uint64;
                                            description "The max value this resource can have, depending on the configuration";
                                        }

                                        leaf peak {
                                            type yang:gauge64;
                                            description "The peak value for the resource";
                                        }

                                        leaf peak-timestamp {
                                            type types-sros:date-time;
                                            description "The timestamp when the peak value was observed";
                                        }

                                    } // container upstream

                                    container downstream {
                                        description "Enter the downstream context";

                                        leaf value {
                                            type yang:gauge64;
                                            description "Actual consumed value";
                                        }

                                        leaf max {
                                            type uint64;
                                            description "The max value this resource can have, depending on the configuration";
                                        }

                                        leaf peak {
                                            type yang:gauge64;
                                            description "The peak value for the resource";
                                        }

                                        leaf peak-timestamp {
                                            type types-sros:date-time;
                                            description "The timestamp when the peak value was observed";
                                        }

                                    } // container downstream

                                } // container fragment-bufs

                                container dormant-subscribers {
                                    description "Enter the dormant-subscribers context";

                                    leaf value {
                                        type yang:gauge64;
                                        description "Actual consumed value";
                                    }

                                    leaf max {
                                        type uint64;
                                        description "The max value this resource can have, depending on the configuration";
                                    }

                                    leaf peak {
                                        type yang:gauge64;
                                        description "The peak value for the resource";
                                    }

                                    leaf peak-timestamp {
                                        type types-sros:date-time;
                                        description "The timestamp when the peak value was observed";
                                    }

                                } // container dormant-subscribers

                                container upnp {
                                    description "Enter the upnp context";

                                    container mappings {
                                        description "Enter the mappings context";

                                        leaf value {
                                            type yang:gauge64;
                                            description "Actual consumed value";
                                        }

                                        leaf max {
                                            type uint64;
                                            description "The max value this resource can have, depending on the configuration";
                                        }

                                        leaf peak {
                                            type yang:gauge64;
                                            description "The peak value for the resource";
                                        }

                                        leaf peak-timestamp {
                                            type types-sros:date-time;
                                            description "The timestamp when the peak value was observed";
                                        }

                                    } // container mappings

                                    container sessions {
                                        description "Enter the sessions context";

                                        leaf value {
                                            type yang:gauge64;
                                            description "Actual consumed value";
                                        }

                                        leaf max {
                                            type uint64;
                                            description "The max value this resource can have, depending on the configuration";
                                        }

                                        leaf peak {
                                            type yang:gauge64;
                                            description "The peak value for the resource";
                                        }

                                        leaf peak-timestamp {
                                            type types-sros:date-time;
                                            description "The timestamp when the peak value was observed";
                                        }

                                    } // container sessions

                                } // container upnp

                                container pppoe-sessions {
                                    description "Enter the pppoe-sessions context";

                                    leaf value {
                                        type yang:gauge64;
                                        description "Actual consumed value";
                                    }

                                    leaf max {
                                        type uint64;
                                        description "The max value this resource can have, depending on the configuration";
                                    }

                                    leaf peak {
                                        type yang:gauge64;
                                        description "The peak value for the resource";
                                    }

                                    leaf peak-timestamp {
                                        type types-sros:date-time;
                                        description "The timestamp when the peak value was observed";
                                    }

                                } // container pppoe-sessions

                            } // container resources

                            container statistics {
                                description "Enter the statistics context";

                                container ip-forwarding {
                                    description "Enter the ip-forwarding context";

                                    leaf fragments {
                                        type yang:counter64;
                                        description "Fragments handled";
                                    }

                                    leaf reassembled-packets {
                                        type yang:counter64;
                                        description "Frames reassembled";
                                    }

                                    leaf forwarded-packets {
                                        type yang:counter64;
                                        description "Frames forwarded";
                                    }

                                    container receive-errors {
                                        description "Enter the receive-errors context";

                                        leaf l2-error {
                                            type yang:counter64;
                                            description "L2 parse error";
                                        }

                                        leaf l3-not-ip {
                                            type yang:counter64;
                                            description "L3 is not IPv4 or IPv6";
                                        }

                                        leaf ip-invalid-checksum {
                                            type yang:counter64;
                                            description "IPv4 invalid checksum";
                                        }

                                        leaf ip-malformed-header {
                                            type yang:counter64;
                                            description "IP malformed header";
                                        }

                                        leaf ip-malformed-packet {
                                            type yang:counter64;
                                            description "IP malformed packet";
                                        }

                                        leaf ip-zero-ttl {
                                            type yang:counter64;
                                            description "IP zero ttl";
                                        }

                                        leaf ip-opts-or-ext-headers {
                                            type yang:counter64;
                                            description "IPv4 options or IPv6 extension headers";
                                        }

                                        leaf ip-fragment-unsupported {
                                            type yang:counter64;
                                            description "IP fragment unsupported";
                                        }

                                        leaf ip-error {
                                            type yang:counter64;
                                            description "IP parse error";
                                        }

                                        leaf tcp-udp-malformed-header {
                                            type yang:counter64;
                                            description "TCP/UDP malformed header";
                                        }

                                        leaf tcp-udp-invalid-checksum {
                                            type yang:counter64;
                                            description "TCP/UDP invalid checksum";
                                        }

                                        leaf other {
                                            type yang:counter64;
                                            description "Other parse error";
                                        }

                                    } // container receive-errors

                                    container reassembly-errors {
                                        description "Enter the reassembly-errors context";

                                        leaf too-many-fragmented-packets {
                                            type yang:counter64;
                                            description "Too many fragmented packets";
                                        }

                                        leaf too-many-fragment-buffers {
                                            type yang:counter64;
                                            description "Too many fragment buffers";
                                        }

                                        leaf too-many-fragment-holes {
                                            type yang:counter64;
                                            description "Too many fragment holes";
                                        }

                                        leaf fragment-filtered {
                                            type yang:counter64;
                                            description "Fragments filtered";
                                        }

                                        leaf fragment-not-supported {
                                            type yang:counter64;
                                            description "Fragment not supported";
                                        }

                                        leaf fragment-list-expired {
                                            type yang:counter64;
                                            description "Fragment list expired";
                                        }

                                        leaf fragment-list-cleanup-in-progress {
                                            type yang:counter64;
                                            description "Fragment list cleanup in progress";
                                        }

                                        leaf reassembly-failed {
                                            type yang:counter64;
                                            description "Reassembly failed";
                                        }

                                    } // container reassembly-errors

                                } // container ip-forwarding

                                container pppoe-client {
                                    description "Enter the pppoe-client context";

                                    leaf rx-error-l2 {
                                        type yang:counter64;
                                        description "Number of packets received with layer 2 parse errors";
                                    }

                                    leaf rx-error-invalid-headers {
                                        type yang:counter64;
                                        description "Number of packets received with invalid PPPoE headers";
                                    }

                                    leaf rx-error-invalid-magic {
                                        type yang:counter64;
                                        description "Number of LCP echo-request or echo-reply packets received with an invalid magic number";
                                    }

                                    leaf rx-error-no-session {
                                        type yang:counter64;
                                        description "Number of LCP echo or data packets received without an associated session";
                                    }

                                    leaf rx-discovery {
                                        type yang:counter64;
                                        description "Number of PPPoE discovery packets received";
                                    }

                                    leaf rx-ppp-control {
                                        type yang:counter64;
                                        description "Number of PPP control packets received";
                                    }

                                    leaf rx-lcp-echo-request {
                                        type yang:counter64;
                                        description "Number of LCP echo-request packets received";
                                    }

                                    leaf rx-lcp-echo-reply {
                                        type yang:counter64;
                                        description "Number of LCP echo-reply packets received";
                                    }

                                    leaf tx-lcp-echo-request {
                                        type yang:counter64;
                                        description "Number of LCP echo-request packets transmitted";
                                    }

                                    leaf tx-lcp-echo-reply {
                                        type yang:counter64;
                                        description "Number of LCP echo-reply packets transmitted";
                                    }

                                } // container pppoe-client

                                container nat {
                                    description "Enter the nat context";

                                    container dropped {
                                        description "Enter the dropped context";

                                        container general {
                                            description "Enter the general context";

                                            leaf arp {
                                                type yang:counter64;
                                                description "ARP frames are ignored";
                                            }

                                            leaf checksum-calculation-error {
                                                type yang:counter64;
                                                description "Error while calculating L4 checksum before transmitting";
                                            }

                                            leaf send-error {
                                                type yang:counter64;
                                                description "Packet send error";
                                            }

                                            leaf no-copy-buffer {
                                                type yang:counter64;
                                                description "No buffer to copy frame";
                                            }

                                            leaf mtu-exceeded {
                                                type yang:counter64;
                                                description "Egress MTU exceeded";
                                            }

                                            leaf multicast {
                                                type yang:counter64;
                                                description "Multicast dropped";
                                            }

                                        } // container general

                                        container receive-errors {
                                            description "Enter the receive-errors context";

                                            leaf l2-error {
                                                type yang:counter64;
                                                description "L2 parse error";
                                            }

                                            leaf l3-not-ip {
                                                type yang:counter64;
                                                description "L3 is not IPv4 or IPv6";
                                            }

                                            leaf ip-invalid-checksum {
                                                type yang:counter64;
                                                description "IPv4 invalid checksum";
                                            }

                                            leaf ip-malformed-header {
                                                type yang:counter64;
                                                description "IP malformed header";
                                            }

                                            leaf ip-malformed-packet {
                                                type yang:counter64;
                                                description "IP malformed packet";
                                            }

                                            leaf ip-zero-ttl {
                                                type yang:counter64;
                                                description "IP zero ttl";
                                            }

                                            leaf ip-opts-or-ext-headers {
                                                type yang:counter64;
                                                description "IPv4 options or IPv6 extension headers";
                                            }

                                            leaf ip-parse-error {
                                                type yang:counter64;
                                                description "IP parse error";
                                            }

                                            leaf ipv6-fragments-unsupported {
                                                type yang:counter64;
                                                description "IPv6 fragments unsupported";
                                            }

                                            leaf ipv6-extension-header-parse-error {
                                                type yang:counter64;
                                                description "IPv6 extension headers parse error";
                                            }

                                            leaf dslite-unsupported-next-header {
                                                type yang:counter64;
                                                description "Dual-stack-lite next header unsupported";
                                            }

                                            leaf l4-unsupported-protocol {
                                                type yang:counter64;
                                                description "Unsupported L4 protocol";
                                            }

                                            leaf tcp-udp-malformed-header {
                                                type yang:counter64;
                                                description "TCP/UDP malformed header";
                                            }

                                            leaf tcp-udp-invalid-checksum {
                                                type yang:counter64;
                                                description "TCP/UDP invalid checksum";
                                            }

                                            leaf icmp-embedded-ipv6-extension-header-parse-error {
                                                type yang:counter64;
                                                description "ICMP embedded IPv6 extension header parse error";
                                            }

                                            leaf other-parse-error {
                                                type yang:counter64;
                                                description "Other parse error";
                                            }

                                        } // container receive-errors

                                        container flow {
                                            description "Enter the flow context";

                                            leaf no-matching-flow {
                                                type yang:counter64;
                                                description "No matching flow";
                                            }

                                            leaf forwarding-blocked {
                                                type yang:counter64;
                                                description "Management core has blocked new flow creation or forwarding. Reasons include policies or port-blocks being released.";
                                            }

                                            leaf tcp-resetting {
                                                type yang:counter64;
                                                description "TCP flow is in reset state but not yet cleaned up";
                                            }

                                        } // container flow

                                        container flow-creation-failed {
                                            description "Enter the flow-creation-failed context";

                                            leaf no-resources {
                                                type yang:counter64;
                                                description "No resources";
                                            }

                                            leaf no-host-resources {
                                                type yang:counter64;
                                                description "Could not create host";
                                            }

                                            leaf no-ip-or-port-resources {
                                                type yang:counter64;
                                                description "Could not allocate ip or port-range";
                                            }

                                            leaf max-flows-exceeded {
                                                type yang:counter64;
                                                description "Max number of flows exceeded";
                                            }

                                            leaf ipv6-downstream-prohibited {
                                                type yang:counter64;
                                                description "IPv6 downstream traffic prohibited";
                                            }

                                            leaf address-dependent-filtering {
                                                type yang:counter64;
                                                description "Address dependent filtering";
                                            }

                                            leaf firewall-address-dependent-filtering {
                                                type yang:counter64;
                                                description "Firewall address dependent filtering";
                                            }

                                            leaf transient-no-policy {
                                                type yang:counter64;
                                                description "Policy could temporarily not be used";
                                            }

                                            leaf unmatched-policy {
                                                type yang:counter64;
                                                description "Matched policy not in use by subscriber";
                                            }

                                            leaf conflicting-policies {
                                                type yang:counter64;
                                                description "Conflicting policies";
                                            }

                                            leaf port-range-log-failed {
                                                type yang:counter64;
                                                description "Logging of port range allocation failed";
                                            }

                                            leaf flow-log-failed {
                                                type yang:counter64;
                                                description "Logging of flow creation failed";
                                            }

                                            leaf multiple-host-or-subscriber-ip {
                                                type yang:counter64;
                                                description "No multiple host or subscriber IPs allowed";
                                            }

                                            leaf destination-nat-destination-mismatch {
                                                type yang:counter64;
                                                description "Destination NAT destination IP mismatch";
                                            }

                                            leaf destination-nat-foreign-mismatch {
                                                type yang:counter64;
                                                description "Destination NAT foreign IP mismatch";
                                            }

                                            leaf ambiguous-flow-key {
                                                type yang:counter64;
                                                description "Ambiguous flow key";
                                            }

                                            leaf requested-port-not-in-host-range {
                                                type yang:counter64;
                                                description "Requested port not in host port range";
                                            }

                                            leaf destination-not-routable {
                                                type yang:counter64;
                                                description "Destination IP is not routable";
                                            }

                                            leaf dslite-unknown-aftr {
                                                type yang:counter64;
                                                description "Dual-stack-lite unknown AFTR address";
                                            }

                                            leaf pppoe-uplink-down {
                                                type yang:counter64;
                                                description "PPPoE uplink down";
                                            }

                                            leaf subscriber-id-unknown {
                                                type yang:counter64;
                                                description "Subscriber-id unknown";
                                            }

                                            leaf tcp-unexpected-rst {
                                                type yang:counter64;
                                                description "No flow creation on TCP RST";
                                            }

                                            leaf tcp-unexpected-fin {
                                                type yang:counter64;
                                                description "No flow creation on TCP FIN";
                                            }

                                            leaf tcp-unexpected-flags {
                                                type yang:counter64;
                                                description "No flow creation for invalid flags combinations";
                                            }

                                            leaf portrange-outside-ip-conflict {
                                                type yang:counter64;
                                                description "conflict between forced port range and outside IP of existing flow";
                                            }

                                            leaf requested-outside-port-conflict {
                                                type yang:counter64;
                                                description "conflict between requested outside port and outside port of existing flow";
                                            }

                                        } // container flow-creation-failed

                                        container icmp {
                                            description "Enter the icmp context";

                                            leaf unsupported-type-v4 {
                                                type yang:counter64;
                                                description "ICMP type unsupported";
                                            }

                                            leaf unsupported-type-v6 {
                                                type yang:counter64;
                                                description "ICMPv6 type unsupported";
                                            }

                                            leaf unsupported-type-for-translation {
                                                type yang:counter64;
                                                description "ICMP type unsupported for 4 to 6 translation";
                                            }

                                            leaf unsupported-length-for-translation {
                                                type yang:counter64;
                                                description "ICMP length error for 4 to 6 translation";
                                            }

                                            leaf unsupported-local {
                                                type yang:counter64;
                                                description "ICMP to l2aware-host gateway address unsupported";
                                            }

                                            leaf invalid-checksum {
                                                type yang:counter64;
                                                description "ICMP/ICMPv6 invalid checksum";
                                            }

                                            leaf embedded-invalid-checksum {
                                                type yang:counter64;
                                                description "ICMP invalid embedded IP checksum";
                                            }

                                            leaf unsupported-embedded-l3 {
                                                type yang:counter64;
                                                description "ICMP/ICMPv6 invalid embedded IP";
                                            }

                                            leaf unsupported-embedded-l4 {
                                                type yang:counter64;
                                                description "ICMP/ICMPv6 invalid embedded L4";
                                            }

                                            leaf too-short {
                                                type yang:counter64;
                                                description "ICMP/ICMPv6 too short";
                                            }

                                            leaf invalid-length {
                                                type yang:counter64;
                                                description "ICMP/ICMPv6 invalid length";
                                            }

                                            leaf fragmented {
                                                type yang:counter64;
                                                description "ICMP/ICMPv6 fragmentation";
                                            }

                                            leaf icmp6-packet-too-big {
                                                type yang:counter64;
                                                description "ICMP6 Packet-Too-Big with mtu < 1280";
                                            }

                                        } // container icmp

                                        container nat64 {
                                            description "Enter the nat64 context";

                                            leaf disabled {
                                                type yang:counter64;
                                                description "NAT64 disabled";
                                            }

                                            leaf invalid-source-address {
                                                type yang:counter64;
                                                description "NAT64 invalid source address";
                                            }

                                            leaf fragment-zero-checksum {
                                                type yang:counter64;
                                                description "NAT64 fragment has zero checksum";
                                            }

                                            leaf ipv4-zero-checksum {
                                                type yang:counter64;
                                                description "NAT64 IPv4 zero checksum";
                                            }

                                            leaf icmp-fragment-unsupported {
                                                type yang:counter64;
                                                description "NAT64 ICMP fragments unsupported";
                                            }

                                            leaf unknown-next-header {
                                                type yang:counter64;
                                                description "NAT64 unknown next header";
                                            }

                                            leaf embedded-ipv4-options {
                                                type yang:counter64;
                                                description "NAT64 ICMP embedded IPv4 options";
                                            }

                                        } // container nat64

                                        container fragments {
                                            description "Enter the fragments context";

                                            leaf too-many-fragmented-packets {
                                                type yang:counter64;
                                                description "Too many fragmented packets";
                                            }

                                            leaf too-many-fragment-buffers {
                                                type yang:counter64;
                                                description "Fragmentation buffers exhausted";
                                            }

                                            leaf too-many-fragment-holes {
                                                type yang:counter64;
                                                description "Too many fragment holes";
                                            }

                                            leaf too-many-fragments-per-packet {
                                                type yang:counter64;
                                                description "Too many fragments for IP packet";
                                            }

                                            leaf too-many-fragment-lists-for-flow {
                                                type yang:counter64;
                                                description "Too many fragment lists for flow";
                                            }

                                            leaf fragment-list-expired {
                                                type yang:counter64;
                                                description "Fragment list expired";
                                            }

                                            leaf fragment-list-cleanup-in-progress {
                                                type yang:counter64;
                                                description "Fragment list cleanup in progress";
                                            }

                                            leaf reassembly-failed {
                                                type yang:counter64;
                                                description "Reassembly failed";
                                            }

                                        } // container fragments

                                        container radius {
                                            description "Enter the radius context";

                                            leaf error {
                                                type yang:counter64;
                                                description "Error while processing RADIUS packet";
                                            }

                                            leaf no-send-resources {
                                                type yang:counter64;
                                                description "No resources to send RADIUS packet";
                                            }

                                        } // container radius

                                        container upnp {
                                            description "Enter the upnp context";

                                            leaf ssdp {
                                                type yang:counter64;
                                                description "SSDP dropped";
                                            }

                                            leaf control {
                                                type yang:counter64;
                                                description "UPnP control dropped";
                                            }

                                        } // container upnp

                                        container service-chaining {
                                            description "Enter the service-chaining context";

                                            leaf tx-error {
                                                type yang:counter64;
                                                description "Transmit error";
                                            }

                                            leaf rx-error {
                                                type yang:counter64;
                                                description "Receive error";
                                            }

                                            leaf rx-unsupported {
                                                type yang:counter64;
                                                description "Unhandled frames";
                                            }

                                            leaf filter-action-drop {
                                                type yang:counter64;
                                                description "Frames dropped by vas-filter";
                                            }

                                        } // container service-chaining

                                        container inter-chassis-sync {
                                            description "Enter the inter-chassis-sync context";

                                            leaf standby-drop {
                                                type yang:counter64;
                                                description "Standby drop";
                                            }

                                        } // container inter-chassis-sync

                                    } // container dropped

                                    container flow {
                                        description "Enter the flow context";

                                        leaf new-flow {
                                            type yang:counter64;
                                            description "New flow created";
                                        }

                                        leaf found-flow {
                                            type yang:counter64;
                                            description "Frame matched existing flow";
                                        }

                                        leaf tcp-closed {
                                            type yang:counter64;
                                            description "Flow terminated by TCP session close";
                                        }

                                        container timeouts {
                                            description "Enter the timeouts context";

                                            leaf tcp-expired {
                                                type yang:counter64;
                                                description "TCP flow expired";
                                            }

                                            leaf udp-expired {
                                                type yang:counter64;
                                                description "UDP flow expired";
                                            }

                                            leaf icmp-expired {
                                                type yang:counter64;
                                                description "ICMP/ICMPv6 flow expired";
                                            }

                                            leaf gre-expired {
                                                type yang:counter64;
                                                description "GRE flow expired";
                                            }

                                            leaf ipv6-any-l4-expired {
                                                type yang:counter64;
                                                description "Any IPv6 L4 flow expired";
                                            }

                                        } // container timeouts

                                    } // container flow

                                    container icmp {
                                        description "Enter the icmp context";

                                        leaf to-local {
                                            type yang:counter64;
                                            description "ICMP to local address";
                                        }

                                    } // container icmp

                                    container dslite {
                                        description "Enter the dslite context";

                                        leaf forward {
                                            type yang:counter64;
                                            description "IPv6 dual-stack-lite frame forwarded";
                                        }

                                    } // container dslite

                                    container fragmentation {
                                        description "Enter the fragmentation context";

                                        leaf ipv4 {
                                            type yang:counter64;
                                            description "IPv4 frame was fragmented";
                                        }

                                        leaf ipv6 {
                                            type yang:counter64;
                                            description "IPv6 frame was fragmented";
                                        }

                                    } // container fragmentation

                                    container reassembly {
                                        description "Enter the reassembly context";

                                        leaf packets {
                                            type yang:counter64;
                                            description "Reassembled frames";
                                        }

                                    } // container reassembly

                                    container flow-log {
                                        description "Enter the flow-log context";

                                        leaf logged-flow-create {
                                            type yang:counter64;
                                            description "Flow create logged";
                                        }

                                        leaf logged-flow-delete {
                                            type yang:counter64;
                                            description "Flow delete logged";
                                        }

                                        leaf tx-packet {
                                            type yang:counter64;
                                            description "Transmitted flow log frames";
                                        }

                                        leaf rate-limit-drop {
                                            type yang:counter64;
                                            description "Flow log frames dropped by rate limiting";
                                        }

                                    } // container flow-log

                                    container radius {
                                        description "Enter the radius context";

                                        leaf to-local {
                                            type yang:counter64;
                                            description "Frame handled by local radius client";
                                        }

                                    } // container radius

                                    container subscriber-id-cache {
                                        description "Enter the subscriber-id-cache context";

                                        leaf cached {
                                            type yang:counter64;
                                            description "Subscriber-id cached";
                                        }

                                        leaf delayed {
                                            type yang:counter64;
                                            description "Subscriber-id delayed";
                                        }

                                        leaf cache-timeout {
                                            type yang:counter64;
                                            description "Subscriber-id timeout";
                                        }

                                    } // container subscriber-id-cache

                                    container fragments {
                                        description "Enter the fragments context";

                                        leaf rx-large-scale {
                                            type yang:counter64;
                                            description "Fragments received on large-scale nat interface";
                                        }

                                        leaf rx-dual-stack-lite {
                                            type yang:counter64;
                                            description "Fragments received on dual-stack-lite interface";
                                        }

                                        leaf rx-dormant {
                                            type yang:counter64;
                                            description "Fragments received on dormant interface";
                                        }

                                        leaf rx-l2aware {
                                            type yang:counter64;
                                            description "Fragments received on l2aware interface";
                                        }

                                        leaf rx-outside {
                                            type yang:counter64;
                                            description "Fragments received on outside interface";
                                        }

                                        leaf tx-large-scale {
                                            type yang:counter64;
                                            description "Fragments transmitted on large-scale nat interface";
                                        }

                                        leaf tx-dual-stack-lite {
                                            type yang:counter64;
                                            description "Fragments transmitted on dual-stack-lite interface";
                                        }

                                        leaf tx-dormant {
                                            type yang:counter64;
                                            description "Fragments transmitted on dormant interface";
                                        }

                                        leaf tx-l2aware {
                                            type yang:counter64;
                                            description "Fragments transmitted on l2aware interface";
                                        }

                                        leaf tx-nat64 {
                                            type yang:counter64;
                                            description "Fragments transmitted on nat64 interface";
                                        }

                                        leaf tx-outside {
                                            type yang:counter64;
                                            description "Fragments transmitted on outside interface";
                                        }

                                    } // container fragments

                                    container upnp {
                                        description "Enter the upnp context";

                                        leaf ssdp-rx {
                                            type yang:counter64;
                                            description "SSDP frames received";
                                        }

                                        leaf ssdp-tx {
                                            type yang:counter64;
                                            description "SSDP frames transmitted";
                                        }

                                        leaf control-rx {
                                            type yang:counter64;
                                            description "UPnP control frames received";
                                        }

                                        leaf control-tx {
                                            type yang:counter64;
                                            description "UPnP control frames transmitted";
                                        }

                                        leaf rate-limited-request {
                                            type yang:counter64;
                                            description "UPnP query rate limited";
                                        }

                                        leaf pinhole-without-default-policy {
                                            type yang:counter64;
                                            description "Attempt to create pinhole without default policy";
                                        }

                                        leaf pinhole-without-source-nat {
                                            type yang:counter64;
                                            description "Attempt to create pinhole with source-nat disabled";
                                        }

                                    } // container upnp

                                    container service-chaining {
                                        description "Enter the service-chaining context";

                                        leaf rx {
                                            type yang:counter64;
                                            description "Service-chaining frames received";
                                        }

                                        leaf tx {
                                            type yang:counter64;
                                            description "Service-chaining frames transmitted";
                                        }

                                    } // container service-chaining

                                } // container nat

                            } // container statistics

                        } // container nat

                        container performance {
                            description "Enter the performance context";

                            container last-hour {
                                description "Enter the last-hour context";

                                list minutes-ago {
                                    key "index";
                                    description "Enter the minutes-ago list instance";

                                    leaf index {
                                        type uint32;
                                        description "Numerical index value generated by the system.";
                                    }

                                    leaf timestamp {
                                        type yang:date-and-time;
                                        description "Time at which the measurement was taken";
                                    }

                                    leaf waiting {
                                        type decimal64 {
                                            range "0..100";
                                            fraction-digits 2;
                                        }
                                        units "percent";
                                        description "Relative time spent waiting in the measured period.";
                                    }

                                    leaf idling {
                                        type decimal64 {
                                            range "0..100";
                                            fraction-digits 2;
                                        }
                                        units "percent";
                                        description "Relative time spent idling in the measured period.";
                                    }

                                    leaf working {
                                        type decimal64 {
                                            range "0..100";
                                            fraction-digits 2;
                                        }
                                        units "percent";
                                        description "Relative time spent working in the measured period.";
                                    }

                                    leaf jobs {
                                        type uint32;
                                        description "The number of jobs performed in the measured period.";
                                    }

                                    leaf throughput {
                                        type uint64;
                                        units "bytes";
                                        description "The amount of data processed in the measured period.";
                                    }

                                } // list minutes-ago

                            } // container last-hour

                            container last-day {
                                description "Enter the last-day context";

                                list hours-ago {
                                    key "index";
                                    description "Enter the hours-ago list instance";

                                    leaf index {
                                        type uint32;
                                        description "Numerical index value generated by the system.";
                                    }

                                    leaf timestamp {
                                        type yang:date-and-time;
                                        description "Time at which the measurement was taken";
                                    }

                                    leaf waiting {
                                        type decimal64 {
                                            range "0..100";
                                            fraction-digits 2;
                                        }
                                        units "percent";
                                        description "Relative time spent waiting in the measured period.";
                                    }

                                    leaf idling {
                                        type decimal64 {
                                            range "0..100";
                                            fraction-digits 2;
                                        }
                                        units "percent";
                                        description "Relative time spent idling in the measured period.";
                                    }

                                    leaf working {
                                        type decimal64 {
                                            range "0..100";
                                            fraction-digits 2;
                                        }
                                        units "percent";
                                        description "Relative time spent working in the measured period.";
                                    }

                                    leaf jobs {
                                        type uint32;
                                        description "The number of jobs performed in the measured period.";
                                    }

                                    leaf throughput {
                                        type uint64;
                                        units "bytes";
                                        description "The amount of data processed in the measured period.";
                                    }

                                } // list hours-ago

                            } // container last-day

                            container last-month {
                                description "Enter the last-month context";

                                list days-ago {
                                    key "index";
                                    description "Enter the days-ago list instance";

                                    leaf index {
                                        type uint32;
                                        description "Numerical index value generated by the system.";
                                    }

                                    leaf timestamp {
                                        type yang:date-and-time;
                                        description "Time at which the measurement was taken";
                                    }

                                    leaf waiting {
                                        type decimal64 {
                                            range "0..100";
                                            fraction-digits 2;
                                        }
                                        units "percent";
                                        description "Relative time spent waiting in the measured period.";
                                    }

                                    leaf idling {
                                        type decimal64 {
                                            range "0..100";
                                            fraction-digits 2;
                                        }
                                        units "percent";
                                        description "Relative time spent idling in the measured period.";
                                    }

                                    leaf working {
                                        type decimal64 {
                                            range "0..100";
                                            fraction-digits 2;
                                        }
                                        units "percent";
                                        description "Relative time spent working in the measured period.";
                                    }

                                    leaf jobs {
                                        type uint32;
                                        description "The number of jobs performed in the measured period.";
                                    }

                                    leaf throughput {
                                        type uint64;
                                        units "bytes";
                                        description "The amount of data processed in the measured period.";
                                    }

                                } // list days-ago

                            } // container last-month

                        } // container performance

                    } // list mda

                } // list iom

                list mda {
                    key "mda-id";
                    description "Enter the mda list instance";

                    leaf mda-id {
                        type types-isa:slot-mda;
                        description "MDA slot value";
                    }

                    leaf oper-state {
                        type types-isa:nat-member-operational-state;
                        description "Operational status of a WLAN-GW group MDA";
                    }

                    container nat {
                        description "Enter the nat context";

                        leaf peak-values-last-reset {
                            type yang:date-and-time;
                            description "Moment when the peak values were last reset";
                        }

                        container resources {
                            description "Enter the resources context";

                            container flows {
                                description "Enter the flows context";

                                leaf value {
                                    type yang:gauge64;
                                    description "Actual consumed value";
                                }

                                leaf max {
                                    type uint64;
                                    description "The max value this resource can have, depending on the configuration";
                                }

                                leaf peak {
                                    type yang:gauge64;
                                    description "The peak value for the resource";
                                }

                                leaf peak-timestamp {
                                    type types-sros:date-time;
                                    description "The timestamp when the peak value was observed";
                                }

                            } // container flows

                            container policies {
                                description "Enter the policies context";

                                leaf value {
                                    type yang:gauge64;
                                    description "Actual consumed value";
                                }

                                leaf max {
                                    type uint64;
                                    description "The max value this resource can have, depending on the configuration";
                                }

                                leaf peak {
                                    type yang:gauge64;
                                    description "The peak value for the resource";
                                }

                                leaf peak-timestamp {
                                    type types-sros:date-time;
                                    description "The timestamp when the peak value was observed";
                                }

                            } // container policies

                            container subscriber-cache-entries {
                                description "Enter the subscriber-cache-entries context";

                                leaf value {
                                    type yang:gauge64;
                                    description "Actual consumed value";
                                }

                                leaf max {
                                    type uint64;
                                    description "The max value this resource can have, depending on the configuration";
                                }

                                leaf peak {
                                    type yang:gauge64;
                                    description "The peak value for the resource";
                                }

                                leaf peak-timestamp {
                                    type types-sros:date-time;
                                    description "The timestamp when the peak value was observed";
                                }

                            } // container subscriber-cache-entries

                            container delayed-icmps {
                                description "Enter the delayed-icmps context";

                                leaf value {
                                    type yang:gauge64;
                                    description "Actual consumed value";
                                }

                                leaf max {
                                    type uint64;
                                    description "The max value this resource can have, depending on the configuration";
                                }

                                leaf peak {
                                    type yang:gauge64;
                                    description "The peak value for the resource";
                                }

                                leaf peak-timestamp {
                                    type types-sros:date-time;
                                    description "The timestamp when the peak value was observed";
                                }

                            } // container delayed-icmps

                            container alg-session {
                                description "Enter the alg-session context";

                                leaf value {
                                    type yang:gauge64;
                                    description "Actual consumed value";
                                }

                                leaf max {
                                    type uint64;
                                    description "The max value this resource can have, depending on the configuration";
                                }

                                leaf peak {
                                    type yang:gauge64;
                                    description "The peak value for the resource";
                                }

                                leaf peak-timestamp {
                                    type types-sros:date-time;
                                    description "The timestamp when the peak value was observed";
                                }

                            } // container alg-session

                            container fragment-lists {
                                description "Enter the fragment-lists context";

                                container upstream {
                                    description "Enter the upstream context";

                                    leaf value {
                                        type yang:gauge64;
                                        description "Actual consumed value";
                                    }

                                    leaf max {
                                        type uint64;
                                        description "The max value this resource can have, depending on the configuration";
                                    }

                                    leaf peak {
                                        type yang:gauge64;
                                        description "The peak value for the resource";
                                    }

                                    leaf peak-timestamp {
                                        type types-sros:date-time;
                                        description "The timestamp when the peak value was observed";
                                    }

                                } // container upstream

                                container downstream {
                                    description "Enter the downstream context";

                                    leaf value {
                                        type yang:gauge64;
                                        description "Actual consumed value";
                                    }

                                    leaf max {
                                        type uint64;
                                        description "The max value this resource can have, depending on the configuration";
                                    }

                                    leaf peak {
                                        type yang:gauge64;
                                        description "The peak value for the resource";
                                    }

                                    leaf peak-timestamp {
                                        type types-sros:date-time;
                                        description "The timestamp when the peak value was observed";
                                    }

                                } // container downstream

                            } // container fragment-lists

                            container fragment-holes {
                                description "Enter the fragment-holes context";

                                container upstream {
                                    description "Enter the upstream context";

                                    leaf value {
                                        type yang:gauge64;
                                        description "Actual consumed value";
                                    }

                                    leaf max {
                                        type uint64;
                                        description "The max value this resource can have, depending on the configuration";
                                    }

                                    leaf peak {
                                        type yang:gauge64;
                                        description "The peak value for the resource";
                                    }

                                    leaf peak-timestamp {
                                        type types-sros:date-time;
                                        description "The timestamp when the peak value was observed";
                                    }

                                } // container upstream

                                container downstream {
                                    description "Enter the downstream context";

                                    leaf value {
                                        type yang:gauge64;
                                        description "Actual consumed value";
                                    }

                                    leaf max {
                                        type uint64;
                                        description "The max value this resource can have, depending on the configuration";
                                    }

                                    leaf peak {
                                        type yang:gauge64;
                                        description "The peak value for the resource";
                                    }

                                    leaf peak-timestamp {
                                        type types-sros:date-time;
                                        description "The timestamp when the peak value was observed";
                                    }

                                } // container downstream

                            } // container fragment-holes

                            container fragment-bufs {
                                description "Enter the fragment-bufs context";

                                container upstream {
                                    description "Enter the upstream context";

                                    leaf value {
                                        type yang:gauge64;
                                        description "Actual consumed value";
                                    }

                                    leaf max {
                                        type uint64;
                                        description "The max value this resource can have, depending on the configuration";
                                    }

                                    leaf peak {
                                        type yang:gauge64;
                                        description "The peak value for the resource";
                                    }

                                    leaf peak-timestamp {
                                        type types-sros:date-time;
                                        description "The timestamp when the peak value was observed";
                                    }

                                } // container upstream

                                container downstream {
                                    description "Enter the downstream context";

                                    leaf value {
                                        type yang:gauge64;
                                        description "Actual consumed value";
                                    }

                                    leaf max {
                                        type uint64;
                                        description "The max value this resource can have, depending on the configuration";
                                    }

                                    leaf peak {
                                        type yang:gauge64;
                                        description "The peak value for the resource";
                                    }

                                    leaf peak-timestamp {
                                        type types-sros:date-time;
                                        description "The timestamp when the peak value was observed";
                                    }

                                } // container downstream

                            } // container fragment-bufs

                            container dormant-subscribers {
                                description "Enter the dormant-subscribers context";

                                leaf value {
                                    type yang:gauge64;
                                    description "Actual consumed value";
                                }

                                leaf max {
                                    type uint64;
                                    description "The max value this resource can have, depending on the configuration";
                                }

                                leaf peak {
                                    type yang:gauge64;
                                    description "The peak value for the resource";
                                }

                                leaf peak-timestamp {
                                    type types-sros:date-time;
                                    description "The timestamp when the peak value was observed";
                                }

                            } // container dormant-subscribers

                            container upnp {
                                description "Enter the upnp context";

                                container mappings {
                                    description "Enter the mappings context";

                                    leaf value {
                                        type yang:gauge64;
                                        description "Actual consumed value";
                                    }

                                    leaf max {
                                        type uint64;
                                        description "The max value this resource can have, depending on the configuration";
                                    }

                                    leaf peak {
                                        type yang:gauge64;
                                        description "The peak value for the resource";
                                    }

                                    leaf peak-timestamp {
                                        type types-sros:date-time;
                                        description "The timestamp when the peak value was observed";
                                    }

                                } // container mappings

                                container sessions {
                                    description "Enter the sessions context";

                                    leaf value {
                                        type yang:gauge64;
                                        description "Actual consumed value";
                                    }

                                    leaf max {
                                        type uint64;
                                        description "The max value this resource can have, depending on the configuration";
                                    }

                                    leaf peak {
                                        type yang:gauge64;
                                        description "The peak value for the resource";
                                    }

                                    leaf peak-timestamp {
                                        type types-sros:date-time;
                                        description "The timestamp when the peak value was observed";
                                    }

                                } // container sessions

                            } // container upnp

                            container pppoe-sessions {
                                description "Enter the pppoe-sessions context";

                                leaf value {
                                    type yang:gauge64;
                                    description "Actual consumed value";
                                }

                                leaf max {
                                    type uint64;
                                    description "The max value this resource can have, depending on the configuration";
                                }

                                leaf peak {
                                    type yang:gauge64;
                                    description "The peak value for the resource";
                                }

                                leaf peak-timestamp {
                                    type types-sros:date-time;
                                    description "The timestamp when the peak value was observed";
                                }

                            } // container pppoe-sessions

                        } // container resources

                        container statistics {
                            description "Enter the statistics context";

                            container ip-forwarding {
                                description "Enter the ip-forwarding context";

                                leaf fragments {
                                    type yang:counter64;
                                    description "Fragments handled";
                                }

                                leaf reassembled-packets {
                                    type yang:counter64;
                                    description "Frames reassembled";
                                }

                                leaf forwarded-packets {
                                    type yang:counter64;
                                    description "Frames forwarded";
                                }

                                container receive-errors {
                                    description "Enter the receive-errors context";

                                    leaf l2-error {
                                        type yang:counter64;
                                        description "L2 parse error";
                                    }

                                    leaf l3-not-ip {
                                        type yang:counter64;
                                        description "L3 is not IPv4 or IPv6";
                                    }

                                    leaf ip-invalid-checksum {
                                        type yang:counter64;
                                        description "IPv4 invalid checksum";
                                    }

                                    leaf ip-malformed-header {
                                        type yang:counter64;
                                        description "IP malformed header";
                                    }

                                    leaf ip-malformed-packet {
                                        type yang:counter64;
                                        description "IP malformed packet";
                                    }

                                    leaf ip-zero-ttl {
                                        type yang:counter64;
                                        description "IP zero ttl";
                                    }

                                    leaf ip-opts-or-ext-headers {
                                        type yang:counter64;
                                        description "IPv4 options or IPv6 extension headers";
                                    }

                                    leaf ip-fragment-unsupported {
                                        type yang:counter64;
                                        description "IP fragment unsupported";
                                    }

                                    leaf ip-error {
                                        type yang:counter64;
                                        description "IP parse error";
                                    }

                                    leaf tcp-udp-malformed-header {
                                        type yang:counter64;
                                        description "TCP/UDP malformed header";
                                    }

                                    leaf tcp-udp-invalid-checksum {
                                        type yang:counter64;
                                        description "TCP/UDP invalid checksum";
                                    }

                                    leaf other {
                                        type yang:counter64;
                                        description "Other parse error";
                                    }

                                } // container receive-errors

                                container reassembly-errors {
                                    description "Enter the reassembly-errors context";

                                    leaf too-many-fragmented-packets {
                                        type yang:counter64;
                                        description "Too many fragmented packets";
                                    }

                                    leaf too-many-fragment-buffers {
                                        type yang:counter64;
                                        description "Too many fragment buffers";
                                    }

                                    leaf too-many-fragment-holes {
                                        type yang:counter64;
                                        description "Too many fragment holes";
                                    }

                                    leaf fragment-filtered {
                                        type yang:counter64;
                                        description "Fragments filtered";
                                    }

                                    leaf fragment-not-supported {
                                        type yang:counter64;
                                        description "Fragment not supported";
                                    }

                                    leaf fragment-list-expired {
                                        type yang:counter64;
                                        description "Fragment list expired";
                                    }

                                    leaf fragment-list-cleanup-in-progress {
                                        type yang:counter64;
                                        description "Fragment list cleanup in progress";
                                    }

                                    leaf reassembly-failed {
                                        type yang:counter64;
                                        description "Reassembly failed";
                                    }

                                } // container reassembly-errors

                            } // container ip-forwarding

                            container pppoe-client {
                                description "Enter the pppoe-client context";

                                leaf rx-error-l2 {
                                    type yang:counter64;
                                    description "Number of packets received with layer 2 parse errors";
                                }

                                leaf rx-error-invalid-headers {
                                    type yang:counter64;
                                    description "Number of packets received with invalid PPPoE headers";
                                }

                                leaf rx-error-invalid-magic {
                                    type yang:counter64;
                                    description "Number of LCP echo-request or echo-reply packets received with an invalid magic number";
                                }

                                leaf rx-error-no-session {
                                    type yang:counter64;
                                    description "Number of LCP echo or data packets received without an associated session";
                                }

                                leaf rx-discovery {
                                    type yang:counter64;
                                    description "Number of PPPoE discovery packets received";
                                }

                                leaf rx-ppp-control {
                                    type yang:counter64;
                                    description "Number of PPP control packets received";
                                }

                                leaf rx-lcp-echo-request {
                                    type yang:counter64;
                                    description "Number of LCP echo-request packets received";
                                }

                                leaf rx-lcp-echo-reply {
                                    type yang:counter64;
                                    description "Number of LCP echo-reply packets received";
                                }

                                leaf tx-lcp-echo-request {
                                    type yang:counter64;
                                    description "Number of LCP echo-request packets transmitted";
                                }

                                leaf tx-lcp-echo-reply {
                                    type yang:counter64;
                                    description "Number of LCP echo-reply packets transmitted";
                                }

                            } // container pppoe-client

                            container nat {
                                description "Enter the nat context";

                                container dropped {
                                    description "Enter the dropped context";

                                    container general {
                                        description "Enter the general context";

                                        leaf arp {
                                            type yang:counter64;
                                            description "ARP frames are ignored";
                                        }

                                        leaf checksum-calculation-error {
                                            type yang:counter64;
                                            description "Error while calculating L4 checksum before transmitting";
                                        }

                                        leaf send-error {
                                            type yang:counter64;
                                            description "Packet send error";
                                        }

                                        leaf no-copy-buffer {
                                            type yang:counter64;
                                            description "No buffer to copy frame";
                                        }

                                        leaf mtu-exceeded {
                                            type yang:counter64;
                                            description "Egress MTU exceeded";
                                        }

                                        leaf multicast {
                                            type yang:counter64;
                                            description "Multicast dropped";
                                        }

                                    } // container general

                                    container receive-errors {
                                        description "Enter the receive-errors context";

                                        leaf l2-error {
                                            type yang:counter64;
                                            description "L2 parse error";
                                        }

                                        leaf l3-not-ip {
                                            type yang:counter64;
                                            description "L3 is not IPv4 or IPv6";
                                        }

                                        leaf ip-invalid-checksum {
                                            type yang:counter64;
                                            description "IPv4 invalid checksum";
                                        }

                                        leaf ip-malformed-header {
                                            type yang:counter64;
                                            description "IP malformed header";
                                        }

                                        leaf ip-malformed-packet {
                                            type yang:counter64;
                                            description "IP malformed packet";
                                        }

                                        leaf ip-zero-ttl {
                                            type yang:counter64;
                                            description "IP zero ttl";
                                        }

                                        leaf ip-opts-or-ext-headers {
                                            type yang:counter64;
                                            description "IPv4 options or IPv6 extension headers";
                                        }

                                        leaf ip-parse-error {
                                            type yang:counter64;
                                            description "IP parse error";
                                        }

                                        leaf ipv6-fragments-unsupported {
                                            type yang:counter64;
                                            description "IPv6 fragments unsupported";
                                        }

                                        leaf ipv6-extension-header-parse-error {
                                            type yang:counter64;
                                            description "IPv6 extension headers parse error";
                                        }

                                        leaf dslite-unsupported-next-header {
                                            type yang:counter64;
                                            description "Dual-stack-lite next header unsupported";
                                        }

                                        leaf l4-unsupported-protocol {
                                            type yang:counter64;
                                            description "Unsupported L4 protocol";
                                        }

                                        leaf tcp-udp-malformed-header {
                                            type yang:counter64;
                                            description "TCP/UDP malformed header";
                                        }

                                        leaf tcp-udp-invalid-checksum {
                                            type yang:counter64;
                                            description "TCP/UDP invalid checksum";
                                        }

                                        leaf icmp-embedded-ipv6-extension-header-parse-error {
                                            type yang:counter64;
                                            description "ICMP embedded IPv6 extension header parse error";
                                        }

                                        leaf other-parse-error {
                                            type yang:counter64;
                                            description "Other parse error";
                                        }

                                    } // container receive-errors

                                    container flow {
                                        description "Enter the flow context";

                                        leaf no-matching-flow {
                                            type yang:counter64;
                                            description "No matching flow";
                                        }

                                        leaf forwarding-blocked {
                                            type yang:counter64;
                                            description "Management core has blocked new flow creation or forwarding. Reasons include policies or port-blocks being released.";
                                        }

                                        leaf tcp-resetting {
                                            type yang:counter64;
                                            description "TCP flow is in reset state but not yet cleaned up";
                                        }

                                    } // container flow

                                    container flow-creation-failed {
                                        description "Enter the flow-creation-failed context";

                                        leaf no-resources {
                                            type yang:counter64;
                                            description "No resources";
                                        }

                                        leaf no-host-resources {
                                            type yang:counter64;
                                            description "Could not create host";
                                        }

                                        leaf no-ip-or-port-resources {
                                            type yang:counter64;
                                            description "Could not allocate ip or port-range";
                                        }

                                        leaf max-flows-exceeded {
                                            type yang:counter64;
                                            description "Max number of flows exceeded";
                                        }

                                        leaf ipv6-downstream-prohibited {
                                            type yang:counter64;
                                            description "IPv6 downstream traffic prohibited";
                                        }

                                        leaf address-dependent-filtering {
                                            type yang:counter64;
                                            description "Address dependent filtering";
                                        }

                                        leaf firewall-address-dependent-filtering {
                                            type yang:counter64;
                                            description "Firewall address dependent filtering";
                                        }

                                        leaf transient-no-policy {
                                            type yang:counter64;
                                            description "Policy could temporarily not be used";
                                        }

                                        leaf unmatched-policy {
                                            type yang:counter64;
                                            description "Matched policy not in use by subscriber";
                                        }

                                        leaf conflicting-policies {
                                            type yang:counter64;
                                            description "Conflicting policies";
                                        }

                                        leaf port-range-log-failed {
                                            type yang:counter64;
                                            description "Logging of port range allocation failed";
                                        }

                                        leaf flow-log-failed {
                                            type yang:counter64;
                                            description "Logging of flow creation failed";
                                        }

                                        leaf multiple-host-or-subscriber-ip {
                                            type yang:counter64;
                                            description "No multiple host or subscriber IPs allowed";
                                        }

                                        leaf destination-nat-destination-mismatch {
                                            type yang:counter64;
                                            description "Destination NAT destination IP mismatch";
                                        }

                                        leaf destination-nat-foreign-mismatch {
                                            type yang:counter64;
                                            description "Destination NAT foreign IP mismatch";
                                        }

                                        leaf ambiguous-flow-key {
                                            type yang:counter64;
                                            description "Ambiguous flow key";
                                        }

                                        leaf requested-port-not-in-host-range {
                                            type yang:counter64;
                                            description "Requested port not in host port range";
                                        }

                                        leaf destination-not-routable {
                                            type yang:counter64;
                                            description "Destination IP is not routable";
                                        }

                                        leaf dslite-unknown-aftr {
                                            type yang:counter64;
                                            description "Dual-stack-lite unknown AFTR address";
                                        }

                                        leaf pppoe-uplink-down {
                                            type yang:counter64;
                                            description "PPPoE uplink down";
                                        }

                                        leaf subscriber-id-unknown {
                                            type yang:counter64;
                                            description "Subscriber-id unknown";
                                        }

                                        leaf tcp-unexpected-rst {
                                            type yang:counter64;
                                            description "No flow creation on TCP RST";
                                        }

                                        leaf tcp-unexpected-fin {
                                            type yang:counter64;
                                            description "No flow creation on TCP FIN";
                                        }

                                        leaf tcp-unexpected-flags {
                                            type yang:counter64;
                                            description "No flow creation for invalid flags combinations";
                                        }

                                        leaf portrange-outside-ip-conflict {
                                            type yang:counter64;
                                            description "conflict between forced port range and outside IP of existing flow";
                                        }

                                        leaf requested-outside-port-conflict {
                                            type yang:counter64;
                                            description "conflict between requested outside port and outside port of existing flow";
                                        }

                                    } // container flow-creation-failed

                                    container icmp {
                                        description "Enter the icmp context";

                                        leaf unsupported-type-v4 {
                                            type yang:counter64;
                                            description "ICMP type unsupported";
                                        }

                                        leaf unsupported-type-v6 {
                                            type yang:counter64;
                                            description "ICMPv6 type unsupported";
                                        }

                                        leaf unsupported-type-for-translation {
                                            type yang:counter64;
                                            description "ICMP type unsupported for 4 to 6 translation";
                                        }

                                        leaf unsupported-length-for-translation {
                                            type yang:counter64;
                                            description "ICMP length error for 4 to 6 translation";
                                        }

                                        leaf unsupported-local {
                                            type yang:counter64;
                                            description "ICMP to l2aware-host gateway address unsupported";
                                        }

                                        leaf invalid-checksum {
                                            type yang:counter64;
                                            description "ICMP/ICMPv6 invalid checksum";
                                        }

                                        leaf embedded-invalid-checksum {
                                            type yang:counter64;
                                            description "ICMP invalid embedded IP checksum";
                                        }

                                        leaf unsupported-embedded-l3 {
                                            type yang:counter64;
                                            description "ICMP/ICMPv6 invalid embedded IP";
                                        }

                                        leaf unsupported-embedded-l4 {
                                            type yang:counter64;
                                            description "ICMP/ICMPv6 invalid embedded L4";
                                        }

                                        leaf too-short {
                                            type yang:counter64;
                                            description "ICMP/ICMPv6 too short";
                                        }

                                        leaf invalid-length {
                                            type yang:counter64;
                                            description "ICMP/ICMPv6 invalid length";
                                        }

                                        leaf fragmented {
                                            type yang:counter64;
                                            description "ICMP/ICMPv6 fragmentation";
                                        }

                                        leaf icmp6-packet-too-big {
                                            type yang:counter64;
                                            description "ICMP6 Packet-Too-Big with mtu < 1280";
                                        }

                                    } // container icmp

                                    container nat64 {
                                        description "Enter the nat64 context";

                                        leaf disabled {
                                            type yang:counter64;
                                            description "NAT64 disabled";
                                        }

                                        leaf invalid-source-address {
                                            type yang:counter64;
                                            description "NAT64 invalid source address";
                                        }

                                        leaf fragment-zero-checksum {
                                            type yang:counter64;
                                            description "NAT64 fragment has zero checksum";
                                        }

                                        leaf ipv4-zero-checksum {
                                            type yang:counter64;
                                            description "NAT64 IPv4 zero checksum";
                                        }

                                        leaf icmp-fragment-unsupported {
                                            type yang:counter64;
                                            description "NAT64 ICMP fragments unsupported";
                                        }

                                        leaf unknown-next-header {
                                            type yang:counter64;
                                            description "NAT64 unknown next header";
                                        }

                                        leaf embedded-ipv4-options {
                                            type yang:counter64;
                                            description "NAT64 ICMP embedded IPv4 options";
                                        }

                                    } // container nat64

                                    container fragments {
                                        description "Enter the fragments context";

                                        leaf too-many-fragmented-packets {
                                            type yang:counter64;
                                            description "Too many fragmented packets";
                                        }

                                        leaf too-many-fragment-buffers {
                                            type yang:counter64;
                                            description "Fragmentation buffers exhausted";
                                        }

                                        leaf too-many-fragment-holes {
                                            type yang:counter64;
                                            description "Too many fragment holes";
                                        }

                                        leaf too-many-fragments-per-packet {
                                            type yang:counter64;
                                            description "Too many fragments for IP packet";
                                        }

                                        leaf too-many-fragment-lists-for-flow {
                                            type yang:counter64;
                                            description "Too many fragment lists for flow";
                                        }

                                        leaf fragment-list-expired {
                                            type yang:counter64;
                                            description "Fragment list expired";
                                        }

                                        leaf fragment-list-cleanup-in-progress {
                                            type yang:counter64;
                                            description "Fragment list cleanup in progress";
                                        }

                                        leaf reassembly-failed {
                                            type yang:counter64;
                                            description "Reassembly failed";
                                        }

                                    } // container fragments

                                    container radius {
                                        description "Enter the radius context";

                                        leaf error {
                                            type yang:counter64;
                                            description "Error while processing RADIUS packet";
                                        }

                                        leaf no-send-resources {
                                            type yang:counter64;
                                            description "No resources to send RADIUS packet";
                                        }

                                    } // container radius

                                    container upnp {
                                        description "Enter the upnp context";

                                        leaf ssdp {
                                            type yang:counter64;
                                            description "SSDP dropped";
                                        }

                                        leaf control {
                                            type yang:counter64;
                                            description "UPnP control dropped";
                                        }

                                    } // container upnp

                                    container service-chaining {
                                        description "Enter the service-chaining context";

                                        leaf tx-error {
                                            type yang:counter64;
                                            description "Transmit error";
                                        }

                                        leaf rx-error {
                                            type yang:counter64;
                                            description "Receive error";
                                        }

                                        leaf rx-unsupported {
                                            type yang:counter64;
                                            description "Unhandled frames";
                                        }

                                        leaf filter-action-drop {
                                            type yang:counter64;
                                            description "Frames dropped by vas-filter";
                                        }

                                    } // container service-chaining

                                    container inter-chassis-sync {
                                        description "Enter the inter-chassis-sync context";

                                        leaf standby-drop {
                                            type yang:counter64;
                                            description "Standby drop";
                                        }

                                    } // container inter-chassis-sync

                                } // container dropped

                                container flow {
                                    description "Enter the flow context";

                                    leaf new-flow {
                                        type yang:counter64;
                                        description "New flow created";
                                    }

                                    leaf found-flow {
                                        type yang:counter64;
                                        description "Frame matched existing flow";
                                    }

                                    leaf tcp-closed {
                                        type yang:counter64;
                                        description "Flow terminated by TCP session close";
                                    }

                                    container timeouts {
                                        description "Enter the timeouts context";

                                        leaf tcp-expired {
                                            type yang:counter64;
                                            description "TCP flow expired";
                                        }

                                        leaf udp-expired {
                                            type yang:counter64;
                                            description "UDP flow expired";
                                        }

                                        leaf icmp-expired {
                                            type yang:counter64;
                                            description "ICMP/ICMPv6 flow expired";
                                        }

                                        leaf gre-expired {
                                            type yang:counter64;
                                            description "GRE flow expired";
                                        }

                                        leaf ipv6-any-l4-expired {
                                            type yang:counter64;
                                            description "Any IPv6 L4 flow expired";
                                        }

                                    } // container timeouts

                                } // container flow

                                container icmp {
                                    description "Enter the icmp context";

                                    leaf to-local {
                                        type yang:counter64;
                                        description "ICMP to local address";
                                    }

                                } // container icmp

                                container dslite {
                                    description "Enter the dslite context";

                                    leaf forward {
                                        type yang:counter64;
                                        description "IPv6 dual-stack-lite frame forwarded";
                                    }

                                } // container dslite

                                container fragmentation {
                                    description "Enter the fragmentation context";

                                    leaf ipv4 {
                                        type yang:counter64;
                                        description "IPv4 frame was fragmented";
                                    }

                                    leaf ipv6 {
                                        type yang:counter64;
                                        description "IPv6 frame was fragmented";
                                    }

                                } // container fragmentation

                                container reassembly {
                                    description "Enter the reassembly context";

                                    leaf packets {
                                        type yang:counter64;
                                        description "Reassembled frames";
                                    }

                                } // container reassembly

                                container flow-log {
                                    description "Enter the flow-log context";

                                    leaf logged-flow-create {
                                        type yang:counter64;
                                        description "Flow create logged";
                                    }

                                    leaf logged-flow-delete {
                                        type yang:counter64;
                                        description "Flow delete logged";
                                    }

                                    leaf tx-packet {
                                        type yang:counter64;
                                        description "Transmitted flow log frames";
                                    }

                                    leaf rate-limit-drop {
                                        type yang:counter64;
                                        description "Flow log frames dropped by rate limiting";
                                    }

                                } // container flow-log

                                container radius {
                                    description "Enter the radius context";

                                    leaf to-local {
                                        type yang:counter64;
                                        description "Frame handled by local radius client";
                                    }

                                } // container radius

                                container subscriber-id-cache {
                                    description "Enter the subscriber-id-cache context";

                                    leaf cached {
                                        type yang:counter64;
                                        description "Subscriber-id cached";
                                    }

                                    leaf delayed {
                                        type yang:counter64;
                                        description "Subscriber-id delayed";
                                    }

                                    leaf cache-timeout {
                                        type yang:counter64;
                                        description "Subscriber-id timeout";
                                    }

                                } // container subscriber-id-cache

                                container fragments {
                                    description "Enter the fragments context";

                                    leaf rx-large-scale {
                                        type yang:counter64;
                                        description "Fragments received on large-scale nat interface";
                                    }

                                    leaf rx-dual-stack-lite {
                                        type yang:counter64;
                                        description "Fragments received on dual-stack-lite interface";
                                    }

                                    leaf rx-dormant {
                                        type yang:counter64;
                                        description "Fragments received on dormant interface";
                                    }

                                    leaf rx-l2aware {
                                        type yang:counter64;
                                        description "Fragments received on l2aware interface";
                                    }

                                    leaf rx-outside {
                                        type yang:counter64;
                                        description "Fragments received on outside interface";
                                    }

                                    leaf tx-large-scale {
                                        type yang:counter64;
                                        description "Fragments transmitted on large-scale nat interface";
                                    }

                                    leaf tx-dual-stack-lite {
                                        type yang:counter64;
                                        description "Fragments transmitted on dual-stack-lite interface";
                                    }

                                    leaf tx-dormant {
                                        type yang:counter64;
                                        description "Fragments transmitted on dormant interface";
                                    }

                                    leaf tx-l2aware {
                                        type yang:counter64;
                                        description "Fragments transmitted on l2aware interface";
                                    }

                                    leaf tx-nat64 {
                                        type yang:counter64;
                                        description "Fragments transmitted on nat64 interface";
                                    }

                                    leaf tx-outside {
                                        type yang:counter64;
                                        description "Fragments transmitted on outside interface";
                                    }

                                } // container fragments

                                container upnp {
                                    description "Enter the upnp context";

                                    leaf ssdp-rx {
                                        type yang:counter64;
                                        description "SSDP frames received";
                                    }

                                    leaf ssdp-tx {
                                        type yang:counter64;
                                        description "SSDP frames transmitted";
                                    }

                                    leaf control-rx {
                                        type yang:counter64;
                                        description "UPnP control frames received";
                                    }

                                    leaf control-tx {
                                        type yang:counter64;
                                        description "UPnP control frames transmitted";
                                    }

                                    leaf rate-limited-request {
                                        type yang:counter64;
                                        description "UPnP query rate limited";
                                    }

                                    leaf pinhole-without-default-policy {
                                        type yang:counter64;
                                        description "Attempt to create pinhole without default policy";
                                    }

                                    leaf pinhole-without-source-nat {
                                        type yang:counter64;
                                        description "Attempt to create pinhole with source-nat disabled";
                                    }

                                } // container upnp

                                container service-chaining {
                                    description "Enter the service-chaining context";

                                    leaf rx {
                                        type yang:counter64;
                                        description "Service-chaining frames received";
                                    }

                                    leaf tx {
                                        type yang:counter64;
                                        description "Service-chaining frames transmitted";
                                    }

                                } // container service-chaining

                            } // container nat

                        } // container statistics

                    } // container nat

                    container performance {
                        description "Enter the performance context";

                        container last-hour {
                            description "Enter the last-hour context";

                            list minutes-ago {
                                key "index";
                                description "Enter the minutes-ago list instance";

                                leaf index {
                                    type uint32;
                                    description "Numerical index value generated by the system.";
                                }

                                leaf timestamp {
                                    type yang:date-and-time;
                                    description "Time at which the measurement was taken";
                                }

                                leaf waiting {
                                    type decimal64 {
                                        range "0..100";
                                        fraction-digits 2;
                                    }
                                    units "percent";
                                    description "Relative time spent waiting in the measured period.";
                                }

                                leaf idling {
                                    type decimal64 {
                                        range "0..100";
                                        fraction-digits 2;
                                    }
                                    units "percent";
                                    description "Relative time spent idling in the measured period.";
                                }

                                leaf working {
                                    type decimal64 {
                                        range "0..100";
                                        fraction-digits 2;
                                    }
                                    units "percent";
                                    description "Relative time spent working in the measured period.";
                                }

                                leaf jobs {
                                    type uint32;
                                    description "The number of jobs performed in the measured period.";
                                }

                                leaf throughput {
                                    type uint64;
                                    units "bytes";
                                    description "The amount of data processed in the measured period.";
                                }

                            } // list minutes-ago

                        } // container last-hour

                        container last-day {
                            description "Enter the last-day context";

                            list hours-ago {
                                key "index";
                                description "Enter the hours-ago list instance";

                                leaf index {
                                    type uint32;
                                    description "Numerical index value generated by the system.";
                                }

                                leaf timestamp {
                                    type yang:date-and-time;
                                    description "Time at which the measurement was taken";
                                }

                                leaf waiting {
                                    type decimal64 {
                                        range "0..100";
                                        fraction-digits 2;
                                    }
                                    units "percent";
                                    description "Relative time spent waiting in the measured period.";
                                }

                                leaf idling {
                                    type decimal64 {
                                        range "0..100";
                                        fraction-digits 2;
                                    }
                                    units "percent";
                                    description "Relative time spent idling in the measured period.";
                                }

                                leaf working {
                                    type decimal64 {
                                        range "0..100";
                                        fraction-digits 2;
                                    }
                                    units "percent";
                                    description "Relative time spent working in the measured period.";
                                }

                                leaf jobs {
                                    type uint32;
                                    description "The number of jobs performed in the measured period.";
                                }

                                leaf throughput {
                                    type uint64;
                                    units "bytes";
                                    description "The amount of data processed in the measured period.";
                                }

                            } // list hours-ago

                        } // container last-day

                        container last-month {
                            description "Enter the last-month context";

                            list days-ago {
                                key "index";
                                description "Enter the days-ago list instance";

                                leaf index {
                                    type uint32;
                                    description "Numerical index value generated by the system.";
                                }

                                leaf timestamp {
                                    type yang:date-and-time;
                                    description "Time at which the measurement was taken";
                                }

                                leaf waiting {
                                    type decimal64 {
                                        range "0..100";
                                        fraction-digits 2;
                                    }
                                    units "percent";
                                    description "Relative time spent waiting in the measured period.";
                                }

                                leaf idling {
                                    type decimal64 {
                                        range "0..100";
                                        fraction-digits 2;
                                    }
                                    units "percent";
                                    description "Relative time spent idling in the measured period.";
                                }

                                leaf working {
                                    type decimal64 {
                                        range "0..100";
                                        fraction-digits 2;
                                    }
                                    units "percent";
                                    description "Relative time spent working in the measured period.";
                                }

                                leaf jobs {
                                    type uint32;
                                    description "The number of jobs performed in the measured period.";
                                }

                                leaf throughput {
                                    type uint64;
                                    units "bytes";
                                    description "The amount of data processed in the measured period.";
                                }

                            } // list days-ago

                        } // container last-month

                    } // container performance

                } // list mda

                list esa {
                    key "esa-id vm";
                    description "Enter the esa list instance";

                    leaf esa-id {
                        type leafref {
                            path "../../../../esa/esa-id";
                        }
                        description "ESA ID";
                    }

                    leaf vm {
                        type leafref {
                            path "../../../../esa[esa-id=current()/../esa-id]/vm/vm-id";
                        }
                        description "VM ID";
                    }

                    leaf oper-state {
                        type types-isa:nat-member-operational-state;
                        description "Operational status of a WLAN-GW group ESA-VM";
                    }

                    container nat {
                        description "Enter the nat context";

                        leaf peak-values-last-reset {
                            type yang:date-and-time;
                            description "Moment when the peak values were last reset";
                        }

                        container resources {
                            description "Enter the resources context";

                            container flows {
                                description "Enter the flows context";

                                leaf value {
                                    type yang:gauge64;
                                    description "Actual consumed value";
                                }

                                leaf max {
                                    type uint64;
                                    description "The max value this resource can have, depending on the configuration";
                                }

                                leaf peak {
                                    type yang:gauge64;
                                    description "The peak value for the resource";
                                }

                                leaf peak-timestamp {
                                    type types-sros:date-time;
                                    description "The timestamp when the peak value was observed";
                                }

                            } // container flows

                            container policies {
                                description "Enter the policies context";

                                leaf value {
                                    type yang:gauge64;
                                    description "Actual consumed value";
                                }

                                leaf max {
                                    type uint64;
                                    description "The max value this resource can have, depending on the configuration";
                                }

                                leaf peak {
                                    type yang:gauge64;
                                    description "The peak value for the resource";
                                }

                                leaf peak-timestamp {
                                    type types-sros:date-time;
                                    description "The timestamp when the peak value was observed";
                                }

                            } // container policies

                            container subscriber-cache-entries {
                                description "Enter the subscriber-cache-entries context";

                                leaf value {
                                    type yang:gauge64;
                                    description "Actual consumed value";
                                }

                                leaf max {
                                    type uint64;
                                    description "The max value this resource can have, depending on the configuration";
                                }

                                leaf peak {
                                    type yang:gauge64;
                                    description "The peak value for the resource";
                                }

                                leaf peak-timestamp {
                                    type types-sros:date-time;
                                    description "The timestamp when the peak value was observed";
                                }

                            } // container subscriber-cache-entries

                            container delayed-icmps {
                                description "Enter the delayed-icmps context";

                                leaf value {
                                    type yang:gauge64;
                                    description "Actual consumed value";
                                }

                                leaf max {
                                    type uint64;
                                    description "The max value this resource can have, depending on the configuration";
                                }

                                leaf peak {
                                    type yang:gauge64;
                                    description "The peak value for the resource";
                                }

                                leaf peak-timestamp {
                                    type types-sros:date-time;
                                    description "The timestamp when the peak value was observed";
                                }

                            } // container delayed-icmps

                            container alg-session {
                                description "Enter the alg-session context";

                                leaf value {
                                    type yang:gauge64;
                                    description "Actual consumed value";
                                }

                                leaf max {
                                    type uint64;
                                    description "The max value this resource can have, depending on the configuration";
                                }

                                leaf peak {
                                    type yang:gauge64;
                                    description "The peak value for the resource";
                                }

                                leaf peak-timestamp {
                                    type types-sros:date-time;
                                    description "The timestamp when the peak value was observed";
                                }

                            } // container alg-session

                            container fragment-lists {
                                description "Enter the fragment-lists context";

                                container upstream {
                                    description "Enter the upstream context";

                                    leaf value {
                                        type yang:gauge64;
                                        description "Actual consumed value";
                                    }

                                    leaf max {
                                        type uint64;
                                        description "The max value this resource can have, depending on the configuration";
                                    }

                                    leaf peak {
                                        type yang:gauge64;
                                        description "The peak value for the resource";
                                    }

                                    leaf peak-timestamp {
                                        type types-sros:date-time;
                                        description "The timestamp when the peak value was observed";
                                    }

                                } // container upstream

                                container downstream {
                                    description "Enter the downstream context";

                                    leaf value {
                                        type yang:gauge64;
                                        description "Actual consumed value";
                                    }

                                    leaf max {
                                        type uint64;
                                        description "The max value this resource can have, depending on the configuration";
                                    }

                                    leaf peak {
                                        type yang:gauge64;
                                        description "The peak value for the resource";
                                    }

                                    leaf peak-timestamp {
                                        type types-sros:date-time;
                                        description "The timestamp when the peak value was observed";
                                    }

                                } // container downstream

                            } // container fragment-lists

                            container fragment-holes {
                                description "Enter the fragment-holes context";

                                container upstream {
                                    description "Enter the upstream context";

                                    leaf value {
                                        type yang:gauge64;
                                        description "Actual consumed value";
                                    }

                                    leaf max {
                                        type uint64;
                                        description "The max value this resource can have, depending on the configuration";
                                    }

                                    leaf peak {
                                        type yang:gauge64;
                                        description "The peak value for the resource";
                                    }

                                    leaf peak-timestamp {
                                        type types-sros:date-time;
                                        description "The timestamp when the peak value was observed";
                                    }

                                } // container upstream

                                container downstream {
                                    description "Enter the downstream context";

                                    leaf value {
                                        type yang:gauge64;
                                        description "Actual consumed value";
                                    }

                                    leaf max {
                                        type uint64;
                                        description "The max value this resource can have, depending on the configuration";
                                    }

                                    leaf peak {
                                        type yang:gauge64;
                                        description "The peak value for the resource";
                                    }

                                    leaf peak-timestamp {
                                        type types-sros:date-time;
                                        description "The timestamp when the peak value was observed";
                                    }

                                } // container downstream

                            } // container fragment-holes

                            container fragment-bufs {
                                description "Enter the fragment-bufs context";

                                container upstream {
                                    description "Enter the upstream context";

                                    leaf value {
                                        type yang:gauge64;
                                        description "Actual consumed value";
                                    }

                                    leaf max {
                                        type uint64;
                                        description "The max value this resource can have, depending on the configuration";
                                    }

                                    leaf peak {
                                        type yang:gauge64;
                                        description "The peak value for the resource";
                                    }

                                    leaf peak-timestamp {
                                        type types-sros:date-time;
                                        description "The timestamp when the peak value was observed";
                                    }

                                } // container upstream

                                container downstream {
                                    description "Enter the downstream context";

                                    leaf value {
                                        type yang:gauge64;
                                        description "Actual consumed value";
                                    }

                                    leaf max {
                                        type uint64;
                                        description "The max value this resource can have, depending on the configuration";
                                    }

                                    leaf peak {
                                        type yang:gauge64;
                                        description "The peak value for the resource";
                                    }

                                    leaf peak-timestamp {
                                        type types-sros:date-time;
                                        description "The timestamp when the peak value was observed";
                                    }

                                } // container downstream

                            } // container fragment-bufs

                            container dormant-subscribers {
                                description "Enter the dormant-subscribers context";

                                leaf value {
                                    type yang:gauge64;
                                    description "Actual consumed value";
                                }

                                leaf max {
                                    type uint64;
                                    description "The max value this resource can have, depending on the configuration";
                                }

                                leaf peak {
                                    type yang:gauge64;
                                    description "The peak value for the resource";
                                }

                                leaf peak-timestamp {
                                    type types-sros:date-time;
                                    description "The timestamp when the peak value was observed";
                                }

                            } // container dormant-subscribers

                            container upnp {
                                description "Enter the upnp context";

                                container mappings {
                                    description "Enter the mappings context";

                                    leaf value {
                                        type yang:gauge64;
                                        description "Actual consumed value";
                                    }

                                    leaf max {
                                        type uint64;
                                        description "The max value this resource can have, depending on the configuration";
                                    }

                                    leaf peak {
                                        type yang:gauge64;
                                        description "The peak value for the resource";
                                    }

                                    leaf peak-timestamp {
                                        type types-sros:date-time;
                                        description "The timestamp when the peak value was observed";
                                    }

                                } // container mappings

                                container sessions {
                                    description "Enter the sessions context";

                                    leaf value {
                                        type yang:gauge64;
                                        description "Actual consumed value";
                                    }

                                    leaf max {
                                        type uint64;
                                        description "The max value this resource can have, depending on the configuration";
                                    }

                                    leaf peak {
                                        type yang:gauge64;
                                        description "The peak value for the resource";
                                    }

                                    leaf peak-timestamp {
                                        type types-sros:date-time;
                                        description "The timestamp when the peak value was observed";
                                    }

                                } // container sessions

                            } // container upnp

                            container pppoe-sessions {
                                description "Enter the pppoe-sessions context";

                                leaf value {
                                    type yang:gauge64;
                                    description "Actual consumed value";
                                }

                                leaf max {
                                    type uint64;
                                    description "The max value this resource can have, depending on the configuration";
                                }

                                leaf peak {
                                    type yang:gauge64;
                                    description "The peak value for the resource";
                                }

                                leaf peak-timestamp {
                                    type types-sros:date-time;
                                    description "The timestamp when the peak value was observed";
                                }

                            } // container pppoe-sessions

                        } // container resources

                        container statistics {
                            description "Enter the statistics context";

                            container ip-forwarding {
                                description "Enter the ip-forwarding context";

                                leaf fragments {
                                    type yang:counter64;
                                    description "Fragments handled";
                                }

                                leaf reassembled-packets {
                                    type yang:counter64;
                                    description "Frames reassembled";
                                }

                                leaf forwarded-packets {
                                    type yang:counter64;
                                    description "Frames forwarded";
                                }

                                container receive-errors {
                                    description "Enter the receive-errors context";

                                    leaf l2-error {
                                        type yang:counter64;
                                        description "L2 parse error";
                                    }

                                    leaf l3-not-ip {
                                        type yang:counter64;
                                        description "L3 is not IPv4 or IPv6";
                                    }

                                    leaf ip-invalid-checksum {
                                        type yang:counter64;
                                        description "IPv4 invalid checksum";
                                    }

                                    leaf ip-malformed-header {
                                        type yang:counter64;
                                        description "IP malformed header";
                                    }

                                    leaf ip-malformed-packet {
                                        type yang:counter64;
                                        description "IP malformed packet";
                                    }

                                    leaf ip-zero-ttl {
                                        type yang:counter64;
                                        description "IP zero ttl";
                                    }

                                    leaf ip-opts-or-ext-headers {
                                        type yang:counter64;
                                        description "IPv4 options or IPv6 extension headers";
                                    }

                                    leaf ip-fragment-unsupported {
                                        type yang:counter64;
                                        description "IP fragment unsupported";
                                    }

                                    leaf ip-error {
                                        type yang:counter64;
                                        description "IP parse error";
                                    }

                                    leaf tcp-udp-malformed-header {
                                        type yang:counter64;
                                        description "TCP/UDP malformed header";
                                    }

                                    leaf tcp-udp-invalid-checksum {
                                        type yang:counter64;
                                        description "TCP/UDP invalid checksum";
                                    }

                                    leaf other {
                                        type yang:counter64;
                                        description "Other parse error";
                                    }

                                } // container receive-errors

                                container reassembly-errors {
                                    description "Enter the reassembly-errors context";

                                    leaf too-many-fragmented-packets {
                                        type yang:counter64;
                                        description "Too many fragmented packets";
                                    }

                                    leaf too-many-fragment-buffers {
                                        type yang:counter64;
                                        description "Too many fragment buffers";
                                    }

                                    leaf too-many-fragment-holes {
                                        type yang:counter64;
                                        description "Too many fragment holes";
                                    }

                                    leaf fragment-filtered {
                                        type yang:counter64;
                                        description "Fragments filtered";
                                    }

                                    leaf fragment-not-supported {
                                        type yang:counter64;
                                        description "Fragment not supported";
                                    }

                                    leaf fragment-list-expired {
                                        type yang:counter64;
                                        description "Fragment list expired";
                                    }

                                    leaf fragment-list-cleanup-in-progress {
                                        type yang:counter64;
                                        description "Fragment list cleanup in progress";
                                    }

                                    leaf reassembly-failed {
                                        type yang:counter64;
                                        description "Reassembly failed";
                                    }

                                } // container reassembly-errors

                            } // container ip-forwarding

                            container pppoe-client {
                                description "Enter the pppoe-client context";

                                leaf rx-error-l2 {
                                    type yang:counter64;
                                    description "Number of packets received with layer 2 parse errors";
                                }

                                leaf rx-error-invalid-headers {
                                    type yang:counter64;
                                    description "Number of packets received with invalid PPPoE headers";
                                }

                                leaf rx-error-invalid-magic {
                                    type yang:counter64;
                                    description "Number of LCP echo-request or echo-reply packets received with an invalid magic number";
                                }

                                leaf rx-error-no-session {
                                    type yang:counter64;
                                    description "Number of LCP echo or data packets received without an associated session";
                                }

                                leaf rx-discovery {
                                    type yang:counter64;
                                    description "Number of PPPoE discovery packets received";
                                }

                                leaf rx-ppp-control {
                                    type yang:counter64;
                                    description "Number of PPP control packets received";
                                }

                                leaf rx-lcp-echo-request {
                                    type yang:counter64;
                                    description "Number of LCP echo-request packets received";
                                }

                                leaf rx-lcp-echo-reply {
                                    type yang:counter64;
                                    description "Number of LCP echo-reply packets received";
                                }

                                leaf tx-lcp-echo-request {
                                    type yang:counter64;
                                    description "Number of LCP echo-request packets transmitted";
                                }

                                leaf tx-lcp-echo-reply {
                                    type yang:counter64;
                                    description "Number of LCP echo-reply packets transmitted";
                                }

                            } // container pppoe-client

                            container nat {
                                description "Enter the nat context";

                                container dropped {
                                    description "Enter the dropped context";

                                    container general {
                                        description "Enter the general context";

                                        leaf arp {
                                            type yang:counter64;
                                            description "ARP frames are ignored";
                                        }

                                        leaf checksum-calculation-error {
                                            type yang:counter64;
                                            description "Error while calculating L4 checksum before transmitting";
                                        }

                                        leaf send-error {
                                            type yang:counter64;
                                            description "Packet send error";
                                        }

                                        leaf no-copy-buffer {
                                            type yang:counter64;
                                            description "No buffer to copy frame";
                                        }

                                        leaf mtu-exceeded {
                                            type yang:counter64;
                                            description "Egress MTU exceeded";
                                        }

                                        leaf multicast {
                                            type yang:counter64;
                                            description "Multicast dropped";
                                        }

                                    } // container general

                                    container receive-errors {
                                        description "Enter the receive-errors context";

                                        leaf l2-error {
                                            type yang:counter64;
                                            description "L2 parse error";
                                        }

                                        leaf l3-not-ip {
                                            type yang:counter64;
                                            description "L3 is not IPv4 or IPv6";
                                        }

                                        leaf ip-invalid-checksum {
                                            type yang:counter64;
                                            description "IPv4 invalid checksum";
                                        }

                                        leaf ip-malformed-header {
                                            type yang:counter64;
                                            description "IP malformed header";
                                        }

                                        leaf ip-malformed-packet {
                                            type yang:counter64;
                                            description "IP malformed packet";
                                        }

                                        leaf ip-zero-ttl {
                                            type yang:counter64;
                                            description "IP zero ttl";
                                        }

                                        leaf ip-opts-or-ext-headers {
                                            type yang:counter64;
                                            description "IPv4 options or IPv6 extension headers";
                                        }

                                        leaf ip-parse-error {
                                            type yang:counter64;
                                            description "IP parse error";
                                        }

                                        leaf ipv6-fragments-unsupported {
                                            type yang:counter64;
                                            description "IPv6 fragments unsupported";
                                        }

                                        leaf ipv6-extension-header-parse-error {
                                            type yang:counter64;
                                            description "IPv6 extension headers parse error";
                                        }

                                        leaf dslite-unsupported-next-header {
                                            type yang:counter64;
                                            description "Dual-stack-lite next header unsupported";
                                        }

                                        leaf l4-unsupported-protocol {
                                            type yang:counter64;
                                            description "Unsupported L4 protocol";
                                        }

                                        leaf tcp-udp-malformed-header {
                                            type yang:counter64;
                                            description "TCP/UDP malformed header";
                                        }

                                        leaf tcp-udp-invalid-checksum {
                                            type yang:counter64;
                                            description "TCP/UDP invalid checksum";
                                        }

                                        leaf icmp-embedded-ipv6-extension-header-parse-error {
                                            type yang:counter64;
                                            description "ICMP embedded IPv6 extension header parse error";
                                        }

                                        leaf other-parse-error {
                                            type yang:counter64;
                                            description "Other parse error";
                                        }

                                    } // container receive-errors

                                    container flow {
                                        description "Enter the flow context";

                                        leaf no-matching-flow {
                                            type yang:counter64;
                                            description "No matching flow";
                                        }

                                        leaf forwarding-blocked {
                                            type yang:counter64;
                                            description "Management core has blocked new flow creation or forwarding. Reasons include policies or port-blocks being released.";
                                        }

                                        leaf tcp-resetting {
                                            type yang:counter64;
                                            description "TCP flow is in reset state but not yet cleaned up";
                                        }

                                    } // container flow

                                    container flow-creation-failed {
                                        description "Enter the flow-creation-failed context";

                                        leaf no-resources {
                                            type yang:counter64;
                                            description "No resources";
                                        }

                                        leaf no-host-resources {
                                            type yang:counter64;
                                            description "Could not create host";
                                        }

                                        leaf no-ip-or-port-resources {
                                            type yang:counter64;
                                            description "Could not allocate ip or port-range";
                                        }

                                        leaf max-flows-exceeded {
                                            type yang:counter64;
                                            description "Max number of flows exceeded";
                                        }

                                        leaf ipv6-downstream-prohibited {
                                            type yang:counter64;
                                            description "IPv6 downstream traffic prohibited";
                                        }

                                        leaf address-dependent-filtering {
                                            type yang:counter64;
                                            description "Address dependent filtering";
                                        }

                                        leaf firewall-address-dependent-filtering {
                                            type yang:counter64;
                                            description "Firewall address dependent filtering";
                                        }

                                        leaf transient-no-policy {
                                            type yang:counter64;
                                            description "Policy could temporarily not be used";
                                        }

                                        leaf unmatched-policy {
                                            type yang:counter64;
                                            description "Matched policy not in use by subscriber";
                                        }

                                        leaf conflicting-policies {
                                            type yang:counter64;
                                            description "Conflicting policies";
                                        }

                                        leaf port-range-log-failed {
                                            type yang:counter64;
                                            description "Logging of port range allocation failed";
                                        }

                                        leaf flow-log-failed {
                                            type yang:counter64;
                                            description "Logging of flow creation failed";
                                        }

                                        leaf multiple-host-or-subscriber-ip {
                                            type yang:counter64;
                                            description "No multiple host or subscriber IPs allowed";
                                        }

                                        leaf destination-nat-destination-mismatch {
                                            type yang:counter64;
                                            description "Destination NAT destination IP mismatch";
                                        }

                                        leaf destination-nat-foreign-mismatch {
                                            type yang:counter64;
                                            description "Destination NAT foreign IP mismatch";
                                        }

                                        leaf ambiguous-flow-key {
                                            type yang:counter64;
                                            description "Ambiguous flow key";
                                        }

                                        leaf requested-port-not-in-host-range {
                                            type yang:counter64;
                                            description "Requested port not in host port range";
                                        }

                                        leaf destination-not-routable {
                                            type yang:counter64;
                                            description "Destination IP is not routable";
                                        }

                                        leaf dslite-unknown-aftr {
                                            type yang:counter64;
                                            description "Dual-stack-lite unknown AFTR address";
                                        }

                                        leaf pppoe-uplink-down {
                                            type yang:counter64;
                                            description "PPPoE uplink down";
                                        }

                                        leaf subscriber-id-unknown {
                                            type yang:counter64;
                                            description "Subscriber-id unknown";
                                        }

                                        leaf tcp-unexpected-rst {
                                            type yang:counter64;
                                            description "No flow creation on TCP RST";
                                        }

                                        leaf tcp-unexpected-fin {
                                            type yang:counter64;
                                            description "No flow creation on TCP FIN";
                                        }

                                        leaf tcp-unexpected-flags {
                                            type yang:counter64;
                                            description "No flow creation for invalid flags combinations";
                                        }

                                        leaf portrange-outside-ip-conflict {
                                            type yang:counter64;
                                            description "conflict between forced port range and outside IP of existing flow";
                                        }

                                        leaf requested-outside-port-conflict {
                                            type yang:counter64;
                                            description "conflict between requested outside port and outside port of existing flow";
                                        }

                                    } // container flow-creation-failed

                                    container icmp {
                                        description "Enter the icmp context";

                                        leaf unsupported-type-v4 {
                                            type yang:counter64;
                                            description "ICMP type unsupported";
                                        }

                                        leaf unsupported-type-v6 {
                                            type yang:counter64;
                                            description "ICMPv6 type unsupported";
                                        }

                                        leaf unsupported-type-for-translation {
                                            type yang:counter64;
                                            description "ICMP type unsupported for 4 to 6 translation";
                                        }

                                        leaf unsupported-length-for-translation {
                                            type yang:counter64;
                                            description "ICMP length error for 4 to 6 translation";
                                        }

                                        leaf unsupported-local {
                                            type yang:counter64;
                                            description "ICMP to l2aware-host gateway address unsupported";
                                        }

                                        leaf invalid-checksum {
                                            type yang:counter64;
                                            description "ICMP/ICMPv6 invalid checksum";
                                        }

                                        leaf embedded-invalid-checksum {
                                            type yang:counter64;
                                            description "ICMP invalid embedded IP checksum";
                                        }

                                        leaf unsupported-embedded-l3 {
                                            type yang:counter64;
                                            description "ICMP/ICMPv6 invalid embedded IP";
                                        }

                                        leaf unsupported-embedded-l4 {
                                            type yang:counter64;
                                            description "ICMP/ICMPv6 invalid embedded L4";
                                        }

                                        leaf too-short {
                                            type yang:counter64;
                                            description "ICMP/ICMPv6 too short";
                                        }

                                        leaf invalid-length {
                                            type yang:counter64;
                                            description "ICMP/ICMPv6 invalid length";
                                        }

                                        leaf fragmented {
                                            type yang:counter64;
                                            description "ICMP/ICMPv6 fragmentation";
                                        }

                                        leaf icmp6-packet-too-big {
                                            type yang:counter64;
                                            description "ICMP6 Packet-Too-Big with mtu < 1280";
                                        }

                                    } // container icmp

                                    container nat64 {
                                        description "Enter the nat64 context";

                                        leaf disabled {
                                            type yang:counter64;
                                            description "NAT64 disabled";
                                        }

                                        leaf invalid-source-address {
                                            type yang:counter64;
                                            description "NAT64 invalid source address";
                                        }

                                        leaf fragment-zero-checksum {
                                            type yang:counter64;
                                            description "NAT64 fragment has zero checksum";
                                        }

                                        leaf ipv4-zero-checksum {
                                            type yang:counter64;
                                            description "NAT64 IPv4 zero checksum";
                                        }

                                        leaf icmp-fragment-unsupported {
                                            type yang:counter64;
                                            description "NAT64 ICMP fragments unsupported";
                                        }

                                        leaf unknown-next-header {
                                            type yang:counter64;
                                            description "NAT64 unknown next header";
                                        }

                                        leaf embedded-ipv4-options {
                                            type yang:counter64;
                                            description "NAT64 ICMP embedded IPv4 options";
                                        }

                                    } // container nat64

                                    container fragments {
                                        description "Enter the fragments context";

                                        leaf too-many-fragmented-packets {
                                            type yang:counter64;
                                            description "Too many fragmented packets";
                                        }

                                        leaf too-many-fragment-buffers {
                                            type yang:counter64;
                                            description "Fragmentation buffers exhausted";
                                        }

                                        leaf too-many-fragment-holes {
                                            type yang:counter64;
                                            description "Too many fragment holes";
                                        }

                                        leaf too-many-fragments-per-packet {
                                            type yang:counter64;
                                            description "Too many fragments for IP packet";
                                        }

                                        leaf too-many-fragment-lists-for-flow {
                                            type yang:counter64;
                                            description "Too many fragment lists for flow";
                                        }

                                        leaf fragment-list-expired {
                                            type yang:counter64;
                                            description "Fragment list expired";
                                        }

                                        leaf fragment-list-cleanup-in-progress {
                                            type yang:counter64;
                                            description "Fragment list cleanup in progress";
                                        }

                                        leaf reassembly-failed {
                                            type yang:counter64;
                                            description "Reassembly failed";
                                        }

                                    } // container fragments

                                    container radius {
                                        description "Enter the radius context";

                                        leaf error {
                                            type yang:counter64;
                                            description "Error while processing RADIUS packet";
                                        }

                                        leaf no-send-resources {
                                            type yang:counter64;
                                            description "No resources to send RADIUS packet";
                                        }

                                    } // container radius

                                    container upnp {
                                        description "Enter the upnp context";

                                        leaf ssdp {
                                            type yang:counter64;
                                            description "SSDP dropped";
                                        }

                                        leaf control {
                                            type yang:counter64;
                                            description "UPnP control dropped";
                                        }

                                    } // container upnp

                                    container service-chaining {
                                        description "Enter the service-chaining context";

                                        leaf tx-error {
                                            type yang:counter64;
                                            description "Transmit error";
                                        }

                                        leaf rx-error {
                                            type yang:counter64;
                                            description "Receive error";
                                        }

                                        leaf rx-unsupported {
                                            type yang:counter64;
                                            description "Unhandled frames";
                                        }

                                        leaf filter-action-drop {
                                            type yang:counter64;
                                            description "Frames dropped by vas-filter";
                                        }

                                    } // container service-chaining

                                    container inter-chassis-sync {
                                        description "Enter the inter-chassis-sync context";

                                        leaf standby-drop {
                                            type yang:counter64;
                                            description "Standby drop";
                                        }

                                    } // container inter-chassis-sync

                                } // container dropped

                                container flow {
                                    description "Enter the flow context";

                                    leaf new-flow {
                                        type yang:counter64;
                                        description "New flow created";
                                    }

                                    leaf found-flow {
                                        type yang:counter64;
                                        description "Frame matched existing flow";
                                    }

                                    leaf tcp-closed {
                                        type yang:counter64;
                                        description "Flow terminated by TCP session close";
                                    }

                                    container timeouts {
                                        description "Enter the timeouts context";

                                        leaf tcp-expired {
                                            type yang:counter64;
                                            description "TCP flow expired";
                                        }

                                        leaf udp-expired {
                                            type yang:counter64;
                                            description "UDP flow expired";
                                        }

                                        leaf icmp-expired {
                                            type yang:counter64;
                                            description "ICMP/ICMPv6 flow expired";
                                        }

                                        leaf gre-expired {
                                            type yang:counter64;
                                            description "GRE flow expired";
                                        }

                                        leaf ipv6-any-l4-expired {
                                            type yang:counter64;
                                            description "Any IPv6 L4 flow expired";
                                        }

                                    } // container timeouts

                                } // container flow

                                container icmp {
                                    description "Enter the icmp context";

                                    leaf to-local {
                                        type yang:counter64;
                                        description "ICMP to local address";
                                    }

                                } // container icmp

                                container dslite {
                                    description "Enter the dslite context";

                                    leaf forward {
                                        type yang:counter64;
                                        description "IPv6 dual-stack-lite frame forwarded";
                                    }

                                } // container dslite

                                container fragmentation {
                                    description "Enter the fragmentation context";

                                    leaf ipv4 {
                                        type yang:counter64;
                                        description "IPv4 frame was fragmented";
                                    }

                                    leaf ipv6 {
                                        type yang:counter64;
                                        description "IPv6 frame was fragmented";
                                    }

                                } // container fragmentation

                                container reassembly {
                                    description "Enter the reassembly context";

                                    leaf packets {
                                        type yang:counter64;
                                        description "Reassembled frames";
                                    }

                                } // container reassembly

                                container flow-log {
                                    description "Enter the flow-log context";

                                    leaf logged-flow-create {
                                        type yang:counter64;
                                        description "Flow create logged";
                                    }

                                    leaf logged-flow-delete {
                                        type yang:counter64;
                                        description "Flow delete logged";
                                    }

                                    leaf tx-packet {
                                        type yang:counter64;
                                        description "Transmitted flow log frames";
                                    }

                                    leaf rate-limit-drop {
                                        type yang:counter64;
                                        description "Flow log frames dropped by rate limiting";
                                    }

                                } // container flow-log

                                container radius {
                                    description "Enter the radius context";

                                    leaf to-local {
                                        type yang:counter64;
                                        description "Frame handled by local radius client";
                                    }

                                } // container radius

                                container subscriber-id-cache {
                                    description "Enter the subscriber-id-cache context";

                                    leaf cached {
                                        type yang:counter64;
                                        description "Subscriber-id cached";
                                    }

                                    leaf delayed {
                                        type yang:counter64;
                                        description "Subscriber-id delayed";
                                    }

                                    leaf cache-timeout {
                                        type yang:counter64;
                                        description "Subscriber-id timeout";
                                    }

                                } // container subscriber-id-cache

                                container fragments {
                                    description "Enter the fragments context";

                                    leaf rx-large-scale {
                                        type yang:counter64;
                                        description "Fragments received on large-scale nat interface";
                                    }

                                    leaf rx-dual-stack-lite {
                                        type yang:counter64;
                                        description "Fragments received on dual-stack-lite interface";
                                    }

                                    leaf rx-dormant {
                                        type yang:counter64;
                                        description "Fragments received on dormant interface";
                                    }

                                    leaf rx-l2aware {
                                        type yang:counter64;
                                        description "Fragments received on l2aware interface";
                                    }

                                    leaf rx-outside {
                                        type yang:counter64;
                                        description "Fragments received on outside interface";
                                    }

                                    leaf tx-large-scale {
                                        type yang:counter64;
                                        description "Fragments transmitted on large-scale nat interface";
                                    }

                                    leaf tx-dual-stack-lite {
                                        type yang:counter64;
                                        description "Fragments transmitted on dual-stack-lite interface";
                                    }

                                    leaf tx-dormant {
                                        type yang:counter64;
                                        description "Fragments transmitted on dormant interface";
                                    }

                                    leaf tx-l2aware {
                                        type yang:counter64;
                                        description "Fragments transmitted on l2aware interface";
                                    }

                                    leaf tx-nat64 {
                                        type yang:counter64;
                                        description "Fragments transmitted on nat64 interface";
                                    }

                                    leaf tx-outside {
                                        type yang:counter64;
                                        description "Fragments transmitted on outside interface";
                                    }

                                } // container fragments

                                container upnp {
                                    description "Enter the upnp context";

                                    leaf ssdp-rx {
                                        type yang:counter64;
                                        description "SSDP frames received";
                                    }

                                    leaf ssdp-tx {
                                        type yang:counter64;
                                        description "SSDP frames transmitted";
                                    }

                                    leaf control-rx {
                                        type yang:counter64;
                                        description "UPnP control frames received";
                                    }

                                    leaf control-tx {
                                        type yang:counter64;
                                        description "UPnP control frames transmitted";
                                    }

                                    leaf rate-limited-request {
                                        type yang:counter64;
                                        description "UPnP query rate limited";
                                    }

                                    leaf pinhole-without-default-policy {
                                        type yang:counter64;
                                        description "Attempt to create pinhole without default policy";
                                    }

                                    leaf pinhole-without-source-nat {
                                        type yang:counter64;
                                        description "Attempt to create pinhole with source-nat disabled";
                                    }

                                } // container upnp

                                container service-chaining {
                                    description "Enter the service-chaining context";

                                    leaf rx {
                                        type yang:counter64;
                                        description "Service-chaining frames received";
                                    }

                                    leaf tx {
                                        type yang:counter64;
                                        description "Service-chaining frames transmitted";
                                    }

                                } // container service-chaining

                            } // container nat

                        } // container statistics

                    } // container nat

                    container performance {
                        description "Enter the performance context";

                        container last-hour {
                            description "Enter the last-hour context";

                            list minutes-ago {
                                key "index";
                                description "Enter the minutes-ago list instance";

                                leaf index {
                                    type uint32;
                                    description "Numerical index value generated by the system.";
                                }

                                leaf timestamp {
                                    type yang:date-and-time;
                                    description "Time at which the measurement was taken";
                                }

                                leaf waiting {
                                    type decimal64 {
                                        range "0..100";
                                        fraction-digits 2;
                                    }
                                    units "percent";
                                    description "Relative time spent waiting in the measured period.";
                                }

                                leaf idling {
                                    type decimal64 {
                                        range "0..100";
                                        fraction-digits 2;
                                    }
                                    units "percent";
                                    description "Relative time spent idling in the measured period.";
                                }

                                leaf working {
                                    type decimal64 {
                                        range "0..100";
                                        fraction-digits 2;
                                    }
                                    units "percent";
                                    description "Relative time spent working in the measured period.";
                                }

                                leaf jobs {
                                    type uint32;
                                    description "The number of jobs performed in the measured period.";
                                }

                                leaf throughput {
                                    type uint64;
                                    units "bytes";
                                    description "The amount of data processed in the measured period.";
                                }

                            } // list minutes-ago

                        } // container last-hour

                        container last-day {
                            description "Enter the last-day context";

                            list hours-ago {
                                key "index";
                                description "Enter the hours-ago list instance";

                                leaf index {
                                    type uint32;
                                    description "Numerical index value generated by the system.";
                                }

                                leaf timestamp {
                                    type yang:date-and-time;
                                    description "Time at which the measurement was taken";
                                }

                                leaf waiting {
                                    type decimal64 {
                                        range "0..100";
                                        fraction-digits 2;
                                    }
                                    units "percent";
                                    description "Relative time spent waiting in the measured period.";
                                }

                                leaf idling {
                                    type decimal64 {
                                        range "0..100";
                                        fraction-digits 2;
                                    }
                                    units "percent";
                                    description "Relative time spent idling in the measured period.";
                                }

                                leaf working {
                                    type decimal64 {
                                        range "0..100";
                                        fraction-digits 2;
                                    }
                                    units "percent";
                                    description "Relative time spent working in the measured period.";
                                }

                                leaf jobs {
                                    type uint32;
                                    description "The number of jobs performed in the measured period.";
                                }

                                leaf throughput {
                                    type uint64;
                                    units "bytes";
                                    description "The amount of data processed in the measured period.";
                                }

                            } // list hours-ago

                        } // container last-day

                        container last-month {
                            description "Enter the last-month context";

                            list days-ago {
                                key "index";
                                description "Enter the days-ago list instance";

                                leaf index {
                                    type uint32;
                                    description "Numerical index value generated by the system.";
                                }

                                leaf timestamp {
                                    type yang:date-and-time;
                                    description "Time at which the measurement was taken";
                                }

                                leaf waiting {
                                    type decimal64 {
                                        range "0..100";
                                        fraction-digits 2;
                                    }
                                    units "percent";
                                    description "Relative time spent waiting in the measured period.";
                                }

                                leaf idling {
                                    type decimal64 {
                                        range "0..100";
                                        fraction-digits 2;
                                    }
                                    units "percent";
                                    description "Relative time spent idling in the measured period.";
                                }

                                leaf working {
                                    type decimal64 {
                                        range "0..100";
                                        fraction-digits 2;
                                    }
                                    units "percent";
                                    description "Relative time spent working in the measured period.";
                                }

                                leaf jobs {
                                    type uint32;
                                    description "The number of jobs performed in the measured period.";
                                }

                                leaf throughput {
                                    type uint64;
                                    units "bytes";
                                    description "The amount of data processed in the measured period.";
                                }

                            } // list days-ago

                        } // container last-month

                    } // container performance

                } // list esa

                list member {
                    key "id";
                    description "Enter the member list instance";

                    leaf id {
                        type uint32;
                        description "Unique value which identifies the member within a WLAN-GW group";
                    }

                    leaf mda {
                        type types-isa:slot-mda;
                        description "Indicate the MDA associated with this member";
                    }

                    leaf num-tunnels {
                        type uint32;
                        description "Number of tunnels processed by the MDA or ESA-VM associated with this member";
                    }

                    leaf num-ues {
                        type uint32;
                        description "Number of UEs processed by the MDA or ESA-VM associated with this member";
                    }

                    leaf num-active-tunnel-shapers {
                        type uint32;
                        description "Number of activated Tunnel Shapers associated with this ISA group member";
                    }

                    leaf num-pending-tunnel-shapers {
                        type uint32;
                        description "Number of pending Tunnel Shapers associated with this ISA group member";
                    }

                    leaf num-failed-tunnel-shapers {
                        type uint32;
                        description "Number of tunnel Qos infrastructure configuration instances on the MDA or ESA-VM associated with this ISA group member that have a resource issue";
                    }

                    leaf state {
                        type enumeration {
                            enum "inactive"                     { value 1; }
                            enum "active"                       { value 2; }
                            enum "needs-reset"                  { value 3; }
                            enum "resetting"                    { value 4; }
                            enum "needs-reconcile"              { value 5; }
                            enum "reconciling"                  { value 6; }
                            enum "needs-audit"                  { value 7; }
                            enum "auditing"                     { value 8; }
                            enum "failed-bypass"                { value 9; }
                            enum "active-bypass"                { value 10; }
                        }
                        description "The state of the MDA or ESA-VM associated with this member";
                    }

                    container esa-vm {
                        description "Enter the esa-vm context";

                        leaf esa {
                            type types-esa:esa-id;
                            description "Indicate the ESA associated with this member";
                        }

                        leaf vm {
                            type types-esa:vm-id;
                            description "Indicate the ESA-VM associated with this member";
                        }

                    } // container esa-vm

                    container nat {
                        description "Enter the nat context";

                        leaf reserved-outside-ip-addresses {
                            type yang:gauge32;
                            description "The number of outside IP addresses reserved for the MDA or ESA-VM associated with this member";
                        }

                        leaf outside-port-blocks {
                            type yang:gauge32;
                            description "The number of outside port blocks reserved for the MDA or ESA-VM associated with this member";
                        }

                        leaf session-usage {
                            type types-isa:nat-usage-level;
                            description "The session usage of the MDA or ESA-VM associated with this member";
                        }

                        leaf high-session-usage {
                            type boolean;
                            description "Indicates if the session usage of the MDA or ESA-VM associated with this member is high according to the values of watermark definitions";
                        }

                        leaf prioritized-sessions {
                            type yang:gauge32;
                            description "The current number of active prioritized sessions of the MDA or ESA-VM associated with this member";
                        }

                        container resources {
                            description "Enter the resources context";

                            container port-ranges {
                                description "Enter the port-ranges context";

                                container configured {
                                    description "Enter the configured context";

                                    leaf value {
                                        type yang:gauge64;
                                        description "Actual consumed value";
                                    }

                                    leaf max {
                                        type uint64;
                                        description "The max value this resource can have, depending on the configuration";
                                    }

                                    leaf peak {
                                        type yang:gauge64;
                                        description "The peak value for the resource";
                                    }

                                    leaf peak-timestamp {
                                        type types-sros:date-time;
                                        description "The timestamp when the peak value was observed";
                                    }

                                } // container configured

                                container used {
                                    description "Enter the used context";

                                    leaf value {
                                        type yang:gauge64;
                                        description "Actual consumed value";
                                    }

                                    leaf max {
                                        type uint64;
                                        description "The max value this resource can have, depending on the configuration";
                                    }

                                    leaf peak {
                                        type yang:gauge64;
                                        description "The peak value for the resource";
                                    }

                                    leaf peak-timestamp {
                                        type types-sros:date-time;
                                        description "The timestamp when the peak value was observed";
                                    }

                                } // container used

                                container retained {
                                    description "Enter the retained context";

                                    leaf value {
                                        type yang:gauge64;
                                        description "Actual consumed value";
                                    }

                                    leaf max {
                                        type uint64;
                                        description "The max value this resource can have, depending on the configuration";
                                    }

                                    leaf peak {
                                        type yang:gauge64;
                                        description "The peak value for the resource";
                                    }

                                    leaf peak-timestamp {
                                        type types-sros:date-time;
                                        description "The timestamp when the peak value was observed";
                                    }

                                } // container retained

                            } // container port-ranges

                            container ports {
                                description "Enter the ports context";

                                leaf value {
                                    type yang:gauge64;
                                    description "Actual consumed value";
                                }

                                leaf max {
                                    type uint64;
                                    description "The max value this resource can have, depending on the configuration";
                                }

                                leaf peak {
                                    type yang:gauge64;
                                    description "The peak value for the resource";
                                }

                                leaf peak-timestamp {
                                    type types-sros:date-time;
                                    description "The timestamp when the peak value was observed";
                                }

                            } // container ports

                            container ip-addresses {
                                description "Enter the ip-addresses context";

                                leaf value {
                                    type yang:gauge64;
                                    description "Actual consumed value";
                                }

                                leaf max {
                                    type uint64;
                                    description "The max value this resource can have, depending on the configuration";
                                }

                                leaf peak {
                                    type yang:gauge64;
                                    description "The peak value for the resource";
                                }

                                leaf peak-timestamp {
                                    type types-sros:date-time;
                                    description "The timestamp when the peak value was observed";
                                }

                            } // container ip-addresses

                            container one-to-one-ip-addresses {
                                description "Enter the one-to-one-ip-addresses context";

                                leaf value {
                                    type yang:gauge64;
                                    description "Actual consumed value";
                                }

                                leaf max {
                                    type uint64;
                                    description "The max value this resource can have, depending on the configuration";
                                }

                                leaf peak {
                                    type yang:gauge64;
                                    description "The peak value for the resource";
                                }

                                leaf peak-timestamp {
                                    type types-sros:date-time;
                                    description "The timestamp when the peak value was observed";
                                }

                            } // container one-to-one-ip-addresses

                            container large-scale-hosts {
                                description "Enter the large-scale-hosts context";

                                leaf value {
                                    type yang:gauge64;
                                    description "Actual consumed value";
                                }

                                leaf max {
                                    type uint64;
                                    description "The max value this resource can have, depending on the configuration";
                                }

                                leaf peak {
                                    type yang:gauge64;
                                    description "The peak value for the resource";
                                }

                                leaf peak-timestamp {
                                    type types-sros:date-time;
                                    description "The timestamp when the peak value was observed";
                                }

                            } // container large-scale-hosts

                            container l2-aware {
                                description "Enter the l2-aware context";

                                container subscribers {
                                    description "Enter the subscribers context";

                                    leaf value {
                                        type yang:gauge64;
                                        description "Actual consumed value";
                                    }

                                    leaf max {
                                        type uint64;
                                        description "The max value this resource can have, depending on the configuration";
                                    }

                                    leaf peak {
                                        type yang:gauge64;
                                        description "The peak value for the resource";
                                    }

                                    leaf peak-timestamp {
                                        type types-sros:date-time;
                                        description "The timestamp when the peak value was observed";
                                    }

                                } // container subscribers

                                container hosts {
                                    description "Enter the hosts context";

                                    leaf value {
                                        type yang:gauge64;
                                        description "Actual consumed value";
                                    }

                                    leaf max {
                                        type uint64;
                                        description "The max value this resource can have, depending on the configuration";
                                    }

                                    leaf peak {
                                        type yang:gauge64;
                                        description "The peak value for the resource";
                                    }

                                    leaf peak-timestamp {
                                        type types-sros:date-time;
                                        description "The timestamp when the peak value was observed";
                                    }

                                } // container hosts

                            } // container l2-aware

                        } // container resources

                    } // container nat

                    container statistics {
                        description "Enter the statistics context";

                        container packet-errors {
                            description "Enter the packet-errors context";

                            leaf malformed-packet {
                                type yang:counter64;
                                description "The received packet isn't valid according to the specification for the protocol";
                            }

                            leaf nge-dropped-packets {
                                type yang:counter64;
                                description "Number of packets dropped by Network Group Encryption";
                            }

                        } // container packet-errors

                        container ue-errors {
                            description "Enter the ue-errors context";

                            leaf out-of-ues {
                                type yang:counter64;
                                description "Out of UE records";
                            }

                            leaf ues-purged {
                                type yang:counter64;
                                description "Number of ISA-only UEs (e.g. DSM or portal) that were removed because an ESM UE was installed";
                            }

                            leaf out-of-resources {
                                type yang:counter64;
                                description "Out of queue or packet resources";
                            }

                            leaf out-of-url-buffer-resources {
                                type yang:counter64;
                                description "Out of URL buffer resources";
                            }

                            leaf source-address-filtered {
                                type yang:counter64;
                                description "Number of UE packets filtered because of unknown source address";
                            }

                            leaf policing-filtered {
                                type yang:counter64;
                                description "Number of UE packets filtered because of policing";
                            }

                            leaf ue-filtered {
                                type yang:counter64;
                                description "Number of UE packets filtered because of various reasons";
                            }

                        } // container ue-errors

                        container bd-errors {
                            description "Enter the bd-errors context";

                            leaf flooding-failed {
                                type yang:counter64;
                                description "Flooding failed because of packet resources";
                            }

                            leaf unknown-vni {
                                type yang:counter64;
                                description "Unknown VNI to access the bridge domain";
                            }

                        } // container bd-errors

                        container forwarded-packets {
                            description "Enter the forwarded-packets context";

                            leaf tunnel-mobility-auto-relearn {
                                type yang:counter64;
                                description "Number of auto-relearn tunnel mobility events";
                            }

                            leaf tx-upstream-tunnel {
                                type yang:counter64;
                                description "Number of tunnel packets transmitted upstream";
                            }

                            leaf tx-downstream-tunnel {
                                type yang:counter64;
                                description "Number of tunnel packets transmitted downstream";
                            }

                            leaf tx-upstream-ue {
                                type yang:counter64;
                                description "Number of UE packets transmitted upstream";
                            }

                            leaf tx-downstream-ue {
                                type yang:counter64;
                                description "Number of UE packets transmitted downstream";
                            }

                            leaf tx-upstream-portal-redirect {
                                type yang:counter64;
                                description "Number of portal packets redirected upstream";
                            }

                            leaf tx-upstream-aa {
                                type yang:counter64;
                                description "Number of packets transmitted upstream to AA";
                            }

                            leaf tx-downstream-aa {
                                type yang:counter64;
                                description "Number of packets transmitted downstream to AA";
                            }

                            leaf tx-upstream-radius-proxy {
                                type yang:counter64;
                                description "Number of RADIUS proxy packets transmitted upstream";
                            }

                        } // container forwarded-packets

                        container reassembly {
                            description "Enter the reassembly context";

                            leaf out-of-fragment-list-resources {
                                type yang:counter64;
                                description "Out of fragment list resources used for incomplete packets with unreceived fragments";
                            }

                            leaf out-of-fragment-buffer-resources {
                                type yang:counter64;
                                description "Out of fragment buffer resources used for received fragments of incomplete packets";
                            }

                            leaf out-of-fragment-hole-resources {
                                type yang:counter64;
                                description "Out of fragment hole resources used for unreceived segments in incomplete packets";
                            }

                            leaf reassembly-failed {
                                type yang:counter64;
                                description "Reassembly failed because of various reasons";
                            }

                            leaf reassembled-packets {
                                type yang:counter64;
                                description "Number of reassembled packets";
                            }

                        } // container reassembly

                        container aa {
                            description "Enter the aa context";

                            leaf out-of-resources {
                                type yang:counter64;
                                description "Out of resources because too many AA enabled UEs for an oversubscribed AA";
                            }

                            leaf out-of-url-buffer-resources {
                                type yang:counter64;
                                description "Out of URL buffer resources used for the AA subscriber URL parameter";
                            }

                            leaf unknown-aso-override {
                                type yang:counter64;
                                description "Unknown ASO override received";
                            }

                        } // container aa

                        container radius {
                            description "Enter the radius context";

                            leaf tx-authentication-request {
                                type yang:counter64;
                                description "Number of transmitted authentication requests";
                            }

                            leaf rx-authentication-response {
                                type yang:counter64;
                                description "Number of received authentication responses";
                            }

                            leaf rx-authentication-reject {
                                type yang:counter64;
                                description "Number of received authentication rejects";
                            }

                            leaf rx-coa-request {
                                type yang:counter64;
                                description "Number of received CoA requests";
                            }

                            leaf tx-coa-ack {
                                type yang:counter64;
                                description "Number of transmitted CoA acknowledgements";
                            }

                            leaf rx-disconnect-request {
                                type yang:counter64;
                                description "Number of received disconnect requests";
                            }

                            leaf authentication-portal-failed {
                                type yang:counter64;
                                description "Authentication request to install portal user failed";
                            }

                            leaf authentication-dsm-failed {
                                type yang:counter64;
                                description "Authentication request to install DSM user failed";
                            }

                            leaf authentication-xconnect-failed {
                                type yang:counter64;
                                description "Authentication request to install xconnect user failed";
                            }

                            leaf out-of-authentication-transaction-resources {
                                type yang:counter64;
                                description "Out of transaction resources used to transmit authentication requests, can also be caused by misconfiguration";
                            }

                            leaf out-of-accounting-transaction-resources {
                                type yang:counter64;
                                description "Out of transaction resources used to transmit accounting requests, can also be caused by misconfiguration";
                            }

                            leaf out-of-accounting-queue-resources {
                                type yang:counter64;
                                description "Out of queue resources used to transmit accounting requests";
                            }

                            leaf out-of-packet-resources {
                                type yang:counter64;
                                description "Out of packet resources";
                            }

                            leaf proxy-dropped-packets {
                                type yang:counter64;
                                description "Number of packets dropped by RADIUS proxy";
                            }

                            leaf proxy-vlan-mismatch {
                                type yang:counter64;
                                description "RADIUS proxy VLAN mismatch with UE record";
                            }

                            leaf python-dropped-packets {
                                type yang:counter64;
                                description "Number of packets dropped by Python";
                            }

                            leaf dns-override-ignored {
                                type yang:counter64;
                                description "Secondary DNS override ignored because no Primary DNS override received";
                            }

                        } // container radius

                        container arp {
                            description "Enter the arp context";

                            leaf tx-gre-request {
                                type yang:counter64;
                                description "Number of transmitted GRE ARP requests";
                            }

                            leaf rx-gre-reply {
                                type yang:counter64;
                                description "Number of received GRE ARP replies";
                            }

                            leaf gre-out-of-packet-resources {
                                type yang:counter64;
                                description "Out of packet resources for GRE ARP requests";
                            }

                            leaf tx-ue-arp-reply {
                                type yang:counter64;
                                description "Number of transmitted UE ARP replies";
                            }

                            leaf rx-shcv-arp-reply {
                                type yang:counter64;
                                description "Number of received SHCV ARP replies";
                            }

                        } // container arp

                        container dhcp4 {
                            description "Enter the dhcp4 context";

                            leaf out-of-resources {
                                type yang:counter64;
                                description "Out of queue or packet resources";
                            }

                            leaf tx-offer {
                                type yang:counter64;
                                description "Number of transmitted DHCP offers";
                            }

                            leaf tx-ack {
                                type yang:counter64;
                                description "Number of transmitted DHCP acks";
                            }

                            leaf tx-nak {
                                type yang:counter64;
                                description "Number of transmitted DHCP naks";
                            }

                            leaf rx-decline {
                                type yang:counter64;
                                description "Number of received DHCP declines";
                            }

                            leaf rx-release {
                                type yang:counter64;
                                description "Number of received DHCP releases";
                            }

                            leaf l2-wholesale-option-insert-failed {
                                type yang:counter64;
                                description "DHCP option insert failed for L2 wholesale";
                            }

                        } // container dhcp4

                        container dhcp6 {
                            description "Enter the dhcp6 context";

                            leaf out-of-resources {
                                type yang:counter64;
                                description "Out of queue or packet resources";
                            }

                            leaf tx-advertise {
                                type yang:counter64;
                                description "Number of transmitted DHCPv6 advertises";
                            }

                            leaf tx-reply {
                                type yang:counter64;
                                description "Number of transmitted DHCPv6 replies";
                            }

                            leaf rx-decline {
                                type yang:counter64;
                                description "Number of received DHCPv6 declines";
                            }

                            leaf rx-release {
                                type yang:counter64;
                                description "Number of received DHCPv6 releases";
                            }

                            leaf rx-confirm {
                                type yang:counter64;
                                description "Number of received DHCPv6 confirms";
                            }

                            leaf rx-info-request {
                                type yang:counter64;
                                description "Number of received DHCPv6 information requests";
                            }

                            leaf ipv6-unavailable {
                                type yang:counter64;
                                description "No IPv6 address available for DHCPv6";
                            }

                        } // container dhcp6

                        container icmp4 {
                            description "Enter the icmp4 context";

                            leaf tx-tunnel-echo-reply {
                                type yang:counter64;
                                description "Number of transmitted tunnel ICMP echo replies";
                            }

                            leaf tx-ue-echo-reply {
                                type yang:counter64;
                                description "Number of transmitted UE ICMP echo replies";
                            }

                        } // container icmp4

                        container icmp6 {
                            description "Enter the icmp6 context";

                            leaf tx-gre-neighbor-solicitation {
                                type yang:counter64;
                                description "Number of transmitted GRE ICMPv6 neighbor solicitations";
                            }

                            leaf rx-gre-neighbor-advertisement {
                                type yang:counter64;
                                description "Number of received GRE ICMPv6 neighbor advertisements";
                            }

                            leaf gre-out-of-packet-resources {
                                type yang:counter64;
                                description "Out of packet resources GRE ICMPv6 neighbor solicitations";
                            }

                            leaf tx-tunnel-echo-reply {
                                type yang:counter64;
                                description "Number of transmitted tunnel ICMPv6 echo replies";
                            }

                            leaf tx-ue-echo-reply {
                                type yang:counter64;
                                description "Number of transmitted UE ICMPv6 echo replies";
                            }

                            leaf out-of-resources {
                                type yang:counter64;
                                description "Out of queue or packet resources";
                            }

                            leaf tx-router-advertisement {
                                type yang:counter64;
                                description "Number of transmitted ICMPv6 router advertisements";
                            }

                            leaf tx-neighbor-solicitation {
                                type yang:counter64;
                                description "Number of transmitted UE ICMPv6 neighbor solicitations";
                            }

                            leaf tx-ue-neighbor-advertisement {
                                type yang:counter64;
                                description "Number of transmitted UE ICMPv6 neighbor advertisements";
                            }

                            leaf rx-shcv-neighbor-advertisement {
                                type yang:counter64;
                                description "Number of received SHCV ICMPv6 neighbor advertisement";
                            }

                            leaf prefix-unavailable {
                                type yang:counter64;
                                description "No IPv6 prefix available for SLAAC";
                            }

                        } // container icmp6

                        container resources {
                            description "Enter the resources context";

                            leaf peak-values-last-reset {
                                type yang:date-and-time;
                                description "Moment when the peak values were last reset";
                            }

                            container destinations {
                                description "Enter the destinations context";

                                leaf max {
                                    type yang:counter64;
                                    description "Maximum possible value of this resource";
                                }

                                leaf value {
                                    type yang:counter64;
                                    description "Actual value of this resource";
                                }

                                leaf peak {
                                    type yang:counter64;
                                    description "Peak value of this resource";
                                }

                                leaf peak-timestamp {
                                    type types-sros:date-time;
                                    description "The time the system reached the peak value of this resource";
                                }

                            } // container destinations

                            container vlan-ranges {
                                description "Enter the vlan-ranges context";

                                leaf max {
                                    type yang:counter64;
                                    description "Maximum possible value of this resource";
                                }

                                leaf value {
                                    type yang:counter64;
                                    description "Actual value of this resource";
                                }

                                leaf peak {
                                    type yang:counter64;
                                    description "Peak value of this resource";
                                }

                                leaf peak-timestamp {
                                    type types-sros:date-time;
                                    description "The time the system reached the peak value of this resource";
                                }

                            } // container vlan-ranges

                            container ues {
                                description "Enter the ues context";

                                leaf max {
                                    type yang:counter64;
                                    description "Maximum possible value of this resource";
                                }

                                leaf value {
                                    type yang:counter64;
                                    description "Actual value of this resource";
                                }

                                leaf peak {
                                    type yang:counter64;
                                    description "Peak value of this resource";
                                }

                                leaf peak-timestamp {
                                    type types-sros:date-time;
                                    description "The time the system reached the peak value of this resource";
                                }

                            } // container ues

                            container http-redirect-policies {
                                description "Enter the http-redirect-policies context";

                                leaf max {
                                    type yang:counter64;
                                    description "Maximum possible value of this resource";
                                }

                                leaf value {
                                    type yang:counter64;
                                    description "Actual value of this resource";
                                }

                                leaf peak {
                                    type yang:counter64;
                                    description "Peak value of this resource";
                                }

                                leaf peak-timestamp {
                                    type types-sros:date-time;
                                    description "The time the system reached the peak value of this resource";
                                }

                            } // container http-redirect-policies

                            container filters {
                                description "Enter the filters context";

                                leaf max {
                                    type yang:counter64;
                                    description "Maximum possible value of this resource";
                                }

                                leaf value {
                                    type yang:counter64;
                                    description "Actual value of this resource";
                                }

                                leaf peak {
                                    type yang:counter64;
                                    description "Peak value of this resource";
                                }

                                leaf peak-timestamp {
                                    type types-sros:date-time;
                                    description "The time the system reached the peak value of this resource";
                                }

                            } // container filters

                            container policers {
                                description "Enter the policers context";

                                leaf max {
                                    type yang:counter64;
                                    description "Maximum possible value of this resource";
                                }

                                leaf value {
                                    type yang:counter64;
                                    description "Actual value of this resource";
                                }

                                leaf peak {
                                    type yang:counter64;
                                    description "Peak value of this resource";
                                }

                                leaf peak-timestamp {
                                    type types-sros:date-time;
                                    description "The time the system reached the peak value of this resource";
                                }

                            } // container policers

                            container mirrors {
                                description "Enter the mirrors context";

                                leaf max {
                                    type yang:counter64;
                                    description "Maximum possible value of this resource";
                                }

                                leaf value {
                                    type yang:counter64;
                                    description "Actual value of this resource";
                                }

                                leaf peak {
                                    type yang:counter64;
                                    description "Peak value of this resource";
                                }

                                leaf peak-timestamp {
                                    type types-sros:date-time;
                                    description "The time the system reached the peak value of this resource";
                                }

                            } // container mirrors

                            container slaac-subnets {
                                description "Enter the slaac-subnets context";

                                leaf max {
                                    type yang:counter64;
                                    description "Maximum possible value of this resource";
                                }

                                leaf value {
                                    type yang:counter64;
                                    description "Actual value of this resource";
                                }

                                leaf peak {
                                    type yang:counter64;
                                    description "Peak value of this resource";
                                }

                                leaf peak-timestamp {
                                    type types-sros:date-time;
                                    description "The time the system reached the peak value of this resource";
                                }

                            } // container slaac-subnets

                            container dhcp6-subnets {
                                description "Enter the dhcp6-subnets context";

                                leaf max {
                                    type yang:counter64;
                                    description "Maximum possible value of this resource";
                                }

                                leaf value {
                                    type yang:counter64;
                                    description "Actual value of this resource";
                                }

                                leaf peak {
                                    type yang:counter64;
                                    description "Peak value of this resource";
                                }

                                leaf peak-timestamp {
                                    type types-sros:date-time;
                                    description "The time the system reached the peak value of this resource";
                                }

                            } // container dhcp6-subnets

                            container dhcp-subnets {
                                description "Enter the dhcp-subnets context";

                                leaf max {
                                    type yang:counter64;
                                    description "Maximum possible value of this resource";
                                }

                                leaf value {
                                    type yang:counter64;
                                    description "Actual value of this resource";
                                }

                                leaf peak {
                                    type yang:counter64;
                                    description "Peak value of this resource";
                                }

                                leaf peak-timestamp {
                                    type types-sros:date-time;
                                    description "The time the system reached the peak value of this resource";
                                }

                            } // container dhcp-subnets

                            container xconnect-router-instances {
                                description "Enter the xconnect-router-instances context";

                                leaf max {
                                    type yang:counter64;
                                    description "Maximum possible value of this resource";
                                }

                                leaf value {
                                    type yang:counter64;
                                    description "Actual value of this resource";
                                }

                                leaf peak {
                                    type yang:counter64;
                                    description "Peak value of this resource";
                                }

                                leaf peak-timestamp {
                                    type types-sros:date-time;
                                    description "The time the system reached the peak value of this resource";
                                }

                            } // container xconnect-router-instances

                            container bridge-domains {
                                description "Enter the bridge-domains context";

                                leaf max {
                                    type yang:counter64;
                                    description "Maximum possible value of this resource";
                                }

                                leaf value {
                                    type yang:counter64;
                                    description "Actual value of this resource";
                                }

                                leaf peak {
                                    type yang:counter64;
                                    description "Peak value of this resource";
                                }

                                leaf peak-timestamp {
                                    type types-sros:date-time;
                                    description "The time the system reached the peak value of this resource";
                                }

                            } // container bridge-domains

                            container virtual-network-identifier {
                                description "Enter the virtual-network-identifier context";

                                leaf max {
                                    type yang:counter64;
                                    description "Maximum possible value of this resource";
                                }

                                leaf value {
                                    type yang:counter64;
                                    description "Actual value of this resource";
                                }

                                leaf peak {
                                    type yang:counter64;
                                    description "Peak value of this resource";
                                }

                                leaf peak-timestamp {
                                    type types-sros:date-time;
                                    description "The time the system reached the peak value of this resource";
                                }

                            } // container virtual-network-identifier

                            container bridge-domain-filters {
                                description "Enter the bridge-domain-filters context";

                                leaf max {
                                    type yang:counter64;
                                    description "Maximum possible value of this resource";
                                }

                                leaf value {
                                    type yang:counter64;
                                    description "Actual value of this resource";
                                }

                                leaf peak {
                                    type yang:counter64;
                                    description "Peak value of this resource";
                                }

                                leaf peak-timestamp {
                                    type types-sros:date-time;
                                    description "The time the system reached the peak value of this resource";
                                }

                            } // container bridge-domain-filters

                            container radius-proxy-servers {
                                description "Enter the radius-proxy-servers context";

                                leaf max {
                                    type yang:counter64;
                                    description "Maximum possible value of this resource";
                                }

                                leaf value {
                                    type yang:counter64;
                                    description "Actual value of this resource";
                                }

                                leaf peak {
                                    type yang:counter64;
                                    description "Peak value of this resource";
                                }

                                leaf peak-timestamp {
                                    type types-sros:date-time;
                                    description "The time the system reached the peak value of this resource";
                                }

                            } // container radius-proxy-servers

                            container radius-proxy-contexts {
                                description "Enter the radius-proxy-contexts context";

                                leaf max {
                                    type yang:counter64;
                                    description "Maximum possible value of this resource";
                                }

                                leaf value {
                                    type yang:counter64;
                                    description "Actual value of this resource";
                                }

                                leaf peak {
                                    type yang:counter64;
                                    description "Peak value of this resource";
                                }

                                leaf peak-timestamp {
                                    type types-sros:date-time;
                                    description "The time the system reached the peak value of this resource";
                                }

                            } // container radius-proxy-contexts

                            container application-profiles {
                                description "Enter the application-profiles context";

                                leaf max {
                                    type yang:counter64;
                                    description "Maximum possible value of this resource";
                                }

                                leaf value {
                                    type yang:counter64;
                                    description "Actual value of this resource";
                                }

                                leaf peak {
                                    type yang:counter64;
                                    description "Peak value of this resource";
                                }

                                leaf peak-timestamp {
                                    type types-sros:date-time;
                                    description "The time the system reached the peak value of this resource";
                                }

                            } // container application-profiles

                            container application-service-options {
                                description "Enter the application-service-options context";

                                leaf max {
                                    type yang:counter64;
                                    description "Maximum possible value of this resource";
                                }

                                leaf value {
                                    type yang:counter64;
                                    description "Actual value of this resource";
                                }

                                leaf peak {
                                    type yang:counter64;
                                    description "Peak value of this resource";
                                }

                                leaf peak-timestamp {
                                    type types-sros:date-time;
                                    description "The time the system reached the peak value of this resource";
                                }

                            } // container application-service-options

                            container aa-ues {
                                description "Enter the aa-ues context";

                                leaf max {
                                    type yang:counter64;
                                    description "Maximum possible value of this resource";
                                }

                                leaf value {
                                    type yang:counter64;
                                    description "Actual value of this resource";
                                }

                                leaf peak {
                                    type yang:counter64;
                                    description "Peak value of this resource";
                                }

                                leaf peak-timestamp {
                                    type types-sros:date-time;
                                    description "The time the system reached the peak value of this resource";
                                }

                            } // container aa-ues

                            container fragment-lists {
                                description "Enter the fragment-lists context";

                                leaf max {
                                    type yang:counter64;
                                    description "Maximum possible value of this resource";
                                }

                                leaf value {
                                    type yang:counter64;
                                    description "Actual value of this resource";
                                }

                                leaf peak {
                                    type yang:counter64;
                                    description "Peak value of this resource";
                                }

                                leaf peak-timestamp {
                                    type types-sros:date-time;
                                    description "The time the system reached the peak value of this resource";
                                }

                            } // container fragment-lists

                            container fragment-holes {
                                description "Enter the fragment-holes context";

                                leaf max {
                                    type yang:counter64;
                                    description "Maximum possible value of this resource";
                                }

                                leaf value {
                                    type yang:counter64;
                                    description "Actual value of this resource";
                                }

                                leaf peak {
                                    type yang:counter64;
                                    description "Peak value of this resource";
                                }

                                leaf peak-timestamp {
                                    type types-sros:date-time;
                                    description "The time the system reached the peak value of this resource";
                                }

                            } // container fragment-holes

                            container fragment-buffers {
                                description "Enter the fragment-buffers context";

                                leaf max {
                                    type yang:counter64;
                                    description "Maximum possible value of this resource";
                                }

                                leaf value {
                                    type yang:counter64;
                                    description "Actual value of this resource";
                                }

                                leaf peak {
                                    type yang:counter64;
                                    description "Peak value of this resource";
                                }

                                leaf peak-timestamp {
                                    type types-sros:date-time;
                                    description "The time the system reached the peak value of this resource";
                                }

                            } // container fragment-buffers

                        } // container resources

                    } // container statistics

                } // list member

            } // list wlan-gw-group

            list lns-group {
                key "id";
                description "Enter the lns-group list instance";

                leaf id {
                    type types-l2tp:lns-group-id;
                    description "LNS group ID";
                }

                leaf oper-state {
                    type types-sros:oper-state;
                    description "Operational state.";
                }

                list mda {
                    key "mda-id";
                    description "Enter the mda list instance";

                    leaf mda-id {
                        type types-isa:slot-mda;
                        description "MDA ID for the ISA LNS group";
                    }

                    leaf oper-state {
                        type types-l2tp:isa-member-oper-state;
                        description "The operation state of the ISA MDA";
                    }

                    leaf sessions {
                        type yang:gauge32;
                        description "The number of sessions handled by the ISA MDA";
                    }

                    list statistics {
                        key "counter";
                        description "Enter the statistics list instance";

                        leaf counter {
                            type uint32 {
                                range "0..70";
                            }
                            description "The counter";
                        }

                        leaf description {
                            type string {
                                length "0..70";
                            }
                            description "The human-readable identifier of the statistic.";
                        }

                        leaf value {
                            type yang:counter64;
                            description "The counter value";
                        }

                    } // list statistics

                } // list mda

                list esa {
                    key "esa-id vm";
                    description "Enter the esa list instance";

                    leaf esa-id {
                        type leafref {
                            path "../../../../esa/esa-id";
                        }
                        description "ESA ID";
                    }

                    leaf vm {
                        type leafref {
                            path "../../../../esa[esa-id=current()/../esa-id]/vm/vm-id";
                        }
                        description "VM ID";
                    }

                    leaf oper-state {
                        type types-l2tp:isa-member-oper-state;
                        description "The operation state of the ESA-VM";
                    }

                    leaf sessions {
                        type yang:gauge32;
                        description "The number of sessions handled by the ESA-VM";
                    }

                    list statistics {
                        key "counter";
                        description "Enter the statistics list instance";

                        leaf counter {
                            type uint32 {
                                range "0..70";
                            }
                            description "The counter";
                        }

                        leaf description {
                            type string {
                                length "0..70";
                            }
                            description "The human-readable identifier of the statistic.";
                        }

                        leaf value {
                            type yang:counter64;
                            description "The counter value";
                        }

                    } // list statistics

                } // list esa

            } // list lns-group

            uses state-isa-application-assurance-group;
            uses state-isa-video-group;
        } // container isa

    } // grouping state-isa

}
