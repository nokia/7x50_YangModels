submodule nokia-conf-aa-group {

    yang-version "1.1";

    belongs-to nokia-conf { prefix "conf"; }

    import ietf-yang-types                { prefix "yang"; }
    import nokia-sros-yang-extensions     { prefix "sros-ext"; }
    import nokia-types-application-assurance { prefix "types-aa"; }
    import nokia-types-qos                { prefix "types-qos"; }
    import nokia-types-services           { prefix "types-services"; }
    import nokia-types-sros               { prefix "types-sros"; }

    include nokia-conf-application-assurance;
    include nokia-conf-groups;
    include nokia-conf-log;
    include nokia-conf-mirror;
    include nokia-conf-subscriber-mgmt;


    sros-ext:sros-major-release "rel22";

    organization "Nokia";

    contact
        "Nokia SR OS Support
         Web: <http://www.nokia.com>";

    description
        "Nokia YANG Data model to configure application assurance group on SR OS based routers.

         Copyright 2016 Nokia. All rights reserved. Reproduction of this document
         is authorized on the condition that the foregoing copyright notice is included.

         This nokia-conf-aa-group YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";

    revision "2022-03-02";

    grouping conf-aa-group {
        list group {
            key "aa-group-id";
            description "Enter the group list instance";

            leaf aa-group-id {
                type uint32 {
                    range "1..255";
                }
                description "AA group ID";
            }

            leaf-list apply-groups {
                type leafref {
                    path "../../../groups/group/name";
                }
                max-elements 8;
                ordered-by user;
                description "Apply a configuration group at this level";
            }

            leaf-list apply-groups-exclude {
                type leafref {
                    path "../../../groups/group/name";
                }
                max-elements 8;
                ordered-by user;
                description "Exclude a configuration group at this level";
            }

            list certificate-profile {
                key "cert-prof-name";
                description "Enter the certificate-profile list instance";

                leaf cert-prof-name {
                    type types-sros:named-item;
                    description "AA group certificate profile name";
                }

                leaf admin-state {
                    type types-sros:admin-state;
                    default "disable";
                    description "Administrative state of the AA certificate profile";
                }

                leaf description {
                    type types-sros:description;
                    description "Text description";
                }

                leaf file {
                    type types-aa:certificate-file;
                    sros-ext:auto-restart-to-modify;
                    description "Certificate file name";
                }

                leaf-list apply-groups {
                    type leafref {
                        path "../../../../groups/group/name";
                    }
                    max-elements 8;
                    ordered-by user;
                    description "Apply a configuration group at this level";
                }

                leaf-list apply-groups-exclude {
                    type leafref {
                        path "../../../../groups/group/name";
                    }
                    max-elements 8;
                    ordered-by user;
                    description "Exclude a configuration group at this level";
                }

            } // list certificate-profile

            container cflowd {
                description "Enter the cflowd context";

                leaf admin-state {
                    type types-sros:admin-state;
                    default "disable";
                    description "Administrative state of cflowd export";
                }

                leaf template-retransmit {
                    type uint32 {
                        range "10..600";
                    }
                    units "seconds";
                    default "600";
                    description "Template retransmit time";
                }

                leaf-list apply-groups {
                    type leafref {
                        path "../../../../groups/group/name";
                    }
                    max-elements 8;
                    ordered-by user;
                    description "Apply a configuration group at this level";
                }

                leaf-list apply-groups-exclude {
                    type leafref {
                        path "../../../../groups/group/name";
                    }
                    max-elements 8;
                    ordered-by user;
                    description "Exclude a configuration group at this level";
                }

                container obfuscation {
                    description "Enter the obfuscation context";

                    leaf aes-128-encryption-key {
                        type types-sros:encrypted-leaf {
                            length "51";
                        }
                        description "AES-128 encryption key";
                    }

                    leaf aes-256-encryption-key {
                        type types-sros:encrypted-leaf {
                            length "71";
                        }
                        description "AES-256 encryption key";
                    }

                } // container obfuscation

                list collector {
                    key "ip-address port";
                    max-elements 2;
                    description "Enter the collector list instance";

                    leaf ip-address {
                        type types-sros:ip-unicast-address;
                        description "IP address of the remote cflowd collector host";
                    }

                    leaf port {
                        type types-sros:tcp-udp-port-non-zero;
                        description "Cflowd collector host port number";
                    }

                    leaf admin-state {
                        type types-sros:admin-state;
                        default "disable";
                        description "Administrative state of the cflowd export";
                    }

                    leaf description {
                        type types-sros:description;
                        description "Text description";
                    }

                    leaf-list apply-groups {
                        type leafref {
                            path "../../../../../groups/group/name";
                        }
                        max-elements 8;
                        ordered-by user;
                        description "Apply a configuration group at this level";
                    }

                    leaf-list apply-groups-exclude {
                        type leafref {
                            path "../../../../../groups/group/name";
                        }
                        max-elements 8;
                        ordered-by user;
                        description "Exclude a configuration group at this level";
                    }

                } // list collector

                container direct-export {
                    description "Enter the direct-export context";

                    leaf vlan-id {
                        type types-sros:vlan-id;
                        description "Cflowd direct export VLAN ID";
                    }

                    list collector {
                        key "collector-id";
                        max-elements 16;
                        description "Enter the collector list instance";

                        leaf collector-id {
                            type uint32 {
                                range "1..65535";
                            }
                            description "Cflowd direct export collector ID";
                        }

                        leaf description {
                            type types-sros:description;
                            description "Text description of the collector";
                        }

                        leaf-list apply-groups {
                            type leafref {
                                path "../../../../../../groups/group/name";
                            }
                            max-elements 8;
                            ordered-by user;
                            description "Apply a configuration group at this level";
                        }

                        leaf-list apply-groups-exclude {
                            type leafref {
                                path "../../../../../../groups/group/name";
                            }
                            max-elements 8;
                            ordered-by user;
                            description "Exclude a configuration group at this level";
                        }

                        list address {
                            key "ip-address port";
                            max-elements 2;
                            description "Enter the address list instance";

                            leaf ip-address {
                                type types-sros:ip-unicast-address;
                                description "IP address of the remote cflowd collector host";
                            }

                            leaf port {
                                type types-sros:tcp-udp-port-non-zero;
                                description "Cflowd collector host port number";
                            }

                            leaf admin-state {
                                type types-sros:admin-state;
                                default "disable";
                                description "Administrative state of the cflowd direct export collector";
                            }

                            leaf-list apply-groups {
                                type leafref {
                                    path "../../../../../../../groups/group/name";
                                }
                                max-elements 8;
                                ordered-by user;
                                description "Apply a configuration group at this level";
                            }

                            leaf-list apply-groups-exclude {
                                type leafref {
                                    path "../../../../../../../groups/group/name";
                                }
                                max-elements 8;
                                ordered-by user;
                                description "Exclude a configuration group at this level";
                            }

                        } // list address

                    } // list collector

                } // container direct-export

                container comprehensive {
                    description "Enter the comprehensive context";

                    leaf flow-rate {
                        type types-aa:cflowd-sample-rate;
                        description "Cflowd flow sampling rate";
                    }

                    leaf flow-rate-2 {
                        type types-aa:cflowd-sample-rate;
                        description "Cflowd per-flow second sampling rate";
                    }

                    leaf-list apply-groups {
                        type leafref {
                            path "../../../../../groups/group/name";
                        }
                        max-elements 8;
                        ordered-by user;
                        description "Apply a configuration group at this level";
                    }

                    leaf-list apply-groups-exclude {
                        type leafref {
                            path "../../../../../groups/group/name";
                        }
                        max-elements 8;
                        ordered-by user;
                        description "Exclude a configuration group at this level";
                    }

                    container template {
                        description "Enter the template context";

                        leaf field-selection {
                            type types-aa:aa-grp-cflowd-template-select;
                            default "legacy";
                            description "Field selection method";
                        }

                        leaf-list apply-groups {
                            type leafref {
                                path "../../../../../../groups/group/name";
                            }
                            max-elements 8;
                            ordered-by user;
                            description "Apply a configuration group at this level";
                        }

                        leaf-list apply-groups-exclude {
                            type leafref {
                                path "../../../../../../groups/group/name";
                            }
                            max-elements 8;
                            ordered-by user;
                            description "Exclude a configuration group at this level";
                        }

                        container dynamic-fields {
                            description "Enter the dynamic-fields context";

                            leaf admin-state {
                                type types-sros:admin-state;
                                default "disable";
                                description "Administrative state of the dynamic fields";
                            }

                            list field {
                                key "field-name";
                                description "Add a list entry for field";

                                leaf field-name {
                                    type types-sros:named-item;
                                    description "Cflowd template dynamic field name";
                                }

                            } // list field

                        } // container dynamic-fields

                    } // container template

                } // container comprehensive

                container export-override {
                    description "Enter the export-override context";

                    leaf mode {
                        type types-aa:cflowd-export-override-type;
                        sros-ext:auto-restart-to-modify;
                        description "AA cflowd export override mode";
                    }

                    leaf prefix {
                        type types-sros:named-item {
                            length "1..8";
                        }
                        sros-ext:auto-restart-to-modify;
                        description "AA group cflowd export override prefix";
                    }

                } // container export-override

                container rtp-performance {
                    description "Enter the rtp-performance context";

                    leaf flow-rate {
                        type types-aa:cflowd-sample-rate;
                        description "Cflowd flow sampling rate";
                    }

                    leaf flow-rate-2 {
                        type types-aa:cflowd-sample-rate;
                        description "Cflowd per-flow second sampling rate";
                    }

                    leaf-list apply-groups {
                        type leafref {
                            path "../../../../../groups/group/name";
                        }
                        max-elements 8;
                        ordered-by user;
                        description "Apply a configuration group at this level";
                    }

                    leaf-list apply-groups-exclude {
                        type leafref {
                            path "../../../../../groups/group/name";
                        }
                        max-elements 8;
                        ordered-by user;
                        description "Exclude a configuration group at this level";
                    }

                    container audio-template {
                        description "Enter the audio-template context";

                        leaf field-selection {
                            type types-aa:aa-grp-cflowd-template-select;
                            default "legacy";
                            description "Field selection method";
                        }

                        leaf-list apply-groups {
                            type leafref {
                                path "../../../../../../groups/group/name";
                            }
                            max-elements 8;
                            ordered-by user;
                            description "Apply a configuration group at this level";
                        }

                        leaf-list apply-groups-exclude {
                            type leafref {
                                path "../../../../../../groups/group/name";
                            }
                            max-elements 8;
                            ordered-by user;
                            description "Exclude a configuration group at this level";
                        }

                        container dynamic-fields {
                            description "Enter the dynamic-fields context";

                            leaf admin-state {
                                type types-sros:admin-state;
                                default "disable";
                                description "Administrative state of the dynamic fields";
                            }

                            list field {
                                key "field-name";
                                description "Add a list entry for field";

                                leaf field-name {
                                    type types-sros:named-item;
                                    description "Cflowd template dynamic field name";
                                }

                            } // list field

                        } // container dynamic-fields

                    } // container audio-template

                    container video-template {
                        description "Enter the video-template context";

                        leaf field-selection {
                            type types-aa:aa-grp-cflowd-template-select;
                            default "legacy";
                            description "Field selection method";
                        }

                        leaf-list apply-groups {
                            type leafref {
                                path "../../../../../../groups/group/name";
                            }
                            max-elements 8;
                            ordered-by user;
                            description "Apply a configuration group at this level";
                        }

                        leaf-list apply-groups-exclude {
                            type leafref {
                                path "../../../../../../groups/group/name";
                            }
                            max-elements 8;
                            ordered-by user;
                            description "Exclude a configuration group at this level";
                        }

                        container dynamic-fields {
                            description "Enter the dynamic-fields context";

                            leaf admin-state {
                                type types-sros:admin-state;
                                default "disable";
                                description "Administrative state of the dynamic fields";
                            }

                            list field {
                                key "field-name";
                                description "Add a list entry for field";

                                leaf field-name {
                                    type types-sros:named-item;
                                    description "Cflowd template dynamic field name";
                                }

                            } // list field

                        } // container dynamic-fields

                    } // container video-template

                    container voice-template {
                        description "Enter the voice-template context";

                        leaf field-selection {
                            type types-aa:aa-grp-cflowd-template-select;
                            default "legacy";
                            description "Field selection method";
                        }

                        leaf-list apply-groups {
                            type leafref {
                                path "../../../../../../groups/group/name";
                            }
                            max-elements 8;
                            ordered-by user;
                            description "Apply a configuration group at this level";
                        }

                        leaf-list apply-groups-exclude {
                            type leafref {
                                path "../../../../../../groups/group/name";
                            }
                            max-elements 8;
                            ordered-by user;
                            description "Exclude a configuration group at this level";
                        }

                        container dynamic-fields {
                            description "Enter the dynamic-fields context";

                            leaf admin-state {
                                type types-sros:admin-state;
                                default "disable";
                                description "Administrative state of the dynamic fields";
                            }

                            list field {
                                key "field-name";
                                description "Add a list entry for field";

                                leaf field-name {
                                    type types-sros:named-item;
                                    description "Cflowd template dynamic field name";
                                }

                            } // list field

                        } // container dynamic-fields

                    } // container voice-template

                } // container rtp-performance

                container tcp-performance {
                    description "Enter the tcp-performance context";

                    leaf flow-rate {
                        type types-aa:cflowd-sample-rate;
                        description "Cflowd flow sampling rate";
                    }

                    leaf flow-rate-2 {
                        type types-aa:cflowd-sample-rate;
                        description "Cflowd per-flow second sampling rate";
                    }

                    leaf-list apply-groups {
                        type leafref {
                            path "../../../../../groups/group/name";
                        }
                        max-elements 8;
                        ordered-by user;
                        description "Apply a configuration group at this level";
                    }

                    leaf-list apply-groups-exclude {
                        type leafref {
                            path "../../../../../groups/group/name";
                        }
                        max-elements 8;
                        ordered-by user;
                        description "Exclude a configuration group at this level";
                    }

                    container template {
                        description "Enter the template context";

                        leaf field-selection {
                            type types-aa:aa-grp-cflowd-template-select;
                            default "legacy";
                            description "Field selection method";
                        }

                        leaf-list apply-groups {
                            type leafref {
                                path "../../../../../../groups/group/name";
                            }
                            max-elements 8;
                            ordered-by user;
                            description "Apply a configuration group at this level";
                        }

                        leaf-list apply-groups-exclude {
                            type leafref {
                                path "../../../../../../groups/group/name";
                            }
                            max-elements 8;
                            ordered-by user;
                            description "Exclude a configuration group at this level";
                        }

                        container dynamic-fields {
                            description "Enter the dynamic-fields context";

                            leaf admin-state {
                                type types-sros:admin-state;
                                default "disable";
                                description "Administrative state of the dynamic fields";
                            }

                            list field {
                                key "field-name";
                                description "Add a list entry for field";

                                leaf field-name {
                                    type types-sros:named-item;
                                    description "Cflowd template dynamic field name";
                                }

                            } // list field

                        } // container dynamic-fields

                    } // container template

                } // container tcp-performance

                container volume {
                    description "Enter the volume context";

                    leaf rate {
                        type uint32 {
                            range "1..10000";
                        }
                        description "Cflowd packet sampling rate";
                    }

                    container template {
                        description "Enter the template context";

                        leaf field-selection {
                            type types-aa:aa-grp-cflowd-template-select;
                            default "legacy";
                            description "Field selection method";
                        }

                        leaf-list apply-groups {
                            type leafref {
                                path "../../../../../../groups/group/name";
                            }
                            max-elements 8;
                            ordered-by user;
                            description "Apply a configuration group at this level";
                        }

                        leaf-list apply-groups-exclude {
                            type leafref {
                                path "../../../../../../groups/group/name";
                            }
                            max-elements 8;
                            ordered-by user;
                            description "Exclude a configuration group at this level";
                        }

                        container dynamic-fields {
                            description "Enter the dynamic-fields context";

                            leaf admin-state {
                                type types-sros:admin-state;
                                default "disable";
                                description "Administrative state of the dynamic fields";
                            }

                            list field {
                                key "field-name";
                                description "Add a list entry for field";

                                leaf field-name {
                                    type types-sros:named-item;
                                    description "Cflowd template dynamic field name";
                                }

                            } // list field

                        } // container dynamic-fields

                    } // container template

                } // container volume

            } // container cflowd

            list dns-ip-cache {
                key "dns-ip-cache-name";
                description "Enter the dns-ip-cache list instance";

                leaf dns-ip-cache-name {
                    type types-sros:named-item;
                    description "DNS IP cache name within the AA group";
                }

                leaf admin-state {
                    type types-sros:admin-state;
                    default "disable";
                    description "Administrative state of the AA DNS IP cache object";
                }

                leaf description {
                    type types-sros:description;
                    description "Text description";
                }

                leaf-list apply-groups {
                    type leafref {
                        path "../../../../groups/group/name";
                    }
                    max-elements 8;
                    ordered-by user;
                    description "Apply a configuration group at this level";
                }

                leaf-list apply-groups-exclude {
                    type leafref {
                        path "../../../../groups/group/name";
                    }
                    max-elements 8;
                    ordered-by user;
                    description "Exclude a configuration group at this level";
                }

                container dns-match {
                    description "Enter the dns-match context";

                    list domain {
                        key "domain-name";
                        description "Enter the domain list instance";

                        leaf domain-name {
                            type types-sros:named-item;
                            description "DNS IP cache domain name";
                        }

                        leaf expression {
                            type types-sros:display-string;
                            description "AA DNS domain expression to match";
                        }

                        leaf-list apply-groups {
                            type leafref {
                                path "../../../../../../groups/group/name";
                            }
                            max-elements 8;
                            ordered-by user;
                            description "Apply a configuration group at this level";
                        }

                        leaf-list apply-groups-exclude {
                            type leafref {
                                path "../../../../../../groups/group/name";
                            }
                            max-elements 8;
                            ordered-by user;
                            description "Exclude a configuration group at this level";
                        }

                    } // list domain

                    list trusted-server-address {
                        key "dns-server-address";
                        description "Enter the trusted-server-address list instance";

                        leaf dns-server-address {
                            type types-sros:ip-address;
                            description "Trusted DNS server address";
                        }

                        leaf server-name {
                            type types-sros:named-item;
                            description "DNS server name";
                        }

                        leaf-list apply-groups {
                            type leafref {
                                path "../../../../../../groups/group/name";
                            }
                            max-elements 8;
                            ordered-by user;
                            description "Apply a configuration group at this level";
                        }

                        leaf-list apply-groups-exclude {
                            type leafref {
                                path "../../../../../../groups/group/name";
                            }
                            max-elements 8;
                            ordered-by user;
                            description "Exclude a configuration group at this level";
                        }

                    } // list trusted-server-address

                } // container dns-match

                container ip-cache {
                    description "Enter the ip-cache context";

                    leaf high-watermark {
                        type uint32 {
                            range "0..100";
                        }
                        default "90";
                        description "High watermark value for the DNS IP cache";
                    }

                    leaf low-watermark {
                        type uint32 {
                            range "0..100";
                        }
                        default "80";
                        description "Low watermark value for the DNS IP cache";
                    }

                    leaf size {
                        type uint32 {
                            range "10..64000";
                        }
                        default "10";
                        description "Maximum number of IP addresses stored in the cache";
                    }

                    list static-address {
                        key "static-ip-address";
                        description "Add a list entry for static-address";

                        leaf static-ip-address {
                            type types-sros:ip-address;
                            description "Trusted IP address for the DNS IP cache";
                        }

                    } // list static-address

                } // container ip-cache

            } // list dns-ip-cache

            list http-enrich {
                key "http-enrich-name";
                description "Enter the http-enrich list instance";

                leaf http-enrich-name {
                    type types-sros:named-item;
                    description "HTTP header enrichment policy name";
                }

                leaf admin-state {
                    type types-sros:admin-state;
                    default "disable";
                    description "Administrative state of the HTTP enrichment policy";
                }

                leaf description {
                    type types-sros:description;
                    description "Text description";
                }

                leaf-list apply-groups {
                    type leafref {
                        path "../../../../groups/group/name";
                    }
                    max-elements 8;
                    ordered-by user;
                    description "Apply a configuration group at this level";
                }

                leaf-list apply-groups-exclude {
                    type leafref {
                        path "../../../../groups/group/name";
                    }
                    max-elements 8;
                    ordered-by user;
                    description "Exclude a configuration group at this level";
                }

                list field {
                    key "field-name";
                    description "Enter the field list instance";

                    leaf field-name {
                        type types-sros:named-item;
                        description "Field name to insert into the HTTP header";
                    }

                    leaf anti-spoof {
                        type boolean;
                        default "false";
                        description "Enable anti-spoofing";
                    }

                    leaf calling-line-id {
                        type boolean;
                        default "false";
                        description "Enable calling line identification";
                    }

                    leaf name {
                        type types-sros:named-item;
                        sros-ext:immutable;
                        description "HTTP header field name";
                    }

                    leaf static-string {
                        type types-sros:string-not-all-spaces {
                            length "1..16";
                        }
                        description "HTTP header enrichment template field static string";
                    }

                    leaf-list apply-groups {
                        type leafref {
                            path "../../../../../groups/group/name";
                        }
                        max-elements 8;
                        ordered-by user;
                        description "Apply a configuration group at this level";
                    }

                    leaf-list apply-groups-exclude {
                        type leafref {
                            path "../../../../../groups/group/name";
                        }
                        max-elements 8;
                        ordered-by user;
                        description "Exclude a configuration group at this level";
                    }

                    container encode {
                        description "Enter the encode context";

                        choice encode-choice {
                            case cert-profile {

                                leaf cert-profile {
                                    type leafref {
                                        path "../../../../certificate-profile/cert-prof-name";
                                    }
                                    description "Certificate profile name used for encryption";
                                }

                            }
                            case key {

                                container key {
                                    description "Enter the key context";

                                    leaf type {
                                        type types-aa:http-field-encoding;
                                        description "Encoding type";
                                    }

                                    leaf value {
                                        type types-sros:encrypted-leaf {
                                            length "1..114";
                                        }
                                        description "Secret key for encrypting the field";
                                    }

                                } // container key

                            }
                        }
                    } // container encode

                } // list field

                container rat-type-enrichment {
                    description "Enter the rat-type-enrichment context";

                    list rat-type {
                        key "rat-type-name";
                        description "Enter the rat-type list instance";

                        leaf rat-type-name {
                            type types-aa:mobile-rat-type;
                            description "RAT type name";
                        }

                        leaf rat-string {
                            type types-sros:string-not-all-spaces {
                                length "1..31";
                            }
                            mandatory true;
                            description "Customised RAT type value";
                        }

                        leaf-list apply-groups {
                            type leafref {
                                path "../../../../../../groups/group/name";
                            }
                            max-elements 8;
                            ordered-by user;
                            description "Apply a configuration group at this level";
                        }

                        leaf-list apply-groups-exclude {
                            type leafref {
                                path "../../../../../../groups/group/name";
                            }
                            max-elements 8;
                            ordered-by user;
                            description "Exclude a configuration group at this level";
                        }

                    } // list rat-type

                } // container rat-type-enrichment

            } // list http-enrich

            list http-error-redirect {
                key "http-error-redirect-name";
                description "Enter the http-error-redirect list instance";

                leaf http-error-redirect-name {
                    type types-sros:named-item;
                    description "HTTP error redirect policy name";
                }

                leaf admin-state {
                    type types-sros:admin-state;
                    default "disable";
                    description "Administrative state of the HTTP error redirect object";
                }

                leaf description {
                    type types-sros:description;
                    description "Text description";
                }

                leaf http-host {
                    type types-sros:display-string;
                    description "HTTP host for the HTTP error redirect object";
                }

                leaf participant-id {
                    type types-sros:named-item;
                    description "Participant ID for the HTTP error redirect object";
                }

                leaf template {
                    type uint32;
                    description "Template ID for the HTTP error redirect object";
                }

                leaf-list apply-groups {
                    type leafref {
                        path "../../../../groups/group/name";
                    }
                    max-elements 8;
                    ordered-by user;
                    description "Apply a configuration group at this level";
                }

                leaf-list apply-groups-exclude {
                    type leafref {
                        path "../../../../groups/group/name";
                    }
                    max-elements 8;
                    ordered-by user;
                    description "Exclude a configuration group at this level";
                }

                list error-code {
                    key "error-code-value";
                    description "Enter the error-code list instance";

                    leaf error-code-value {
                        type uint32;
                        description "HTTP error code value for an HTTP error redirect";
                    }

                    leaf custom-message-size {
                        type uint32;
                        units "octets";
                        default "1024";
                        description "HTTP error redirect error code custom message size";
                    }

                    leaf-list apply-groups {
                        type leafref {
                            path "../../../../../groups/group/name";
                        }
                        max-elements 8;
                        ordered-by user;
                        description "Apply a configuration group at this level";
                    }

                    leaf-list apply-groups-exclude {
                        type leafref {
                            path "../../../../../groups/group/name";
                        }
                        max-elements 8;
                        ordered-by user;
                        description "Exclude a configuration group at this level";
                    }

                } // list error-code

            } // list http-error-redirect

            list http-notification {
                key "http-notification-name";
                description "Enter the http-notification list instance";

                leaf http-notification-name {
                    type types-sros:named-item;
                    description "HTTP notification policy name";
                }

                leaf admin-state {
                    type types-sros:admin-state;
                    default "disable";
                    description "Administrative state of the AA HTTP notification object";
                }

                leaf description {
                    type types-sros:description;
                    description "Text description";
                }

                leaf interval {
                    type types-aa:http-notif-interval;
                    description "Minimum HTTP response notification interval";
                }

                leaf script-url {
                    type types-sros:http-redirect-url;
                    description "Script URL inserted into the HTTP response";
                }

                leaf template {
                    type uint32;
                    description "Template ID for the AA HTTP notification object";
                }

                leaf-list apply-groups {
                    type leafref {
                        path "../../../../groups/group/name";
                    }
                    max-elements 8;
                    ordered-by user;
                    description "Apply a configuration group at this level";
                }

                leaf-list apply-groups-exclude {
                    type leafref {
                        path "../../../../groups/group/name";
                    }
                    max-elements 8;
                    ordered-by user;
                    description "Exclude a configuration group at this level";
                }

            } // list http-notification

            list http-redirect {
                key "http-redirect-name";
                description "Enter the http-redirect list instance";

                leaf http-redirect-name {
                    type types-sros:named-item;
                    description "HTTP redirect policy name";
                }

                leaf admin-state {
                    type types-sros:admin-state;
                    default "disable";
                    description "Administrative state of the AA HTTP redirect object";
                }

                leaf description {
                    type types-sros:description;
                    description "Text description";
                }

                leaf redirect-https {
                    type boolean;
                    default "false";
                    description "Enable HTTPS redirect";
                }

                leaf redirect-url {
                    type types-sros:http-redirect-url;
                    description "HTTP redirect URL";
                }

                leaf tcp-client-reset {
                    type boolean;
                    default "false";
                    description "Enable TCP client reset";
                }

                leaf template {
                    type uint32;
                    description "Template ID for the HTTP redirect object";
                }

                leaf-list apply-groups {
                    type leafref {
                        path "../../../../groups/group/name";
                    }
                    max-elements 8;
                    ordered-by user;
                    description "Apply a configuration group at this level";
                }

                leaf-list apply-groups-exclude {
                    type leafref {
                        path "../../../../groups/group/name";
                    }
                    max-elements 8;
                    ordered-by user;
                    description "Exclude a configuration group at this level";
                }

                container captive-redirect {
                    description "Enter the captive-redirect context";

                    leaf vlan-id {
                        type types-sros:vlan-id;
                        description "Captive redirect VLAN ID";
                    }

                } // container captive-redirect

            } // list http-redirect

            list tcp-optimizer {
                key "tcp-optimizer-name";
                description "Enter the tcp-optimizer list instance";

                leaf tcp-optimizer-name {
                    type types-sros:named-item;
                    description "TCP optimizer name";
                }

                leaf description {
                    type types-sros:description;
                    description "Text description";
                }

                leaf dack-timeout {
                    type uint32 {
                        range "200";
                    }
                    units "milliseconds";
                    description "Delayed acknowledgment timeout for client and server";
                }

                leaf initial-cwnd {
                    type uint32 {
                        range "1..256";
                    }
                    default "8";
                    description "Initial congestion window of the TCP optimizer";
                }

                leaf initial-ss-threshold {
                    type union {
                        type uint32 {
                            range "0..1000000";
                        }
                        type enumeration {
                            enum "auto"                         { value 1000001; }
                        }
                    }
                    units "kilobytes";
                    default "1000000";
                    description "Initial TCP Slow Start threshold for client and server";
                }

                leaf network-rtt-threshold {
                    type uint32 {
                        range "1..100";
                    }
                    units "milliseconds";
                    description "Network round trip time threshold";
                }

                leaf tcp-stack {
                    type types-aa:tcp-optimizer-stack;
                    description "TCP stack congestion control algorithm";
                }

                leaf-list apply-groups {
                    type leafref {
                        path "../../../../groups/group/name";
                    }
                    max-elements 8;
                    ordered-by user;
                    description "Apply a configuration group at this level";
                }

                leaf-list apply-groups-exclude {
                    type leafref {
                        path "../../../../groups/group/name";
                    }
                    max-elements 8;
                    ordered-by user;
                    description "Exclude a configuration group at this level";
                }

            } // list tcp-optimizer

            list url-list {
                key "url-list-name";
                description "Enter the url-list list instance";

                leaf url-list-name {
                    type types-sros:named-item;
                    description "URL list name";
                }

                leaf admin-state {
                    type types-sros:admin-state;
                    default "disable";
                    description "Administrative state of the URL list";
                }

                leaf description {
                    type types-sros:description;
                    description "Text description";
                }

                leaf file {
                    type types-sros:display-string {
                        length "1..180";
                    }
                    description "File name of the URL list on compact flash";
                }

                leaf host-expressions {
                    type boolean;
                    sros-ext:auto-restart-to-modify;
                    default "false";
                    description "Allow URL list to contain hostnames with wildcards";
                }

                leaf key {
                    type types-sros:encrypted-leaf {
                        length "1..115";
                    }
                    description "URL list decryption key";
                }

                leaf size {
                    type enumeration {
                        enum "standard"                     { value 1; }
                        enum "extended"                     { value 2; }
                    }
                    sros-ext:auto-restart-to-modify;
                    default "standard";
                    description "Size limit of the URL list";
                }

                leaf-list apply-groups {
                    type leafref {
                        path "../../../../groups/group/name";
                    }
                    max-elements 8;
                    ordered-by user;
                    description "Apply a configuration group at this level";
                }

                leaf-list apply-groups-exclude {
                    type leafref {
                        path "../../../../groups/group/name";
                    }
                    max-elements 8;
                    ordered-by user;
                    description "Exclude a configuration group at this level";
                }

            } // list url-list

            list url-filter {
                key "url-filter-name";
                description "Enter the url-filter list instance";

                leaf url-filter-name {
                    type types-sros:named-item;
                    description "URL filter name";
                }

                leaf admin-state {
                    type types-sros:admin-state;
                    default "disable";
                    description "Administrative state of the AA URL filter";
                }

                leaf description {
                    type types-sros:description;
                    description "Text description";
                }

                leaf apply-function-specific-behaviour {
                    type boolean;
                    default "false";
                    description "Use function-specific behavior for action or redirect";
                }

                leaf http-redirect {
                    type leafref {
                        path "../../http-redirect/http-redirect-name";
                    }
                    description "HTTP redirect for a blocked HTTP request";
                }

                leaf http-request-filtering {
                    type enumeration {
                        enum "all"                          { value 1; }
                        enum "first"                        { value 2; }
                    }
                    default "all";
                    description "HTTP filtering for all HTTP requests";
                }

                leaf-list apply-groups {
                    type leafref {
                        path "../../../../groups/group/name";
                    }
                    max-elements 8;
                    ordered-by user;
                    description "Apply a configuration group at this level";
                }

                leaf-list apply-groups-exclude {
                    type leafref {
                        path "../../../../groups/group/name";
                    }
                    max-elements 8;
                    ordered-by user;
                    description "Exclude a configuration group at this level";
                }

                container default-action {
                    description "Enter the default-action context";

                    choice action-choice {
                        default "block-all";
                        case allow {

                            leaf allow {
                                type empty;
                                description "Allow all requests as the default URL filter action";
                            }

                        }
                        case block-all {

                            leaf block-all {
                                type empty;
                                description "Block all requests as the default URL filter action";
                            }

                        }
                        case block-http-redirect {

                            leaf block-http-redirect {
                                type leafref {
                                    path "../../../http-redirect/http-redirect-name";
                                }
                                description "HTTP URL name for block and redirect request action";
                            }

                        }
                    }
                } // container default-action

                container local-filtering {
                    description "Enter the local-filtering context";

                    leaf allow-list {
                        type leafref {
                            path "../../../url-list/url-list-name";
                        }
                        sros-ext:auto-restart-to-modify;
                        description "Local filtering URL list for allowed URLs";
                    }

                    list deny-list {
                        key "url-list-name";
                        description "Enter the deny-list list instance";

                        leaf url-list-name {
                            type leafref {
                                path "../../../../url-list/url-list-name";
                            }
                            description "URL list name";
                        }

                        leaf http-redirect {
                            type leafref {
                                path "../../../../http-redirect/http-redirect-name";
                            }
                            description "HTTP redirect object applied to blocked HTTP requests";
                        }

                        leaf-list apply-groups {
                            type leafref {
                                path "../../../../../../groups/group/name";
                            }
                            max-elements 8;
                            ordered-by user;
                            description "Apply a configuration group at this level";
                        }

                        leaf-list apply-groups-exclude {
                            type leafref {
                                path "../../../../../../groups/group/name";
                            }
                            max-elements 8;
                            ordered-by user;
                            description "Exclude a configuration group at this level";
                        }

                        container default-action {
                            description "Enter the default-action context";

                            choice action-choice {
                                default "block-all";
                                case allow {

                                    leaf allow {
                                        type empty;
                                        description "Allow all requests as the default action";
                                    }

                                }
                                case block-all {

                                    leaf block-all {
                                        type empty;
                                        description "Block all requests as the default action";
                                    }

                                }
                                case block-http-redirect {

                                    leaf block-http-redirect {
                                        type leafref {
                                            path "../../../../../http-redirect/http-redirect-name";
                                        }
                                        description "HTTP URL for redirection when URL filter cannot be used";
                                    }

                                }
                            }
                        } // container default-action

                    } // list deny-list

                } // container local-filtering

                container icap {
                    description "Enter the icap context";

                    leaf custom-x-header {
                        type types-sros:named-item;
                        description "Custom x-header field name to include in ICAP requests";
                    }

                    leaf http-redirect {
                        type leafref {
                            path "../../../http-redirect/http-redirect-name";
                        }
                        description "HTTP redirect object used when ICAP blocks HTTP request";
                    }

                    leaf vlan-id {
                        type types-sros:vlan-id;
                        sros-ext:auto-restart-to-modify;
                        description "VLAN ID of the ICAP server service port";
                    }

                    container default-action {
                        description "Enter the default-action context";

                        choice action-choice {
                            default "block-all";
                            case allow {

                                leaf allow {
                                    type empty;
                                    description "Allow all requests as the default action";
                                }

                            }
                            case block-all {

                                leaf block-all {
                                    type empty;
                                    description "Block all requests as the default action";
                                }

                            }
                            case block-http-redirect {

                                leaf block-http-redirect {
                                    type leafref {
                                        path "../../../../http-redirect/http-redirect-name";
                                    }
                                    description "HTTP URL for redirection when URL filter cannot be used";
                                }

                            }
                        }
                    } // container default-action

                    list server {
                        key "ip-address port";
                        description "Enter the server list instance";

                        leaf ip-address {
                            type types-sros:ip-unicast-address;
                            description "ICAP server IP address";
                        }

                        leaf port {
                            type types-sros:tcp-udp-port-non-zero;
                            description "ICAP server port";
                        }

                        leaf admin-state {
                            type types-sros:admin-state;
                            default "disable";
                            description "Administrative state of this URL filter ICAP server";
                        }

                        leaf description {
                            type types-sros:description;
                            description "Text description";
                        }

                        leaf-list apply-groups {
                            type leafref {
                                path "../../../../../../groups/group/name";
                            }
                            max-elements 8;
                            ordered-by user;
                            description "Apply a configuration group at this level";
                        }

                        leaf-list apply-groups-exclude {
                            type leafref {
                                path "../../../../../../groups/group/name";
                            }
                            max-elements 8;
                            ordered-by user;
                            description "Exclude a configuration group at this level";
                        }

                    } // list server

                } // container icap

                container web-service {
                    description "Enter the web-service context";

                    leaf classifier {
                        type types-aa:web-serv-classifier-id;
                        sros-ext:auto-restart-to-modify;
                        description "Web service classifier";
                    }

                    leaf category-set {
                        type uint32 {
                            range "1..65535";
                        }
                        sros-ext:auto-restart-to-modify;
                        description "Web service category ID";
                    }

                    leaf default-profile {
                        type leafref {
                            path "../profile/profile-name";
                        }
                        sros-ext:auto-restart-to-modify;
                        description "Web service default profile";
                    }

                    leaf dns-server {
                        type types-sros:ip-unicast-address;
                        sros-ext:auto-restart-to-modify;
                        description "Web service DNS server";
                    }

                    leaf fqdn {
                        type types-sros:display-string;
                        sros-ext:auto-restart-to-modify;
                        description "Web service fully qualified domain name";
                    }

                    leaf http-redirect {
                        type leafref {
                            path "../../../http-redirect/http-redirect-name";
                        }
                        description "Web service HTTP redirect";
                    }

                    leaf vlan-id {
                        type types-sros:vlan-id;
                        sros-ext:auto-restart-to-modify;
                        description "Web-service VLAN ID";
                    }

                    container default-action {
                        description "Enter the default-action context";

                        choice action-choice {
                            default "block-all";
                            case allow {

                                leaf allow {
                                    type empty;
                                    description "Allow all requests as the default action";
                                }

                            }
                            case block-all {

                                leaf block-all {
                                    type empty;
                                    description "Block all requests as the default action";
                                }

                            }
                            case block-http-redirect {

                                leaf block-http-redirect {
                                    type leafref {
                                        path "../../../../http-redirect/http-redirect-name";
                                    }
                                    description "HTTP URL for redirection when the web service is unavailable";
                                }

                            }
                        }
                    } // container default-action

                    container classification-overrides {
                        description "Enter the classification-overrides context";

                        list entry {
                            key "entry-id";
                            max-elements 200;
                            description "Enter the entry list instance";

                            leaf entry-id {
                                type uint32 {
                                    range "1..65535";
                                }
                                description "Classification override entry ID";
                            }

                            leaf expression {
                                type types-sros:display-string;
                                mandatory true;
                                description "Hostname of the configured override category";
                            }

                            leaf category-name {
                                type types-sros:named-item;
                                description "Web service category name";
                            }

                            leaf-list apply-groups {
                                type leafref {
                                    path "../../../../../../../groups/group/name";
                                }
                                max-elements 8;
                                ordered-by user;
                                description "Apply a configuration group at this level";
                            }

                            leaf-list apply-groups-exclude {
                                type leafref {
                                    path "../../../../../../../groups/group/name";
                                }
                                max-elements 8;
                                ordered-by user;
                                description "Exclude a configuration group at this level";
                            }

                        } // list entry

                    } // container classification-overrides

                    list profile {
                        key "profile-name";
                        max-elements 8;
                        description "Enter the profile list instance";

                        leaf profile-name {
                            type types-sros:named-item;
                            description "Web service profile name";
                        }

                        leaf description {
                            type types-sros:description;
                            description "Text description";
                        }

                        leaf-list apply-groups {
                            type leafref {
                                path "../../../../../../groups/group/name";
                            }
                            max-elements 8;
                            ordered-by user;
                            description "Apply a configuration group at this level";
                        }

                        leaf-list apply-groups-exclude {
                            type leafref {
                                path "../../../../../../groups/group/name";
                            }
                            max-elements 8;
                            ordered-by user;
                            description "Exclude a configuration group at this level";
                        }

                        container block {
                            description "Enter the block context";

                            list category {
                                key "category-name";
                                description "Add a list entry for category";

                                leaf category-name {
                                    type types-aa:web-serv-category-name;
                                    description "Web service profile category name to be blocked";
                                }

                            } // list category

                        } // container block

                    } // list profile

                } // container web-service

            } // list url-filter

            container policer {
                description "Enter the policer context";

                list anl-bandwidth-policer {
                    key "policer-name";
                    description "Enter the anl-bandwidth-policer list instance";

                    leaf policer-name {
                        type types-sros:named-item;
                        description "Policer name";
                    }

                    leaf action {
                        type types-aa:policer-action;
                        description "Action for packets violating configured policer rate";
                    }

                    leaf description {
                        type types-sros:description;
                        description "Text description";
                    }

                    leaf mbs {
                        type types-aa:policer-burst-size;
                        description "ANL bandwidth policer maximum burst size";
                    }

                    leaf rate-percentage {
                        type int32 {
                            range "0..200";
                        }
                        description "Rate used by Access-Network-Location policers";
                    }

                    leaf rate-percentage-stage-2 {
                        type int32 {
                            range "0..200";
                        }
                        description "Rate used by Access-Network-Location policers";
                    }

                    leaf-list apply-groups {
                        type leafref {
                            path "../../../../../groups/group/name";
                        }
                        max-elements 8;
                        ordered-by user;
                        description "Apply a configuration group at this level";
                    }

                    leaf-list apply-groups-exclude {
                        type leafref {
                            path "../../../../../groups/group/name";
                        }
                        max-elements 8;
                        ordered-by user;
                        description "Exclude a configuration group at this level";
                    }

                    container adaptation-rule {
                        description "Enter the adaptation-rule context";

                        leaf pir {
                            type types-qos:adaptation-rule;
                            default "closest";
                            description "Peak information rate value for the adaptation rule";
                        }

                    } // container adaptation-rule

                } // list anl-bandwidth-policer

                list dual-bucket-bandwidth-policer {
                    key "policer-name";
                    description "Enter the dual-bucket-bandwidth-policer list instance";

                    leaf policer-name {
                        type types-sros:named-item;
                        description "Policer name";
                    }

                    leaf mbs {
                        type types-aa:policer-burst-size;
                        description "Bandwidth policer maximum burst size";
                    }

                    leaf pir {
                        type types-aa:policer-ir;
                        default "max";
                        description "Peak information rate value for the bandwidth policer";
                    }

                    leaf cbs {
                        type types-aa:policer-burst-size;
                        description "Committed burst size when in congested state";
                    }

                    leaf cir {
                        type types-aa:policer-cir;
                        description "Committed information rate value for the policer";
                    }

                    leaf description {
                        type types-sros:description;
                        description "Text description";
                    }

                    leaf-list apply-groups {
                        type leafref {
                            path "../../../../../groups/group/name";
                        }
                        max-elements 8;
                        ordered-by user;
                        description "Apply a configuration group at this level";
                    }

                    leaf-list apply-groups-exclude {
                        type leafref {
                            path "../../../../../groups/group/name";
                        }
                        max-elements 8;
                        ordered-by user;
                        description "Exclude a configuration group at this level";
                    }

                    container adaptation-rule {
                        description "Enter the adaptation-rule context";

                        leaf pir {
                            type types-qos:adaptation-rule;
                            default "closest";
                            description "Peak information rate value for the adaptation rule";
                        }

                        leaf cir {
                            type types-qos:adaptation-rule;
                            default "closest";
                            description "Committed information rate value for adaptation rule";
                        }

                    } // container adaptation-rule

                    container congestion-override {
                        description "Enter the congestion-override context";

                        leaf mbs {
                            type types-aa:policer-burst-size;
                            description "Maximum burst size when in a congested state";
                        }

                        leaf pir {
                            type types-aa:policer-ir;
                            description "Peak information rate value for the congestion override";
                        }

                        leaf cbs {
                            type types-aa:policer-burst-size;
                            description "Committed burst size in a congested stage 2 state";
                        }

                        leaf cir {
                            type types-aa:policer-cir;
                            description "Committed information rate value for the policer override";
                        }

                    } // container congestion-override

                    container congestion-override-stage-2 {
                        description "Enter the congestion-override-stage-2 context";

                        leaf mbs {
                            type types-aa:policer-burst-size;
                            description "Maximum burst size when in a congested state";
                        }

                        leaf pir {
                            type types-aa:policer-ir;
                            description "Peak information rate value for the congestion override";
                        }

                        leaf cbs {
                            type types-aa:policer-burst-size;
                            description "Committed burst size in a congested stage 2 state";
                        }

                        leaf cir {
                            type types-aa:policer-cir;
                            description "Committed information rate value for the policer override";
                        }

                    } // container congestion-override-stage-2

                    list time-of-day-override {
                        key "tod-override-id";
                        max-elements 8;
                        description "Enter the time-of-day-override list instance";

                        leaf tod-override-id {
                            type int32 {
                                range "1..255";
                            }
                            description "ID for time of day override";
                        }

                        leaf admin-state {
                            type types-sros:admin-state;
                            default "disable";
                            description "Administrative state of this time of day policer";
                        }

                        leaf description {
                            type types-sros:description;
                            description "Text description";
                        }

                        leaf cbs {
                            type types-aa:policer-burst-size;
                            description "Committed burst size for time of day override policer";
                        }

                        leaf cir {
                            type types-aa:policer-cir;
                            default "0";
                            description "Committed information rate for time of day override";
                        }

                        leaf mbs {
                            type types-aa:policer-burst-size;
                            description "Maximum burst size for the policer time of day override";
                        }

                        leaf pir {
                            type types-aa:policer-ir;
                            default "max";
                            description "Peak information rate value for the time of day override";
                        }

                        leaf-list apply-groups {
                            type leafref {
                                path "../../../../../../groups/group/name";
                            }
                            max-elements 8;
                            ordered-by user;
                            description "Apply a configuration group at this level";
                        }

                        leaf-list apply-groups-exclude {
                            type leafref {
                                path "../../../../../../groups/group/name";
                            }
                            max-elements 8;
                            ordered-by user;
                            description "Exclude a configuration group at this level";
                        }

                        container time-range {
                            description "Enter the time-range context";

                            choice daily-weekly {
                                case daily {

                                    container daily {
                                        presence "Enable the daily context";
                                        description "Enter the daily context";

                                        leaf start {
                                            type types-aa:policer-start-time;
                                            mandatory true;
                                            description "Daily start time";
                                        }

                                        leaf end {
                                            type types-aa:policer-end-time;
                                            mandatory true;
                                            description "Daily end time";
                                        }

                                        choice days {
                                            default "all-days";
                                            case all-days {

                                                leaf all-days {
                                                    type empty;
                                                    description "Enable policer override on every day";
                                                }

                                            }
                                            case some-week-days {

                                                leaf-list on {
                                                    type enumeration {
                                                        enum "sunday"                       { value 1; }
                                                        enum "monday"                       { value 2; }
                                                        enum "tuesday"                      { value 3; }
                                                        enum "wednesday"                    { value 4; }
                                                        enum "thursday"                     { value 5; }
                                                        enum "friday"                       { value 6; }
                                                        enum "saturday"                     { value 7; }
                                                    }
                                                    max-elements 6;
                                                    description "Policer override on selected days";
                                                }

                                            }
                                        }
                                    } // container daily

                                }
                                case weekly {

                                    container weekly {
                                        presence "Enable the weekly context";
                                        description "Enter the weekly context";

                                        container start {
                                            presence "Enable the start context";
                                            description "Enter the start context";

                                            leaf day {
                                                type types-aa:day-of-week;
                                                mandatory true;
                                                description "Weekly start day";
                                            }

                                            leaf time {
                                                type types-aa:policer-start-time;
                                                mandatory true;
                                                description "Weekly start time";
                                            }

                                        } // container start

                                        container end {
                                            presence "Enable the end context";
                                            description "Enter the end context";

                                            leaf day {
                                                type types-aa:day-of-week;
                                                mandatory true;
                                                description "Weekly end day";
                                            }

                                            leaf time {
                                                type types-aa:policer-end-time;
                                                mandatory true;
                                                description "Weekly end time";
                                            }

                                        } // container end

                                    } // container weekly

                                }
                            }
                        } // container time-range

                    } // list time-of-day-override

                } // list dual-bucket-bandwidth-policer

                list flow-count-limit-policer {
                    key "policer-name";
                    description "Enter the flow-count-limit-policer list instance";

                    leaf policer-name {
                        type types-sros:named-item;
                        description "Policer name";
                    }

                    leaf description {
                        type types-sros:description;
                        description "Text description";
                    }

                    leaf granularity {
                        type types-aa:policer-granularity;
                        sros-ext:immutable;
                        mandatory true;
                        description "Policer granularity";
                    }

                    leaf limit-gtp-flows {
                        type boolean;
                        sros-ext:immutable;
                        default "false";
                        description "Limit concurrent GTP flows";
                    }

                    leaf peak-flow-count {
                        type types-aa:policer-flow-count-limit;
                        description "Peak flow count limit";
                    }

                    leaf action {
                        type types-aa:policer-action;
                        description "Action for packets violating configured policer rate";
                    }

                    leaf-list apply-groups {
                        type leafref {
                            path "../../../../../groups/group/name";
                        }
                        max-elements 8;
                        ordered-by user;
                        description "Apply a configuration group at this level";
                    }

                    leaf-list apply-groups-exclude {
                        type leafref {
                            path "../../../../../groups/group/name";
                        }
                        max-elements 8;
                        ordered-by user;
                        description "Exclude a configuration group at this level";
                    }

                    list time-of-day-override {
                        key "tod-override-id";
                        max-elements 8;
                        description "Enter the time-of-day-override list instance";

                        leaf tod-override-id {
                            type int32 {
                                range "1..255";
                            }
                            description "ID for time of day override";
                        }

                        leaf admin-state {
                            type types-sros:admin-state;
                            default "disable";
                            description "Administrative state of this time of day policer";
                        }

                        leaf description {
                            type types-sros:description;
                            description "Text description";
                        }

                        leaf peak-flow-count {
                            type types-aa:policer-flow-count-limit;
                            description "Peak flow count limit";
                        }

                        leaf-list apply-groups {
                            type leafref {
                                path "../../../../../../groups/group/name";
                            }
                            max-elements 8;
                            ordered-by user;
                            description "Apply a configuration group at this level";
                        }

                        leaf-list apply-groups-exclude {
                            type leafref {
                                path "../../../../../../groups/group/name";
                            }
                            max-elements 8;
                            ordered-by user;
                            description "Exclude a configuration group at this level";
                        }

                        container time-range {
                            description "Enter the time-range context";

                            choice daily-weekly {
                                case daily {

                                    container daily {
                                        presence "Enable the daily context";
                                        description "Enter the daily context";

                                        leaf start {
                                            type types-aa:policer-start-time;
                                            mandatory true;
                                            description "Daily start time";
                                        }

                                        leaf end {
                                            type types-aa:policer-end-time;
                                            mandatory true;
                                            description "Daily end time";
                                        }

                                        choice days {
                                            default "all-days";
                                            case all-days {

                                                leaf all-days {
                                                    type empty;
                                                    description "Enable policer override on every day";
                                                }

                                            }
                                            case some-week-days {

                                                leaf-list on {
                                                    type enumeration {
                                                        enum "sunday"                       { value 1; }
                                                        enum "monday"                       { value 2; }
                                                        enum "tuesday"                      { value 3; }
                                                        enum "wednesday"                    { value 4; }
                                                        enum "thursday"                     { value 5; }
                                                        enum "friday"                       { value 6; }
                                                        enum "saturday"                     { value 7; }
                                                    }
                                                    max-elements 6;
                                                    description "Policer override on selected days";
                                                }

                                            }
                                        }
                                    } // container daily

                                }
                                case weekly {

                                    container weekly {
                                        presence "Enable the weekly context";
                                        description "Enter the weekly context";

                                        container start {
                                            presence "Enable the start context";
                                            description "Enter the start context";

                                            leaf day {
                                                type types-aa:day-of-week;
                                                mandatory true;
                                                description "Weekly start day";
                                            }

                                            leaf time {
                                                type types-aa:policer-start-time;
                                                mandatory true;
                                                description "Weekly start time";
                                            }

                                        } // container start

                                        container end {
                                            presence "Enable the end context";
                                            description "Enter the end context";

                                            leaf day {
                                                type types-aa:day-of-week;
                                                mandatory true;
                                                description "Weekly end day";
                                            }

                                            leaf time {
                                                type types-aa:policer-end-time;
                                                mandatory true;
                                                description "Weekly end time";
                                            }

                                        } // container end

                                    } // container weekly

                                }
                            }
                        } // container time-range

                    } // list time-of-day-override

                } // list flow-count-limit-policer

                list flow-setup-rate-policer {
                    key "policer-name";
                    description "Enter the flow-setup-rate-policer list instance";

                    leaf policer-name {
                        type types-sros:named-item;
                        description "Policer name";
                    }

                    leaf description {
                        type types-sros:description;
                        description "Text description";
                    }

                    leaf granularity {
                        type types-aa:policer-granularity;
                        sros-ext:immutable;
                        mandatory true;
                        description "Policer granularity";
                    }

                    leaf flow-setup-rate-burst-size {
                        type types-aa:policer-flow-burst-size;
                        description "Maximum flow setup rate burst size";
                    }

                    leaf peak-flow-setup-rate {
                        type types-aa:policer-flow-rate;
                        description "Peak flow setup rate";
                    }

                    leaf action {
                        type types-aa:policer-action;
                        description "Action for packets violating configured policer rate";
                    }

                    leaf-list apply-groups {
                        type leafref {
                            path "../../../../../groups/group/name";
                        }
                        max-elements 8;
                        ordered-by user;
                        description "Apply a configuration group at this level";
                    }

                    leaf-list apply-groups-exclude {
                        type leafref {
                            path "../../../../../groups/group/name";
                        }
                        max-elements 8;
                        ordered-by user;
                        description "Exclude a configuration group at this level";
                    }

                    container adaptation-rule {
                        description "Enter the adaptation-rule context";

                        leaf peak-flow-setup-rate {
                            type types-qos:adaptation-rule;
                            default "closest";
                            description "Peak flow setup rate adaptation rule";
                        }

                    } // container adaptation-rule

                    list time-of-day-override {
                        key "tod-override-id";
                        max-elements 8;
                        description "Enter the time-of-day-override list instance";

                        leaf tod-override-id {
                            type int32 {
                                range "1..255";
                            }
                            description "ID for time of day override";
                        }

                        leaf admin-state {
                            type types-sros:admin-state;
                            default "disable";
                            description "Administrative state of this time of day policer";
                        }

                        leaf description {
                            type types-sros:description;
                            description "Text description";
                        }

                        leaf flow-setup-rate-burst-size {
                            type types-aa:policer-flow-burst-size;
                            description "Maximum flow setup rate burst size";
                        }

                        leaf peak-flow-setup-rate {
                            type types-aa:policer-flow-rate;
                            description "Peak flow setup rate";
                        }

                        leaf-list apply-groups {
                            type leafref {
                                path "../../../../../../groups/group/name";
                            }
                            max-elements 8;
                            ordered-by user;
                            description "Apply a configuration group at this level";
                        }

                        leaf-list apply-groups-exclude {
                            type leafref {
                                path "../../../../../../groups/group/name";
                            }
                            max-elements 8;
                            ordered-by user;
                            description "Exclude a configuration group at this level";
                        }

                        container time-range {
                            description "Enter the time-range context";

                            choice daily-weekly {
                                case daily {

                                    container daily {
                                        presence "Enable the daily context";
                                        description "Enter the daily context";

                                        leaf start {
                                            type types-aa:policer-start-time;
                                            mandatory true;
                                            description "Daily start time";
                                        }

                                        leaf end {
                                            type types-aa:policer-end-time;
                                            mandatory true;
                                            description "Daily end time";
                                        }

                                        choice days {
                                            default "all-days";
                                            case all-days {

                                                leaf all-days {
                                                    type empty;
                                                    description "Enable policer override on every day";
                                                }

                                            }
                                            case some-week-days {

                                                leaf-list on {
                                                    type enumeration {
                                                        enum "sunday"                       { value 1; }
                                                        enum "monday"                       { value 2; }
                                                        enum "tuesday"                      { value 3; }
                                                        enum "wednesday"                    { value 4; }
                                                        enum "thursday"                     { value 5; }
                                                        enum "friday"                       { value 6; }
                                                        enum "saturday"                     { value 7; }
                                                    }
                                                    max-elements 6;
                                                    description "Policer override on selected days";
                                                }

                                            }
                                        }
                                    } // container daily

                                }
                                case weekly {

                                    container weekly {
                                        presence "Enable the weekly context";
                                        description "Enter the weekly context";

                                        container start {
                                            presence "Enable the start context";
                                            description "Enter the start context";

                                            leaf day {
                                                type types-aa:day-of-week;
                                                mandatory true;
                                                description "Weekly start day";
                                            }

                                            leaf time {
                                                type types-aa:policer-start-time;
                                                mandatory true;
                                                description "Weekly start time";
                                            }

                                        } // container start

                                        container end {
                                            presence "Enable the end context";
                                            description "Enter the end context";

                                            leaf day {
                                                type types-aa:day-of-week;
                                                mandatory true;
                                                description "Weekly end day";
                                            }

                                            leaf time {
                                                type types-aa:policer-end-time;
                                                mandatory true;
                                                description "Weekly end time";
                                            }

                                        } // container end

                                    } // container weekly

                                }
                            }
                        } // container time-range

                    } // list time-of-day-override

                } // list flow-setup-rate-policer

                list single-bucket-bandwidth-policer {
                    key "policer-name";
                    description "Enter the single-bucket-bandwidth-policer list instance";

                    leaf policer-name {
                        type types-sros:named-item;
                        description "Policer name";
                    }

                    leaf description {
                        type types-sros:description;
                        description "Text description";
                    }

                    leaf granularity {
                        type types-aa:policer-granularity;
                        sros-ext:immutable;
                        mandatory true;
                        description "Policer granularity";
                    }

                    leaf mbs {
                        type types-aa:policer-burst-size;
                        description "Bandwidth policer maximum burst size";
                    }

                    leaf pir {
                        type types-aa:policer-ir;
                        default "max";
                        description "Peak information rate value for the bandwidth policer";
                    }

                    leaf action {
                        type types-aa:policer-action;
                        description "Action for packets violating configured policer rate";
                    }

                    leaf-list apply-groups {
                        type leafref {
                            path "../../../../../groups/group/name";
                        }
                        max-elements 8;
                        ordered-by user;
                        description "Apply a configuration group at this level";
                    }

                    leaf-list apply-groups-exclude {
                        type leafref {
                            path "../../../../../groups/group/name";
                        }
                        max-elements 8;
                        ordered-by user;
                        description "Exclude a configuration group at this level";
                    }

                    container adaptation-rule {
                        description "Enter the adaptation-rule context";

                        leaf pir {
                            type types-qos:adaptation-rule;
                            default "closest";
                            description "Peak information rate value for the adaptation rule";
                        }

                    } // container adaptation-rule

                    container congestion-override {
                        when "../granularity = 'subscriber'";
                        description "Enter the congestion-override context";

                        leaf mbs {
                            type types-aa:policer-burst-size;
                            description "Maximum burst size when in a congested state";
                        }

                        leaf pir {
                            type types-aa:policer-ir;
                            description "Peak information rate value for the congestion override";
                        }

                    } // container congestion-override

                    container congestion-override-stage-2 {
                        when "../granularity = 'subscriber'";
                        description "Enter the congestion-override-stage-2 context";

                        leaf mbs {
                            type types-aa:policer-burst-size;
                            description "Maximum burst size when in a congested state";
                        }

                        leaf pir {
                            type types-aa:policer-ir;
                            description "Peak information rate value for the congestion override";
                        }

                    } // container congestion-override-stage-2

                    list time-of-day-override {
                        key "tod-override-id";
                        max-elements 8;
                        description "Enter the time-of-day-override list instance";

                        leaf tod-override-id {
                            type int32 {
                                range "1..255";
                            }
                            description "ID for time of day override";
                        }

                        leaf admin-state {
                            type types-sros:admin-state;
                            default "disable";
                            description "Administrative state of this time of day policer";
                        }

                        leaf description {
                            type types-sros:description;
                            description "Text description";
                        }

                        leaf mbs {
                            type types-aa:policer-burst-size;
                            description "Bandwidth policer maximum burst size for time of day override";
                        }

                        leaf pir {
                            type types-aa:policer-ir;
                            default "max";
                            description "Peak information rate value for time of day override";
                        }

                        leaf-list apply-groups {
                            type leafref {
                                path "../../../../../../groups/group/name";
                            }
                            max-elements 8;
                            ordered-by user;
                            description "Apply a configuration group at this level";
                        }

                        leaf-list apply-groups-exclude {
                            type leafref {
                                path "../../../../../../groups/group/name";
                            }
                            max-elements 8;
                            ordered-by user;
                            description "Exclude a configuration group at this level";
                        }

                        container time-range {
                            description "Enter the time-range context";

                            choice daily-weekly {
                                case daily {

                                    container daily {
                                        presence "Enable the daily context";
                                        description "Enter the daily context";

                                        leaf start {
                                            type types-aa:policer-start-time;
                                            mandatory true;
                                            description "Daily start time";
                                        }

                                        leaf end {
                                            type types-aa:policer-end-time;
                                            mandatory true;
                                            description "Daily end time";
                                        }

                                        choice days {
                                            default "all-days";
                                            case all-days {

                                                leaf all-days {
                                                    type empty;
                                                    description "Enable policer override on every day";
                                                }

                                            }
                                            case some-week-days {

                                                leaf-list on {
                                                    type enumeration {
                                                        enum "sunday"                       { value 1; }
                                                        enum "monday"                       { value 2; }
                                                        enum "tuesday"                      { value 3; }
                                                        enum "wednesday"                    { value 4; }
                                                        enum "thursday"                     { value 5; }
                                                        enum "friday"                       { value 6; }
                                                        enum "saturday"                     { value 7; }
                                                    }
                                                    max-elements 6;
                                                    description "Policer override on selected days";
                                                }

                                            }
                                        }
                                    } // container daily

                                }
                                case weekly {

                                    container weekly {
                                        presence "Enable the weekly context";
                                        description "Enter the weekly context";

                                        container start {
                                            presence "Enable the start context";
                                            description "Enter the start context";

                                            leaf day {
                                                type types-aa:day-of-week;
                                                mandatory true;
                                                description "Weekly start day";
                                            }

                                            leaf time {
                                                type types-aa:policer-start-time;
                                                mandatory true;
                                                description "Weekly start time";
                                            }

                                        } // container start

                                        container end {
                                            presence "Enable the end context";
                                            description "Enter the end context";

                                            leaf day {
                                                type types-aa:day-of-week;
                                                mandatory true;
                                                description "Weekly end day";
                                            }

                                            leaf time {
                                                type types-aa:policer-end-time;
                                                mandatory true;
                                                description "Weekly end time";
                                            }

                                        } // container end

                                    } // container weekly

                                }
                            }
                        } // container time-range

                    } // list time-of-day-override

                } // list single-bucket-bandwidth-policer

            } // container policer

            list partition {
                key "aa-partition-id";
                description "Enter the partition list instance";

                leaf aa-partition-id {
                    type types-aa:aa-grp-part-id;
                    description "Partition ID within the AA group";
                }

                leaf description {
                    type types-sros:description;
                    description "Text description";
                }

                leaf aa-sub-remote {
                    type boolean;
                    default "false";
                    description "Reverse subscriber traffic direction";
                }

                leaf aqp-initial-lookup {
                    type boolean;
                    default "false";
                    description "Enable AQP initial lookup";
                }

                leaf http-match-all-requests {
                    type boolean;
                    default "false";
                    description "Enable HTTP matching for all requests for an expression";
                }

                leaf http-x-online-host {
                    type boolean;
                    default "false";
                    description "Enable X-Online-Host header field";
                }

                leaf shallow-inspection {
                    type boolean;
                    default "false";
                    description "Enable shallow inspection";
                }

                leaf-list apply-groups {
                    type leafref {
                        path "../../../../groups/group/name";
                    }
                    max-elements 8;
                    ordered-by user;
                    description "Apply a configuration group at this level";
                }

                leaf-list apply-groups-exclude {
                    type leafref {
                        path "../../../../groups/group/name";
                    }
                    max-elements 8;
                    ordered-by user;
                    description "Exclude a configuration group at this level";
                }

                container aa-sub-congestion-detection {
                    description "Enter the aa-sub-congestion-detection context";

                    leaf admin-state {
                        type types-sros:admin-state;
                        default "disable";
                        description "Administrative state of congestion detection";
                    }

                    leaf rtt-threshold {
                        type union {
                            type uint32 {
                                range "1..500";
                            }
                            type enumeration {
                                enum "not-applicable"               { value 0; }
                            }
                        }
                        units "milliseconds";
                        default "173";
                        description "Round trip time congestion threshold";
                    }

                    leaf rtt-threshold-tolerance {
                        type uint32 {
                            range "0..100";
                        }
                        units "percent";
                        default "50";
                        description "RTT threshold tolerance for congestion detection";
                    }

                    leaf-list apply-groups {
                        type leafref {
                            path "../../../../../groups/group/name";
                        }
                        max-elements 8;
                        ordered-by user;
                        description "Apply a configuration group at this level";
                    }

                    leaf-list apply-groups-exclude {
                        type leafref {
                            path "../../../../../groups/group/name";
                        }
                        max-elements 8;
                        ordered-by user;
                        description "Exclude a configuration group at this level";
                    }

                    list rat-type {
                        key "rat-type-name";
                        description "Enter the rat-type list instance";

                        leaf rat-type-name {
                            type types-aa:mobile-rat-type;
                            description "Mobile radio access technology (RAT) type";
                        }

                        leaf rtt-threshold {
                            type union {
                                type int32 {
                                    range "1..500";
                                }
                                type enumeration {
                                    enum "not-applicable"               { value 0; }
                                }
                            }
                            units "milliseconds";
                            mandatory true;
                            description "Round trip time congestion threshold for a RAT type";
                        }

                        leaf-list apply-groups {
                            type leafref {
                                path "../../../../../../groups/group/name";
                            }
                            max-elements 8;
                            ordered-by user;
                            description "Apply a configuration group at this level";
                        }

                        leaf-list apply-groups-exclude {
                            type leafref {
                                path "../../../../../../groups/group/name";
                            }
                            max-elements 8;
                            ordered-by user;
                            description "Exclude a configuration group at this level";
                        }

                    } // list rat-type

                } // container aa-sub-congestion-detection

                container access-network-location {
                    description "Enter the access-network-location context";

                    list source {
                        key "source-type";
                        max-elements 1;
                        description "Enter the source list instance";

                        leaf source-type {
                            type enumeration {
                                enum "mobile-3g"                    { value 0; }
                                enum "access-point"                 { value 1; }
                                enum "uli-3gpp"                     { value 2; }
                            }
                            description "Access network location source";
                        }

                        leaf source-level {
                            type enumeration {
                                enum "cell"                         { value 1; }
                                enum "transport-network-link"       { value 2; }
                                enum "mac-vlan"                     { value 3; }
                            }
                            sros-ext:immutable;
                            default "cell";
                            description "Access network location source level";
                        }

                        leaf rtt-threshold {
                            type union {
                                type uint32 {
                                    range "1..500";
                                }
                                type enumeration {
                                    enum "not-applicable"               { value 0; }
                                }
                            }
                            units "milliseconds";
                            default "173";
                            description "Source round trip time congestion threshold";
                        }

                        leaf rtt-threshold-tolerance {
                            type uint32 {
                                range "0..100";
                            }
                            units "percent";
                            default "50";
                            description "Source round trip time congestion threshold tolerance";
                        }

                        leaf-list apply-groups {
                            type leafref {
                                path "../../../../../../groups/group/name";
                            }
                            max-elements 8;
                            ordered-by user;
                            description "Apply a configuration group at this level";
                        }

                        leaf-list apply-groups-exclude {
                            type leafref {
                                path "../../../../../../groups/group/name";
                            }
                            max-elements 8;
                            ordered-by user;
                            description "Exclude a configuration group at this level";
                        }

                        list rat-type {
                            key "rat-type-name";
                            description "Enter the rat-type list instance";

                            leaf rat-type-name {
                                type types-aa:mobile-rat-type;
                                description "Access network location RAT type";
                            }

                            leaf rtt-threshold {
                                type union {
                                    type int32 {
                                        range "1..500";
                                    }
                                    type enumeration {
                                        enum "not-applicable"               { value 0; }
                                    }
                                }
                                units "milliseconds";
                                mandatory true;
                                description "RTT congestion threshold for a RAT type";
                            }

                            leaf-list apply-groups {
                                type leafref {
                                    path "../../../../../../../groups/group/name";
                                }
                                max-elements 8;
                                ordered-by user;
                                description "Apply a configuration group at this level";
                            }

                            leaf-list apply-groups-exclude {
                                type leafref {
                                    path "../../../../../../../groups/group/name";
                                }
                                max-elements 8;
                                ordered-by user;
                                description "Exclude a configuration group at this level";
                            }

                        } // list rat-type

                    } // list source

                } // container access-network-location

                list event-log {
                    key "event-log-name";
                    description "Enter the event-log list instance";

                    leaf event-log-name {
                        type types-sros:named-item;
                        description "Partition event log name";
                    }

                    leaf admin-state {
                        type types-sros:admin-state;
                        default "disable";
                        description "Administrative state of the event log";
                    }

                    leaf buffer-type {
                        type enumeration {
                            enum "linear"                       { value 1; }
                            enum "circular"                     { value 2; }
                            enum "syslog"                       { value 3; }
                        }
                        sros-ext:auto-restart-to-modify;
                        default "linear";
                        description "Event log buffer type";
                    }

                    leaf max-entries {
                        type uint32 {
                            range "1..100000";
                        }
                        sros-ext:auto-restart-to-modify;
                        default "500";
                        description "Maximum number of entries for the event log";
                    }

                    leaf-list apply-groups {
                        type leafref {
                            path "../../../../../groups/group/name";
                        }
                        max-elements 8;
                        ordered-by user;
                        sros-ext:auto-restart-to-modify;
                        description "Apply a configuration group at this level";
                    }

                    leaf-list apply-groups-exclude {
                        type leafref {
                            path "../../../../../groups/group/name";
                        }
                        max-elements 8;
                        ordered-by user;
                        sros-ext:auto-restart-to-modify;
                        description "Exclude a configuration group at this level";
                    }

                    container syslog {
                        sros-ext:auto-restart-to-modify;
                        description "Enter the syslog context";

                        leaf address {
                            type types-sros:ip-address;
                            sros-ext:auto-restart-to-modify;
                            description "Syslog host IP address";
                        }

                        leaf description {
                            type types-sros:description;
                            description "Text description";
                        }

                        leaf facility {
                            type enumeration {
                                enum "kernel"                       { value 0; }
                                enum "user"                         { value 1; }
                                enum "mail"                         { value 2; }
                                enum "systemd"                      { value 3; }
                                enum "auth"                         { value 4; }
                                enum "syslogd"                      { value 5; }
                                enum "printer"                      { value 6; }
                                enum "netnews"                      { value 7; }
                                enum "uucp"                         { value 8; }
                                enum "cron"                         { value 9; }
                                enum "authpriv"                     { value 10; }
                                enum "ftp"                          { value 11; }
                                enum "ntp"                          { value 12; }
                                enum "logaudit"                     { value 13; }
                                enum "logalert"                     { value 14; }
                                enum "cron2"                        { value 15; }
                                enum "local0"                       { value 16; }
                                enum "local1"                       { value 17; }
                                enum "local2"                       { value 18; }
                                enum "local3"                       { value 19; }
                                enum "local4"                       { value 20; }
                                enum "local5"                       { value 21; }
                                enum "local6"                       { value 22; }
                                enum "local7"                       { value 23; }
                            }
                            sros-ext:auto-restart-to-modify;
                            default "local7";
                            description "AA syslog facility";
                        }

                        leaf port {
                            type uint16;
                            sros-ext:auto-restart-to-modify;
                            default "514";
                            description "Syslog host UDP port";
                        }

                        leaf severity {
                            type enumeration {
                                enum "emergency"                    { value 0; }
                                enum "alert"                        { value 1; }
                                enum "critical"                     { value 2; }
                                enum "error"                        { value 3; }
                                enum "warning"                      { value 4; }
                                enum "notice"                       { value 5; }
                                enum "info"                         { value 6; }
                                enum "debug"                        { value 7; }
                            }
                            sros-ext:auto-restart-to-modify;
                            default "info";
                            description "Syslog message severity level threshold";
                        }

                        leaf vlan-id {
                            type uint32 {
                                range "1..4094";
                            }
                            sros-ext:auto-restart-to-modify;
                            description "ISA service port VLAN ID for sending syslog traffic";
                        }

                    } // container syslog

                } // list event-log

                container gtp {
                    description "Enter the gtp context";

                    leaf admin-state {
                        type types-sros:admin-state;
                        default "disable";
                        description "Administrative state of GTP";
                    }

                    leaf mode {
                        type enumeration {
                            enum "filtering"                    { value 1; }
                            enum "untunneling"                  { value 2; }
                        }
                        sros-ext:auto-restart-to-modify;
                        default "filtering";
                        description "GTP mode";
                    }

                    leaf gtpc-inspection {
                        type boolean;
                        default "false";
                        description "Enable inspection of GTP-C packets";
                    }

                    leaf-list apply-groups {
                        type leafref {
                            path "../../../../../groups/group/name";
                        }
                        max-elements 8;
                        ordered-by user;
                        description "Apply a configuration group at this level";
                    }

                    leaf-list apply-groups-exclude {
                        type leafref {
                            path "../../../../../groups/group/name";
                        }
                        max-elements 8;
                        ordered-by user;
                        description "Exclude a configuration group at this level";
                    }

                    container log {
                        description "Enter the log context";

                        leaf action {
                            type types-aa:event-log-action;
                            default "deny";
                            description "GTP log action";
                        }

                        leaf event-log {
                            type leafref {
                                path "../../../event-log/event-log-name";
                            }
                            description "Event log reference for logging GTP events";
                        }

                    } // container log

                    list gtp-filter {
                        key "gtp-filter-name";
                        description "Enter the gtp-filter list instance";

                        leaf gtp-filter-name {
                            type types-sros:named-item;
                            description "GTP filter name";
                        }

                        leaf description {
                            type types-sros:description;
                            description "Text description";
                        }

                        leaf gtp-in-gtp {
                            type types-aa:permit-deny-action;
                            default "permit";
                            description "GTP in GTP packet filtering";
                        }

                        leaf max-payload-length {
                            type int32 {
                                range "0..65535";
                            }
                            description "Maximum allowed GTP payload length";
                        }

                        leaf-list apply-groups {
                            type leafref {
                                path "../../../../../../groups/group/name";
                            }
                            max-elements 8;
                            ordered-by user;
                            description "Apply a configuration group at this level";
                        }

                        leaf-list apply-groups-exclude {
                            type leafref {
                                path "../../../../../../groups/group/name";
                            }
                            max-elements 8;
                            ordered-by user;
                            description "Exclude a configuration group at this level";
                        }

                        container gtp-tunnel-database {
                            description "Enter the gtp-tunnel-database context";

                            leaf default-tunnel-endpoint-limit {
                                type uint32 {
                                    range "1..4294967295";
                                }
                                default "4294967295";
                                description "Default GTP tunnel endpoint limit";
                            }

                            leaf validate-gtp-tunnels {
                                type boolean;
                                default "false";
                                description "Enable GTP tunnel validation";
                            }

                            leaf validate-sequence-number {
                                type boolean;
                                default "false";
                                description "Enable GTP sequence number checking";
                            }

                            leaf validate-source-ip-addr {
                                type boolean;
                                default "false";
                                description "Validate source IP address in GTP frames";
                            }

                        } // container gtp-tunnel-database

                        container log {
                            description "Enter the log context";

                            leaf action {
                                type types-aa:event-log-action;
                                default "deny";
                                description "GTP filter action to be logged";
                            }

                            leaf event-log {
                                type leafref {
                                    path "../../../../event-log/event-log-name";
                                }
                                description "Event-log name to capture GTP filter events";
                            }

                        } // container log

                        container message-type {
                            description "Enter the message-type context";

                            leaf default-action {
                                type types-aa:permit-deny-action;
                                default "permit";
                                description "GTP message type default action";
                            }

                            list entry {
                                key "entry-id";
                                description "Enter the entry list instance";

                                leaf entry-id {
                                    type uint32 {
                                        range "1..255";
                                    }
                                    description "GTP filter entry ID";
                                }

                                leaf action {
                                    type types-aa:permit-deny-action-no-default;
                                    mandatory true;
                                    description "GTPv1 filter message entry action";
                                }

                                leaf value {
                                    type types-aa:aa-gtp-fltr-msg-value;
                                    sros-ext:immutable;
                                    mandatory true;
                                    description "GTPv1 filter message type value";
                                }

                                leaf-list apply-groups {
                                    type leafref {
                                        path "../../../../../../../../groups/group/name";
                                    }
                                    max-elements 8;
                                    ordered-by user;
                                    description "Apply a configuration group at this level";
                                }

                                leaf-list apply-groups-exclude {
                                    type leafref {
                                        path "../../../../../../../../groups/group/name";
                                    }
                                    max-elements 8;
                                    ordered-by user;
                                    description "Exclude a configuration group at this level";
                                }

                            } // list entry

                        } // container message-type

                        container message-type-gtp-v2 {
                            description "Enter the message-type-gtp-v2 context";

                            leaf default-action {
                                type types-aa:permit-deny-action;
                                default "permit";
                                description "GTPv2 message type default action";
                            }

                            list entry {
                                key "entry-id";
                                description "Enter the entry list instance";

                                leaf entry-id {
                                    type uint32 {
                                        range "516..770";
                                    }
                                    description "GTPv2 filter entry ID";
                                }

                                leaf action {
                                    type types-aa:permit-deny-action-no-default;
                                    mandatory true;
                                    description "GTPv2 filter message entry action";
                                }

                                leaf value {
                                    type types-aa:aa-gtp-fltr-v2-msg-value;
                                    sros-ext:immutable;
                                    mandatory true;
                                    description "GTPv2 filter message type value";
                                }

                                leaf-list apply-groups {
                                    type leafref {
                                        path "../../../../../../../../groups/group/name";
                                    }
                                    max-elements 8;
                                    ordered-by user;
                                    description "Apply a configuration group at this level";
                                }

                                leaf-list apply-groups-exclude {
                                    type leafref {
                                        path "../../../../../../../../groups/group/name";
                                    }
                                    max-elements 8;
                                    ordered-by user;
                                    description "Exclude a configuration group at this level";
                                }

                            } // list entry

                        } // container message-type-gtp-v2

                        container imsi-apn-filter {
                            description "Enter the imsi-apn-filter context";

                            leaf default-action {
                                type types-aa:permit-deny-action;
                                default "permit";
                                description "IMSI APN filter default action";
                            }

                            list entry {
                                key "entry-id";
                                description "Enter the entry list instance";

                                leaf entry-id {
                                    type uint32 {
                                        range "1031..2030";
                                    }
                                    description "AA IMSI-APN filter entry ID";
                                }

                                leaf action {
                                    type types-aa:permit-deny-action;
                                    default "permit";
                                    description "IMSI APN filter entry action";
                                }

                                leaf apn {
                                    type types-sros:display-string {
                                        length "1..100";
                                    }
                                    description "APN as GTP filter match criterion";
                                }

                                leaf imsi-mcc-mnc-prefix {
                                    type types-sros:display-string {
                                        length "1..8";
                                        pattern "([0-9]{1,6})|(ANY_IMSI)";
                                    }
                                    description "IMSI (MCC-MNC) prefix as GTP filter match criterion";
                                }

                                leaf-list apply-groups {
                                    type leafref {
                                        path "../../../../../../../../groups/group/name";
                                    }
                                    max-elements 8;
                                    ordered-by user;
                                    description "Apply a configuration group at this level";
                                }

                                leaf-list apply-groups-exclude {
                                    type leafref {
                                        path "../../../../../../../../groups/group/name";
                                    }
                                    max-elements 8;
                                    ordered-by user;
                                    description "Exclude a configuration group at this level";
                                }

                                container src-gsn {
                                    description "Enter the src-gsn context";

                                    choice source-gsn {
                                        case ip-addr {

                                            leaf ip-prefix {
                                                type types-sros:ip-prefix;
                                                description "Source GSN IP address prefix as GTP filter match criterion";
                                            }

                                        }
                                        case ip-prefix-list {

                                            leaf ip-prefix-list {
                                                type leafref {
                                                    path "../../../../../../ip-prefix-list/ip-prefix-list-name";
                                                }
                                                description "Source GSN IP address prefix list as match criterion";
                                            }

                                        }
                                    }
                                } // container src-gsn

                            } // list entry

                        } // container imsi-apn-filter

                    } // list gtp-filter

                } // container gtp

                list ip-prefix-list {
                    key "ip-prefix-list-name";
                    description "Enter the ip-prefix-list list instance";

                    leaf ip-prefix-list-name {
                        type types-sros:named-item;
                        description "AA IP prefix list name";
                    }

                    leaf description {
                        type types-sros:description;
                        description "Text description";
                    }

                    leaf-list apply-groups {
                        type leafref {
                            path "../../../../../groups/group/name";
                        }
                        max-elements 8;
                        ordered-by user;
                        description "Apply a configuration group at this level";
                    }

                    leaf-list apply-groups-exclude {
                        type leafref {
                            path "../../../../../groups/group/name";
                        }
                        max-elements 8;
                        ordered-by user;
                        description "Exclude a configuration group at this level";
                    }

                    list prefix {
                        key "ip-prefix";
                        description "Enter the prefix list instance";

                        leaf ip-prefix {
                            type types-sros:ip-prefix;
                            description "AA IP prefix";
                        }

                        leaf name {
                            type types-sros:named-item;
                            description "AA IP prefix name";
                        }

                        leaf-list apply-groups {
                            type leafref {
                                path "../../../../../../groups/group/name";
                            }
                            max-elements 8;
                            ordered-by user;
                            description "Apply a configuration group at this level";
                        }

                        leaf-list apply-groups-exclude {
                            type leafref {
                                path "../../../../../../groups/group/name";
                            }
                            max-elements 8;
                            ordered-by user;
                            description "Exclude a configuration group at this level";
                        }

                    } // list prefix

                } // list ip-prefix-list

                list port-list {
                    key "port-list-name";
                    description "Enter the port-list list instance";

                    leaf port-list-name {
                        type types-sros:named-item;
                        description "Port list name";
                    }

                    leaf description {
                        type types-sros:description;
                        description "Text description";
                    }

                    leaf-list apply-groups {
                        type leafref {
                            path "../../../../../groups/group/name";
                        }
                        max-elements 8;
                        ordered-by user;
                        description "Apply a configuration group at this level";
                    }

                    leaf-list apply-groups-exclude {
                        type leafref {
                            path "../../../../../groups/group/name";
                        }
                        max-elements 8;
                        ordered-by user;
                        description "Exclude a configuration group at this level";
                    }

                    list port {
                        key "port-number";
                        description "Add a list entry for port";

                        leaf port-number {
                            type int32 {
                                range "0..65535";
                            }
                            description "Port number";
                        }

                    } // list port

                    list range {
                        key "start end";
                        description "Add a list entry for range";

                        leaf start {
                            type int32 {
                                range "0..65534";
                            }
                            description "Start value for the port range in the AA port list";
                        }

                        leaf end {
                            type int32 {
                                range "1..65535";
                            }
                            description "End value for the port range in the AA port list";
                        }

                    } // list range

                } // list port-list

                list sctp-filter {
                    key "sctp-filter-name";
                    description "Enter the sctp-filter list instance";

                    leaf sctp-filter-name {
                        type types-sros:named-item;
                        description "SCTP filter name";
                    }

                    leaf description {
                        type types-sros:description;
                        description "Text description";
                    }

                    leaf event-log {
                        type leafref {
                            path "../../event-log/event-log-name";
                        }
                        description "Event log for packets dropped by the SCTP filter";
                    }

                    leaf-list apply-groups {
                        type leafref {
                            path "../../../../../groups/group/name";
                        }
                        max-elements 8;
                        ordered-by user;
                        description "Apply a configuration group at this level";
                    }

                    leaf-list apply-groups-exclude {
                        type leafref {
                            path "../../../../../groups/group/name";
                        }
                        max-elements 8;
                        ordered-by user;
                        description "Exclude a configuration group at this level";
                    }

                    container ppid-range {
                        description "Enter the ppid-range context";

                        leaf min {
                            type uint32 {
                                range "0..4294967295";
                            }
                            default "0";
                            description "Minimum PPID value";
                        }

                        leaf max {
                            type uint32 {
                                range "0..4294967295";
                            }
                            default "4294967295";
                            description "Maximum PPID value";
                        }

                    } // container ppid-range

                    container ppid {
                        description "Enter the ppid context";

                        leaf default-action {
                            type types-aa:permit-deny-action;
                            default "permit";
                            description "Default action for all SCTP PPIDs";
                        }

                        list entry {
                            key "entry-id";
                            description "Enter the entry list instance";

                            leaf entry-id {
                                type uint32 {
                                    range "1..255";
                                }
                                description "SCTP filter PPID entry ID";
                            }

                            leaf action {
                                type types-aa:permit-deny-action-no-default;
                                mandatory true;
                                description "SCTP filter PPID entry action";
                            }

                            leaf value {
                                type types-aa:aa-ppid-value;
                                sros-ext:immutable;
                                mandatory true;
                                description "PPID entry value";
                            }

                            leaf-list apply-groups {
                                type leafref {
                                    path "../../../../../../../groups/group/name";
                                }
                                max-elements 8;
                                ordered-by user;
                                description "Apply a configuration group at this level";
                            }

                            leaf-list apply-groups-exclude {
                                type leafref {
                                    path "../../../../../../../groups/group/name";
                                }
                                max-elements 8;
                                ordered-by user;
                                description "Exclude a configuration group at this level";
                            }

                        } // list entry

                    } // container ppid

                } // list sctp-filter

                list tcp-validate {
                    key "tcp-validate-name";
                    description "Enter the tcp-validate list instance";

                    leaf tcp-validate-name {
                        type types-sros:named-item;
                        description "TCP validation policy name";
                    }

                    leaf description {
                        type types-sros:description;
                        description "Text description";
                    }

                    leaf strict {
                        type boolean;
                        default "false";
                        description "Enable strict checking of TCP traffic";
                    }

                    leaf-list apply-groups {
                        type leafref {
                            path "../../../../../groups/group/name";
                        }
                        max-elements 8;
                        ordered-by user;
                        description "Apply a configuration group at this level";
                    }

                    leaf-list apply-groups-exclude {
                        type leafref {
                            path "../../../../../groups/group/name";
                        }
                        max-elements 8;
                        ordered-by user;
                        description "Exclude a configuration group at this level";
                    }

                    container log {
                        description "Enter the log context";

                        leaf all {
                            type boolean;
                            default "false";
                            description "Enable logging of all dropped TCP packets";
                        }

                        leaf event-log {
                            type leafref {
                                path "../../../event-log/event-log-name";
                            }
                            description "Event log name";
                        }

                    } // container log

                } // list tcp-validate

                container tethering-detection {
                    description "Enter the tethering-detection context";

                    leaf admin-state {
                        type types-sros:admin-state;
                        default "disable";
                        description "Administrative state of tethering detection";
                    }

                    leaf-list apply-groups {
                        type leafref {
                            path "../../../../../groups/group/name";
                        }
                        max-elements 8;
                        ordered-by user;
                        description "Apply a configuration group at this level";
                    }

                    leaf-list apply-groups-exclude {
                        type leafref {
                            path "../../../../../groups/group/name";
                        }
                        max-elements 8;
                        ordered-by user;
                        description "Exclude a configuration group at this level";
                    }

                    container single-device {
                        description "Enter the single-device context";

                        list expected-ttl {
                            key "ttl";
                            description "Add a list entry for expected-ttl";

                            leaf ttl {
                                type uint32 {
                                    range "1..255";
                                }
                                description "Expected TTL traffic value from host devices";
                            }

                        } // list expected-ttl

                    } // container single-device

                } // container tethering-detection

                container wap1x {
                    description "Enter the wap1x context";

                    leaf admin-state {
                        type types-sros:admin-state;
                        default "disable";
                        description "Administrative state of WAP1x detection";
                    }

                    leaf-list apply-groups {
                        type leafref {
                            path "../../../../../groups/group/name";
                        }
                        max-elements 8;
                        ordered-by user;
                        description "Apply a configuration group at this level";
                    }

                    leaf-list apply-groups-exclude {
                        type leafref {
                            path "../../../../../groups/group/name";
                        }
                        max-elements 8;
                        ordered-by user;
                        description "Exclude a configuration group at this level";
                    }

                } // container wap1x

                list session-filter {
                    key "session-filter-name";
                    max-elements 300;
                    description "Enter the session-filter list instance";

                    leaf session-filter-name {
                        type types-sros:named-item;
                        description "Session filter name";
                    }

                    leaf description {
                        type types-sros:description;
                        description "Text description";
                    }

                    leaf-list apply-groups {
                        type leafref {
                            path "../../../../../groups/group/name";
                        }
                        max-elements 8;
                        ordered-by user;
                        description "Apply a configuration group at this level";
                    }

                    leaf-list apply-groups-exclude {
                        type leafref {
                            path "../../../../../groups/group/name";
                        }
                        max-elements 8;
                        ordered-by user;
                        description "Exclude a configuration group at this level";
                    }

                    container default-action {
                        description "Enter the default-action context";

                        leaf action {
                            type types-aa:permit-deny-action;
                            default "deny";
                            description "Default action for packets not matching filter entries";
                        }

                        leaf event-log {
                            type leafref {
                                path "../../../event-log/event-log-name";
                            }
                            description "Event logging of default action";
                        }

                    } // container default-action

                    list entry {
                        key "entry-id";
                        description "Enter the entry list instance";

                        leaf entry-id {
                            type uint32 {
                                range "1..65535";
                            }
                            description "Entry ID for the session filter entry";
                        }

                        leaf description {
                            type types-sros:description;
                            description "Text description";
                        }

                        leaf-list apply-groups {
                            type leafref {
                                path "../../../../../../groups/group/name";
                            }
                            max-elements 8;
                            ordered-by user;
                            description "Apply a configuration group at this level";
                        }

                        leaf-list apply-groups-exclude {
                            type leafref {
                                path "../../../../../../groups/group/name";
                            }
                            max-elements 8;
                            ordered-by user;
                            description "Exclude a configuration group at this level";
                        }

                        container match {
                            description "Enter the match context";

                            leaf ip-protocol {
                                type types-sros:match-ip-protocol;
                                description "IP protocol as a match criterion";
                            }

                            container dst-ip {
                                description "Enter the dst-ip context";

                                choice match-addr-choice {
                                    case ip-prefix {

                                        leaf ip-prefix {
                                            type types-sros:ip-prefix;
                                            description "Destination IP address prefix as match criterion";
                                        }

                                    }
                                    case ip-prefix-list {

                                        leaf ip-prefix-list {
                                            type leafref {
                                                path "../../../../../ip-prefix-list/ip-prefix-list-name";
                                            }
                                            description "IP address prefix list as match criterion";
                                        }

                                    }
                                    case dns-ip-cache {

                                        leaf dns-ip-cache {
                                            type leafref {
                                                path "../../../../../../dns-ip-cache/dns-ip-cache-name";
                                            }
                                            description "Destination IPs in specified DNS IP Cache";
                                        }

                                    }
                                }
                            } // container dst-ip

                            container dst-port {
                                description "Enter the dst-port context";

                                choice match-op-choice {
                                    case eq {

                                        leaf eq {
                                            type types-sros:tcp-udp-port;
                                            default "0";
                                            description "Match criterion used for destination or source port";
                                        }

                                    }
                                    case lt {

                                        leaf lt {
                                            type types-sros:tcp-udp-port;
                                            default "0";
                                            description "Less than match criterion for the port";
                                        }

                                    }
                                    case gt {

                                        leaf gt {
                                            type types-sros:tcp-udp-port;
                                            default "0";
                                            description "Greater than match criterion for the port number";
                                        }

                                    }
                                    case range {

                                        container range {
                                            presence "Enable the range context";
                                            description "Enter the range context";

                                            leaf start {
                                                type types-sros:tcp-udp-port;
                                                default "0";
                                                description "Lower bound of the port range as match criterion";
                                            }

                                            leaf end {
                                                type types-sros:tcp-udp-port;
                                                default "1";
                                                description "Upper bound of the port range as match criterion";
                                            }

                                        } // container range

                                    }
                                    case port-list {

                                        leaf port-list {
                                            type leafref {
                                                path "../../../../../port-list/port-list-name";
                                            }
                                            description "Destination or source port list";
                                        }

                                    }
                                }
                            } // container dst-port

                            container src-ip {
                                description "Enter the src-ip context";

                                choice match-addr-choice {
                                    case ip-prefix {

                                        leaf ip-prefix {
                                            type types-sros:ip-prefix;
                                            description "Source IP address prefix as match criterion";
                                        }

                                    }
                                    case ip-prefix-list {

                                        leaf ip-prefix-list {
                                            type leafref {
                                                path "../../../../../ip-prefix-list/ip-prefix-list-name";
                                            }
                                            description "Source IP address prefix list as match criterion";
                                        }

                                    }
                                }
                            } // container src-ip

                            container src-port {
                                description "Enter the src-port context";

                                choice match-op-choice {
                                    case eq {

                                        leaf eq {
                                            type types-sros:tcp-udp-port;
                                            default "0";
                                            description "Match criterion used for destination or source port";
                                        }

                                    }
                                    case lt {

                                        leaf lt {
                                            type types-sros:tcp-udp-port;
                                            default "0";
                                            description "Less than match criterion for the port";
                                        }

                                    }
                                    case gt {

                                        leaf gt {
                                            type types-sros:tcp-udp-port;
                                            default "0";
                                            description "Greater than match criterion for the port number";
                                        }

                                    }
                                    case range {

                                        container range {
                                            presence "Enable the range context";
                                            description "Enter the range context";

                                            leaf start {
                                                type types-sros:tcp-udp-port;
                                                default "0";
                                                description "Lower bound of the port range as match criterion";
                                            }

                                            leaf end {
                                                type types-sros:tcp-udp-port;
                                                default "1";
                                                description "Upper bound of the port range as match criterion";
                                            }

                                        } // container range

                                    }
                                    case port-list {

                                        leaf port-list {
                                            type leafref {
                                                path "../../../../../port-list/port-list-name";
                                            }
                                            description "Destination or source port list";
                                        }

                                    }
                                }
                            } // container src-port

                        } // container match

                        container action {
                            description "Enter the action context";

                            leaf event-log {
                                type leafref {
                                    path "../../../../event-log/event-log-name";
                                }
                                description "Event log name used to log the action";
                            }

                            choice action-choice {
                                default "deny";
                                case deny {

                                    leaf deny {
                                        type empty;
                                        description "Deny sessions matching the criteria";
                                    }

                                }
                                case permit {

                                    leaf permit {
                                        type empty;
                                        description "Permit sessions that match the criteria";
                                    }

                                }
                                case http-redirect {

                                    leaf http-redirect {
                                        type leafref {
                                            path "../../../../../http-redirect/http-redirect-name";
                                        }
                                        description "HTTP redirect for matching sessions";
                                    }

                                }
                                case tcp-optimizer {

                                    leaf tcp-optimizer {
                                        type leafref {
                                            path "../../../../../tcp-optimizer/tcp-optimizer-name";
                                        }
                                        description "TCP optimizer to handle sessions matching the criteria";
                                    }

                                }
                            }
                        } // container action

                    } // list entry

                } // list session-filter

                container policy {
                    description "Enter the policy context";

                    leaf default-charging-group {
                        type leafref {
                            path "../charging-group/charging-group-name";
                        }
                        description "Default charging group";
                    }

                    leaf default-tethered-charging-group {
                        type leafref {
                            path "../charging-group/charging-group-name";
                        }
                        description "Default charging group for tethered traffic";
                    }

                    leaf-list apply-groups {
                        type leafref {
                            path "../../../../../groups/group/name";
                        }
                        max-elements 8;
                        ordered-by user;
                        description "Apply a configuration group at this level";
                    }

                    leaf-list apply-groups-exclude {
                        type leafref {
                            path "../../../../../groups/group/name";
                        }
                        max-elements 8;
                        ordered-by user;
                        description "Exclude a configuration group at this level";
                    }

                    list custom-protocol {
                        key "custom-protocol-id";
                        description "Enter the custom-protocol list instance";

                        leaf custom-protocol-id {
                            type types-aa:custom-protocol-name;
                            description "Custom protocol ID for the AA policy custom protocol";
                        }

                        leaf admin-state {
                            type types-sros:admin-state;
                            default "disable";
                            description "Administrative state of the custom protocol";
                        }

                        leaf description {
                            type types-sros:description;
                            description "Text description";
                        }

                        leaf ip-protocol {
                            type enumeration {
                                enum "tcp"                          { value 6; }
                                enum "udp"                          { value 17; }
                            }
                            sros-ext:immutable;
                            mandatory true;
                            description "IP protocol number for custom-protocol match criterion";
                        }

                        leaf-list apply-groups {
                            type leafref {
                                path "../../../../../../groups/group/name";
                            }
                            max-elements 8;
                            ordered-by user;
                            description "Apply a configuration group at this level";
                        }

                        leaf-list apply-groups-exclude {
                            type leafref {
                                path "../../../../../../groups/group/name";
                            }
                            max-elements 8;
                            ordered-by user;
                            description "Exclude a configuration group at this level";
                        }

                        list expression {
                            key "expr-index";
                            description "Enter the expression list instance";

                            leaf expr-index {
                                type uint32 {
                                    range "1";
                                }
                                description "Expression substring index for custom protocol matching";
                            }

                            leaf direction {
                                type enumeration {
                                    enum "client-to-server"             { value 1; }
                                    enum "server-to-client"             { value 2; }
                                    enum "any"                          { value 3; }
                                }
                                mandatory true;
                                description "Flow direction for custom-protocol expression matching";
                            }

                            leaf offset {
                                type uint32 {
                                    range "0..127";
                                }
                                default "0";
                                description "Offset in protocol flow to start custom-protocol match";
                            }

                            leaf-list apply-groups {
                                type leafref {
                                    path "../../../../../../../groups/group/name";
                                }
                                max-elements 8;
                                ordered-by user;
                                description "Apply a configuration group at this level";
                            }

                            leaf-list apply-groups-exclude {
                                type leafref {
                                    path "../../../../../../../groups/group/name";
                                }
                                max-elements 8;
                                ordered-by user;
                                description "Exclude a configuration group at this level";
                            }

                            choice operator-choice {
                                mandatory true;
                                case eq {

                                    leaf eq {
                                        type types-sros:display-string;
                                        description "Exact match criterion for custom protocol expression";
                                    }

                                }
                            }
                        } // list expression

                    } // list custom-protocol

                    list charging-group {
                        key "charging-group-name";
                        description "Enter the charging-group list instance";

                        leaf charging-group-name {
                            type types-sros:named-item;
                            description "Charging group name";
                        }

                        leaf description {
                            type types-sros:description;
                            description "Text description";
                        }

                        leaf export-id {
                            type uint32 {
                                range "1..255";
                            }
                            description "Charging group export ID used for RADIUS accounting";
                        }

                        leaf notify-start-stop {
                            type types-aa:notify-start-stop-type;
                            description "Start and stop notification for the charging group";
                        }

                        leaf-list apply-groups {
                            type leafref {
                                path "../../../../../../groups/group/name";
                            }
                            max-elements 8;
                            ordered-by user;
                            description "Apply a configuration group at this level";
                        }

                        leaf-list apply-groups-exclude {
                            type leafref {
                                path "../../../../../../groups/group/name";
                            }
                            max-elements 8;
                            ordered-by user;
                            description "Exclude a configuration group at this level";
                        }

                    } // list charging-group

                    list app-group {
                        key "application-group-name";
                        description "Enter the app-group list instance";

                        leaf application-group-name {
                            type types-sros:named-item;
                            description "Application group name";
                        }

                        leaf description {
                            type types-sros:description;
                            description "Text description";
                        }

                        leaf charging-group {
                            type leafref {
                                path "../../charging-group/charging-group-name";
                            }
                            description "Charging group used in the AA application group policy";
                        }

                        leaf export-id {
                            type uint32 {
                                range "1..255";
                            }
                            description "App group export ID used in RADIUS accounting export";
                        }

                        leaf-list apply-groups {
                            type leafref {
                                path "../../../../../../groups/group/name";
                            }
                            max-elements 8;
                            ordered-by user;
                            description "Apply a configuration group at this level";
                        }

                        leaf-list apply-groups-exclude {
                            type leafref {
                                path "../../../../../../groups/group/name";
                            }
                            max-elements 8;
                            ordered-by user;
                            description "Exclude a configuration group at this level";
                        }

                    } // list app-group

                    list application {
                        key "application-name";
                        description "Enter the application list instance";

                        leaf application-name {
                            type types-sros:named-item;
                            description "Application name";
                        }

                        leaf description {
                            type types-sros:description;
                            description "Text description";
                        }

                        leaf app-group {
                            type leafref {
                                path "../../app-group/application-group-name";
                            }
                            description "Application group associated with the application";
                        }

                        leaf charging-group {
                            type leafref {
                                path "../../charging-group/charging-group-name";
                            }
                            description "Charging group associated with the application";
                        }

                        leaf export-id {
                            type uint32 {
                                range "1..255";
                            }
                            description "Application export ID used for RADIUS accounting";
                        }

                        leaf-list apply-groups {
                            type leafref {
                                path "../../../../../../groups/group/name";
                            }
                            max-elements 8;
                            ordered-by user;
                            description "Apply a configuration group at this level";
                        }

                        leaf-list apply-groups-exclude {
                            type leafref {
                                path "../../../../../../groups/group/name";
                            }
                            max-elements 8;
                            ordered-by user;
                            description "Exclude a configuration group at this level";
                        }

                    } // list application

                    container app-service-options {
                        description "Enter the app-service-options context";

                        list characteristic {
                            key "characteristic-name";
                            description "Enter the characteristic list instance";

                            leaf characteristic-name {
                                type types-sros:named-item;
                                description "ASO characteristic name";
                            }

                            leaf default-value {
                                type types-sros:named-item;
                                description "ASO characteristic default value";
                            }

                            leaf-list apply-groups {
                                type leafref {
                                    path "../../../../../../../groups/group/name";
                                }
                                max-elements 8;
                                ordered-by user;
                                description "Apply a configuration group at this level";
                            }

                            leaf-list apply-groups-exclude {
                                type leafref {
                                    path "../../../../../../../groups/group/name";
                                }
                                max-elements 8;
                                ordered-by user;
                                description "Exclude a configuration group at this level";
                            }

                            list value {
                                key "value-name";
                                max-elements 64;
                                description "Add a list entry for value";

                                leaf value-name {
                                    type types-sros:named-item;
                                    description "ASO characteristic value name";
                                }

                            } // list value

                        } // list characteristic

                    } // container app-service-options

                    list app-profile {
                        key "app-profile-name";
                        description "Enter the app-profile list instance";

                        leaf app-profile-name {
                            type types-sros:named-item;
                            description "App-profile name";
                        }

                        leaf description {
                            type types-sros:description;
                            description "Text description";
                        }

                        leaf aa-sub-suppressible {
                            type boolean;
                            default "false";
                            description "Enable AA suppression for subs with this app profile";
                        }

                        leaf capacity-cost {
                            type uint16 {
                                range "1..65535";
                            }
                            default "1";
                            description "Application profile capacity cost";
                        }

                        leaf divert {
                            type boolean;
                            default "false";
                            description "Enable traffic redirection to AA ISAs or ESA VMs";
                        }

                        leaf-list apply-groups {
                            type leafref {
                                path "../../../../../../groups/group/name";
                            }
                            max-elements 8;
                            ordered-by user;
                            description "Apply a configuration group at this level";
                        }

                        leaf-list apply-groups-exclude {
                            type leafref {
                                path "../../../../../../groups/group/name";
                            }
                            max-elements 8;
                            ordered-by user;
                            description "Exclude a configuration group at this level";
                        }

                        list characteristic {
                            key "characteristic-name";
                            description "Enter the characteristic list instance";

                            leaf characteristic-name {
                                type leafref {
                                    path "../../../app-service-options/characteristic/characteristic-name";
                                }
                                description "Application service option characteristic name";
                            }

                            leaf value {
                                type leafref {
                                    path "../../../app-service-options/characteristic[characteristic-name=current()/../characteristic-name]/value/value-name";
                                }
                                mandatory true;
                                description "ASO characteristic value name";
                            }

                            leaf-list apply-groups {
                                type leafref {
                                    path "../../../../../../../groups/group/name";
                                }
                                max-elements 8;
                                ordered-by user;
                                description "Apply a configuration group at this level";
                            }

                            leaf-list apply-groups-exclude {
                                type leafref {
                                    path "../../../../../../../groups/group/name";
                                }
                                max-elements 8;
                                ordered-by user;
                                description "Exclude a configuration group at this level";
                            }

                        } // list characteristic

                    } // list app-profile

                    container app-filter {
                        description "Enter the app-filter context";

                        list entry {
                            key "entry-id";
                            description "Enter the entry list instance";

                            leaf entry-id {
                                type uint32 {
                                    range "1..65535";
                                }
                                description "Application filter entry ID";
                            }

                            leaf admin-state {
                                type types-sros:admin-state;
                                default "disable";
                                description "Administrative state of the AA application filter entry";
                            }

                            leaf description {
                                type types-sros:description;
                                description "Text description";
                            }

                            leaf application {
                                type leafref {
                                    path "../../../application/application-name";
                                }
                                description "Application name";
                            }

                            leaf flow-setup-direction {
                                type types-aa:traffic-direction;
                                default "both";
                                description "Traffic flow direction for the application filter entry";
                            }

                            leaf http-match-all-requests {
                                type boolean;
                                default "false";
                                description "Enable HTTP matching for all requests";
                            }

                            leaf-list apply-groups {
                                type leafref {
                                    path "../../../../../../../groups/group/name";
                                }
                                max-elements 8;
                                ordered-by user;
                                description "Apply a configuration group at this level";
                            }

                            leaf-list apply-groups-exclude {
                                type leafref {
                                    path "../../../../../../../groups/group/name";
                                }
                                max-elements 8;
                                ordered-by user;
                                description "Exclude a configuration group at this level";
                            }

                            choice server-or-network-address {
                                case server-address {

                                    container server-address {
                                        description "Enter the server-address context";

                                        choice match-operator {
                                            case eq {

                                                container eq {
                                                    description "Enter the eq context";

                                                    choice server-addr-choice {
                                                        case ip-prefix {

                                                            leaf ip-prefix {
                                                                type types-sros:ip-prefix;
                                                                description "IP prefix";
                                                            }

                                                        }
                                                        case ip-prefix-list {

                                                            leaf ip-prefix-list {
                                                                type leafref {
                                                                    path "../../../../../../ip-prefix-list/ip-prefix-list-name";
                                                                }
                                                                description "IP prefix list";
                                                            }

                                                        }
                                                        case dns-ip-cache {

                                                            leaf dns-ip-cache {
                                                                type leafref {
                                                                    path "../../../../../../../dns-ip-cache/dns-ip-cache-name";
                                                                }
                                                                description "DNS IP cache name";
                                                            }

                                                        }
                                                        case masked-ip {

                                                            container masked-ip {
                                                                description "Enter the masked-ip context";

                                                                leaf address {
                                                                    type types-sros:ip-address;
                                                                    description "IPv4 or IPv6 address mask";
                                                                }

                                                                leaf netmask {
                                                                    type types-sros:ip-address;
                                                                    description "IPv4 or IPv6 address mask";
                                                                }

                                                            } // container masked-ip

                                                        }
                                                    }
                                                } // container eq

                                            }
                                            case neq {

                                                container neq {
                                                    description "Enter the neq context";

                                                    choice server-addr-choice {
                                                        case ip-prefix {

                                                            leaf ip-prefix {
                                                                type types-sros:ip-prefix;
                                                                description "IP prefix";
                                                            }

                                                        }
                                                        case ip-prefix-list {

                                                            leaf ip-prefix-list {
                                                                type leafref {
                                                                    path "../../../../../../ip-prefix-list/ip-prefix-list-name";
                                                                }
                                                                description "IP prefix list";
                                                            }

                                                        }
                                                        case dns-ip-cache {

                                                            leaf dns-ip-cache {
                                                                type leafref {
                                                                    path "../../../../../../../dns-ip-cache/dns-ip-cache-name";
                                                                }
                                                                description "DNS IP cache name";
                                                            }

                                                        }
                                                        case masked-ip {

                                                            container masked-ip {
                                                                description "Enter the masked-ip context";

                                                                leaf address {
                                                                    type types-sros:ip-address;
                                                                    description "IPv4 or IPv6 address mask";
                                                                }

                                                                leaf netmask {
                                                                    type types-sros:ip-address;
                                                                    description "IPv4 or IPv6 address mask";
                                                                }

                                                            } // container masked-ip

                                                        }
                                                    }
                                                } // container neq

                                            }
                                        }
                                    } // container server-address

                                }
                                case network-address {

                                    container network-address {
                                        description "Enter the network-address context";

                                        choice match-operator {
                                            case eq {

                                                container eq {
                                                    description "Enter the eq context";

                                                    choice network-addr-choice {
                                                        case ip-prefix {

                                                            leaf ip-prefix {
                                                                type types-sros:ip-prefix;
                                                                description "IP prefix";
                                                            }

                                                        }
                                                        case ip-prefix-list {

                                                            leaf ip-prefix-list {
                                                                type leafref {
                                                                    path "../../../../../../ip-prefix-list/ip-prefix-list-name";
                                                                }
                                                                description "IP prefix list";
                                                            }

                                                        }
                                                    }
                                                } // container eq

                                            }
                                            case neq {

                                                container neq {
                                                    description "Enter the neq context";

                                                    choice network-addr-choice {
                                                        case ip-prefix {

                                                            leaf ip-prefix {
                                                                type types-sros:ip-prefix;
                                                                description "IP prefix";
                                                            }

                                                        }
                                                        case ip-prefix-list {

                                                            leaf ip-prefix-list {
                                                                type leafref {
                                                                    path "../../../../../../ip-prefix-list/ip-prefix-list-name";
                                                                }
                                                                description "IP prefix list";
                                                            }

                                                        }
                                                    }
                                                } // container neq

                                            }
                                        }
                                    } // container network-address

                                }
                            }
                            container http-port {
                                description "Enter the http-port context";

                                choice match-operator {
                                    case eq {

                                        container eq {
                                            description "Enter the eq context";

                                            choice eq-port-choice {
                                                case port-number {

                                                    leaf port-number {
                                                        type types-sros:tcp-udp-port;
                                                        default "0";
                                                        description "Server port number";
                                                    }

                                                }
                                                case port-list {

                                                    leaf port-list {
                                                        type leafref {
                                                            path "../../../../../../port-list/port-list-name";
                                                        }
                                                        description "Port list name";
                                                    }

                                                }
                                            }
                                        } // container eq

                                    }
                                    case neq {

                                        container neq {
                                            description "Enter the neq context";

                                            choice neq-port-choice {
                                                case port-number {

                                                    leaf port-number {
                                                        type types-sros:tcp-udp-port;
                                                        default "0";
                                                        description "Server port number";
                                                    }

                                                }
                                                case port-list {

                                                    leaf port-list {
                                                        type leafref {
                                                            path "../../../../../../port-list/port-list-name";
                                                        }
                                                        description "Port list name";
                                                    }

                                                }
                                            }
                                        } // container neq

                                    }
                                }
                            } // container http-port

                            container ip-protocol {
                                description "Enter the ip-protocol context";

                                choice match-operator {
                                    case eq {

                                        leaf eq {
                                            type types-sros:match-ip-protocol;
                                            description "Exact match criterion used for the IP protocol number";
                                        }

                                    }
                                    case neq {

                                        leaf neq {
                                            type types-sros:match-ip-protocol;
                                            description "Non-match criterion used for the IP protocol number";
                                        }

                                    }
                                }
                            } // container ip-protocol

                            container protocol {
                                description "Enter the protocol context";

                                choice match-operator {
                                    case eq {

                                        leaf eq {
                                            type union {
                                                type string;
                                                type types-sros:named-item;
                                            }
                                            description "Exact match criterion used for the AA protocol name";
                                        }

                                    }
                                    case neq {

                                        leaf neq {
                                            type union {
                                                type string;
                                                type types-sros:named-item;
                                            }
                                            description "Non-match criterion used for the AA protocol name";
                                        }

                                    }
                                }
                            } // container protocol

                            container server-port {
                                description "Enter the server-port context";

                                choice match-operator {
                                    case eq {

                                        container eq {
                                            description "Enter the eq context";

                                            leaf first-packet-policy {
                                                type enumeration {
                                                    enum "first-packet-trusted"         { value 1; }
                                                    enum "first-packet-validate"        { value 2; }
                                                }
                                                description "First packet policy";
                                            }

                                            choice eq-port-choice {
                                                case port-number {

                                                    leaf port-number {
                                                        type types-sros:tcp-udp-port;
                                                        default "0";
                                                        description "Server port number used as match criterion";
                                                    }

                                                }
                                                case port-list {

                                                    leaf port-list {
                                                        type leafref {
                                                            path "../../../../../../port-list/port-list-name";
                                                        }
                                                        description "Port-list name used in application filter criteria";
                                                    }

                                                }
                                                case range {

                                                    container range {
                                                        description "Enter the range context";

                                                        leaf start {
                                                            type types-sros:tcp-udp-port;
                                                            default "0";
                                                            description "TCP/UDP starting port number";
                                                        }

                                                        leaf end {
                                                            type types-sros:tcp-udp-port;
                                                            default "1";
                                                            description "TCP/UDP ending port number";
                                                        }

                                                    } // container range

                                                }
                                            }
                                        } // container eq

                                    }
                                    case neq {

                                        container neq {
                                            description "Enter the neq context";

                                            choice neq-port-choice {
                                                case port-number {

                                                    leaf port-number {
                                                        type types-sros:tcp-udp-port;
                                                        default "0";
                                                        description "Server port number used as match criterion";
                                                    }

                                                }
                                                case port-list {

                                                    leaf port-list {
                                                        type leafref {
                                                            path "../../../../../../port-list/port-list-name";
                                                        }
                                                        description "Port-list name used in application filter criteria";
                                                    }

                                                }
                                                case range {

                                                    container range {
                                                        description "Enter the range context";

                                                        leaf start {
                                                            type types-sros:tcp-udp-port;
                                                            default "0";
                                                            description "TCP/UDP starting port number";
                                                        }

                                                        leaf end {
                                                            type types-sros:tcp-udp-port;
                                                            default "1";
                                                            description "TCP/UDP ending port number";
                                                        }

                                                    } // container range

                                                }
                                            }
                                        } // container neq

                                    }
                                    case lt {

                                        container lt {
                                            description "Enter the lt context";

                                            leaf port-number {
                                                type types-sros:tcp-udp-port;
                                                default "0";
                                                description "Server port number used as match criterion";
                                            }

                                        } // container lt

                                    }
                                    case gt {

                                        container gt {
                                            description "Enter the gt context";

                                            leaf port-number {
                                                type types-sros:tcp-udp-port;
                                                default "0";
                                                description "Server port number used as match criterion";
                                            }

                                        } // container gt

                                    }
                                }
                            } // container server-port

                            list expression {
                                key "expr-index";
                                description "Enter the expression list instance";

                                leaf expr-index {
                                    type uint32 {
                                        range "1..4";
                                    }
                                    description "Application filter matching expression identifier";
                                }

                                leaf type {
                                    type types-aa:expr-sub-string;
                                    mandatory true;
                                    description "Application filter matching expression type";
                                }

                                leaf-list apply-groups {
                                    type leafref {
                                        path "../../../../../../../../groups/group/name";
                                    }
                                    max-elements 8;
                                    ordered-by user;
                                    description "Apply a configuration group at this level";
                                }

                                leaf-list apply-groups-exclude {
                                    type leafref {
                                        path "../../../../../../../../groups/group/name";
                                    }
                                    max-elements 8;
                                    ordered-by user;
                                    description "Exclude a configuration group at this level";
                                }

                                choice operator-choice {
                                    mandatory true;
                                    case eq {

                                        leaf eq {
                                            type types-sros:display-string;
                                            description "Exact match for application filter matching expression";
                                        }

                                    }
                                    case neq {

                                        leaf neq {
                                            type types-sros:display-string;
                                            description "Non-match for application filter matching expression";
                                        }

                                    }
                                }
                            } // list expression

                        } // list entry

                    } // container app-filter

                    container app-qos-policy {
                        description "Enter the app-qos-policy context";

                        list entry {
                            key "entry-id";
                            description "Enter the entry list instance";

                            leaf entry-id {
                                type uint32 {
                                    range "1..65535";
                                }
                                description "AQP entry ID";
                            }

                            leaf admin-state {
                                type types-sros:admin-state;
                                default "disable";
                                description "Administrative state of the AA AQP entry";
                            }

                            leaf description {
                                type types-sros:description;
                                description "Text description";
                            }

                            leaf-list apply-groups {
                                type leafref {
                                    path "../../../../../../../groups/group/name";
                                }
                                max-elements 8;
                                ordered-by user;
                                description "Apply a configuration group at this level";
                            }

                            leaf-list apply-groups-exclude {
                                type leafref {
                                    path "../../../../../../../groups/group/name";
                                }
                                max-elements 8;
                                ordered-by user;
                                description "Exclude a configuration group at this level";
                            }

                            container match {
                                description "Enter the match context";

                                leaf aa-sub-tethering {
                                    type types-aa:sub-tether-state;
                                    default "not-applicable";
                                    description "Tethering detection status for flow match criterion";
                                }

                                leaf traffic-direction {
                                    type types-aa:traffic-direction;
                                    default "both";
                                    description "Traffic direction to which AQP match entry is applied";
                                }

                                leaf-list apply-groups {
                                    type leafref {
                                        path "../../../../../../../../groups/group/name";
                                    }
                                    max-elements 8;
                                    ordered-by user;
                                    description "Apply a configuration group at this level";
                                }

                                leaf-list apply-groups-exclude {
                                    type leafref {
                                        path "../../../../../../../../groups/group/name";
                                    }
                                    max-elements 8;
                                    ordered-by user;
                                    description "Exclude a configuration group at this level";
                                }

                                container aa-sub {
                                    description "Enter the aa-sub context";

                                    choice sub-type {
                                        case esm {

                                            container esm {
                                                description "Enter the esm context";

                                                choice esm-op {
                                                    case eqesm {

                                                        leaf eq {
                                                            type types-sros:named-item;
                                                            description "Exact match criterion used for the ESM subscriber";
                                                        }

                                                    }
                                                    case neqesm {

                                                        leaf neq {
                                                            type types-sros:named-item;
                                                            description "Non-match criterion used for ESM subscriber";
                                                        }

                                                    }
                                                }
                                            } // container esm

                                        }
                                        case esm-mac {

                                            container esm-mac {
                                                description "Enter the esm-mac context";

                                                choice esm-mac-op {
                                                    case eqesmmac {

                                                        leaf eq {
                                                            type types-sros:named-item;
                                                            description "Exact match criterion used for ESM MAC subscriber";
                                                        }

                                                    }
                                                    case neqesmmac {

                                                        leaf neq {
                                                            type types-sros:named-item;
                                                            description "Non-match criterion used for AA subscriber ESM MAC";
                                                        }

                                                    }
                                                }
                                            } // container esm-mac

                                        }
                                        case transit {

                                            container transit {
                                                description "Enter the transit context";

                                                choice transit-op {
                                                    case eqtransit {

                                                        leaf eq {
                                                            type types-sros:named-item;
                                                            description "Exact match criterion used for a transit AA subscriber";
                                                        }

                                                    }
                                                    case neqtransit {

                                                        leaf neq {
                                                            type types-sros:named-item;
                                                            description "Non-match criterion used for a transit AA subscriber";
                                                        }

                                                    }
                                                }
                                            } // container transit

                                        }
                                        case sap {

                                            container sap {
                                                description "Enter the sap context";

                                                choice sap-op {
                                                    case eqsap {

                                                        leaf eq {
                                                            type types-sros:sap;
                                                            description "Exact match criterion used for the SAP subscriber";
                                                        }

                                                    }
                                                    case neqsap {

                                                        leaf neq {
                                                            type types-sros:sap;
                                                            description "Non-match criterion used for the SAP subscriber";
                                                        }

                                                    }
                                                }
                                            } // container sap

                                        }
                                        case spoke-sdp {

                                            container spoke-sdp {
                                                description "Enter the spoke-sdp context";

                                                choice spoke-sdp-op {
                                                    case eqspoke {

                                                        leaf eq {
                                                            type types-services:sdp-bind-id;
                                                            description "Exact match criterion used for a spoke SDP subscriber";
                                                        }

                                                    }
                                                    case neqspoke {

                                                        leaf neq {
                                                            type types-services:sdp-bind-id;
                                                            description "Non-match criterion used for a spoke SDP subscriber";
                                                        }

                                                    }
                                                }
                                            } // container spoke-sdp

                                        }
                                    }
                                } // container aa-sub

                                container application {
                                    description "Enter the application context";

                                    choice match-op-choice {
                                        case eq {

                                            leaf eq {
                                                type leafref {
                                                    path "../../../../../application/application-name";
                                                }
                                                description "Exact match criterion used for the application";
                                            }

                                        }
                                        case neq {

                                            leaf neq {
                                                type leafref {
                                                    path "../../../../../application/application-name";
                                                }
                                                description "Non-match criterion used for the application";
                                            }

                                        }
                                    }
                                } // container application

                                container app-group {
                                    description "Enter the app-group context";

                                    choice match-op-choice {
                                        case eq {

                                            leaf eq {
                                                type leafref {
                                                    path "../../../../../app-group/application-group-name";
                                                }
                                                description "Exact match criterion used for the application group";
                                            }

                                        }
                                        case neq {

                                            leaf neq {
                                                type leafref {
                                                    path "../../../../../app-group/application-group-name";
                                                }
                                                description "Non-match criterion used for the application group";
                                            }

                                        }
                                    }
                                } // container app-group

                                list characteristic {
                                    key "characteristic-name";
                                    description "Enter the characteristic list instance";

                                    leaf characteristic-name {
                                        type leafref {
                                            path "../../../../../app-service-options/characteristic/characteristic-name";
                                        }
                                        description "ASO characteristic name for AQP entry matching";
                                    }

                                    leaf-list apply-groups {
                                        type leafref {
                                            path "../../../../../../../../../groups/group/name";
                                        }
                                        max-elements 8;
                                        ordered-by user;
                                        description "Apply a configuration group at this level";
                                    }

                                    leaf-list apply-groups-exclude {
                                        type leafref {
                                            path "../../../../../../../../../groups/group/name";
                                        }
                                        max-elements 8;
                                        ordered-by user;
                                        description "Exclude a configuration group at this level";
                                    }

                                    choice aso-match-choice {
                                        mandatory true;
                                        case eq {

                                            leaf eq {
                                                type leafref {
                                                    path "../../../../../app-service-options/characteristic[characteristic-name=current()/../characteristic-name]/value/value-name";
                                                }
                                                description "Match criterion used for AQP match characteristic";
                                            }

                                        }
                                        case neq {

                                            leaf neq {
                                                type leafref {
                                                    path "../../../../../app-service-options/characteristic[characteristic-name=current()/../characteristic-name]/value/value-name";
                                                }
                                                description "Non-match criterion used for AQP match characteristic";
                                            }

                                        }
                                    }
                                } // list characteristic

                                container charging-group {
                                    description "Enter the charging-group context";

                                    choice match-op-choice {
                                        case eq {

                                            leaf eq {
                                                type leafref {
                                                    path "../../../../../charging-group/charging-group-name";
                                                }
                                                description "Match criterion used for the charging group";
                                            }

                                        }
                                        case neq {

                                            leaf neq {
                                                type leafref {
                                                    path "../../../../../charging-group/charging-group-name";
                                                }
                                                description "Non-match criterion used for the charging group";
                                            }

                                        }
                                    }
                                } // container charging-group

                                container dscp {
                                    description "Enter the dscp context";

                                    choice match-op-choice {
                                        case eq {

                                            leaf eq {
                                                type types-qos:dscp-name;
                                                description "Exact match criterion used for the DSCP";
                                            }

                                        }
                                        case neq {

                                            leaf neq {
                                                type types-qos:dscp-name;
                                                description "Non-match criterion used for the DSCP";
                                            }

                                        }
                                    }
                                } // container dscp

                                container dst-ip {
                                    description "Enter the dst-ip context";

                                    choice match-op-choice {
                                        case eq {

                                            container eq {
                                                description "Enter the eq context";

                                                choice eq-addr-choice {
                                                    case ip-prefix {

                                                        leaf ip-prefix {
                                                            type types-sros:ip-prefix;
                                                            description "IP address prefix used for match criterion";
                                                        }

                                                    }
                                                    case ip-prefix-list {

                                                        leaf ip-prefix-list {
                                                            type leafref {
                                                                path "../../../../../../../ip-prefix-list/ip-prefix-list-name";
                                                            }
                                                            description "IP address prefix list used for match criterion";
                                                        }

                                                    }
                                                }
                                            } // container eq

                                        }
                                        case neq {

                                            container neq {
                                                description "Enter the neq context";

                                                choice neq-addr-choice {
                                                    case ip-prefix {

                                                        leaf ip-prefix {
                                                            type types-sros:ip-prefix;
                                                            description "IP address prefix used for match criterion";
                                                        }

                                                    }
                                                    case ip-prefix-list {

                                                        leaf ip-prefix-list {
                                                            type leafref {
                                                                path "../../../../../../../ip-prefix-list/ip-prefix-list-name";
                                                            }
                                                            description "IP address prefix list used for match criterion";
                                                        }

                                                    }
                                                }
                                            } // container neq

                                        }
                                    }
                                } // container dst-ip

                                container dst-port {
                                    description "Enter the dst-port context";

                                    choice match-op-choice {
                                        case eq {

                                            container eq {
                                                description "Enter the eq context";

                                                choice eq-port-choice {
                                                    case port-number {

                                                        leaf port-number {
                                                            type types-sros:tcp-udp-port;
                                                            default "0";
                                                            description "Server port number used as match criterion";
                                                        }

                                                    }
                                                    case range {

                                                        container range {
                                                            description "Enter the range context";

                                                            leaf start {
                                                                type types-sros:tcp-udp-port;
                                                                default "0";
                                                                description "TCP/UDP starting port number";
                                                            }

                                                            leaf end {
                                                                type types-sros:tcp-udp-port;
                                                                default "1";
                                                                description "TCP/UDP ending port number";
                                                            }

                                                        } // container range

                                                    }
                                                    case port-list {

                                                        leaf port-list {
                                                            type leafref {
                                                                path "../../../../../../../port-list/port-list-name";
                                                            }
                                                            description "IP port list used as match criterion";
                                                        }

                                                    }
                                                }
                                            } // container eq

                                        }
                                        case neq {

                                            container neq {
                                                description "Enter the neq context";

                                                choice neq-port-choice {
                                                    case port-number {

                                                        leaf port-number {
                                                            type types-sros:tcp-udp-port;
                                                            default "0";
                                                            description "Server port number used as match criterion";
                                                        }

                                                    }
                                                    case range {

                                                        container range {
                                                            description "Enter the range context";

                                                            leaf start {
                                                                type types-sros:tcp-udp-port;
                                                                default "0";
                                                                description "TCP/UDP starting port number";
                                                            }

                                                            leaf end {
                                                                type types-sros:tcp-udp-port;
                                                                default "1";
                                                                description "TCP/UDP ending port number";
                                                            }

                                                        } // container range

                                                    }
                                                    case port-list {

                                                        leaf port-list {
                                                            type leafref {
                                                                path "../../../../../../../port-list/port-list-name";
                                                            }
                                                            description "IP port list used as match criterion";
                                                        }

                                                    }
                                                }
                                            } // container neq

                                        }
                                    }
                                } // container dst-port

                                container ip-protocol {
                                    description "Enter the ip-protocol context";

                                    choice match-op-choice {
                                        case eq {

                                            leaf eq {
                                                type types-sros:match-ip-protocol;
                                                description "Exact match criterion used for the IP protocol";
                                            }

                                        }
                                        case neq {

                                            leaf neq {
                                                type types-sros:match-ip-protocol;
                                                description "Non-match criterion used for the IP protocol";
                                            }

                                        }
                                    }
                                } // container ip-protocol

                                container src-ip {
                                    description "Enter the src-ip context";

                                    choice match-op-choice {
                                        case eq {

                                            container eq {
                                                description "Enter the eq context";

                                                choice eq-addr-choice {
                                                    case ip-prefix {

                                                        leaf ip-prefix {
                                                            type types-sros:ip-prefix;
                                                            description "IP address prefix used for match criterion";
                                                        }

                                                    }
                                                    case ip-prefix-list {

                                                        leaf ip-prefix-list {
                                                            type leafref {
                                                                path "../../../../../../../ip-prefix-list/ip-prefix-list-name";
                                                            }
                                                            description "IP address prefix list used for match criterion";
                                                        }

                                                    }
                                                }
                                            } // container eq

                                        }
                                        case neq {

                                            container neq {
                                                description "Enter the neq context";

                                                choice neq-addr-choice {
                                                    case ip-prefix {

                                                        leaf ip-prefix {
                                                            type types-sros:ip-prefix;
                                                            description "IP address prefix used for match criterion";
                                                        }

                                                    }
                                                    case ip-prefix-list {

                                                        leaf ip-prefix-list {
                                                            type leafref {
                                                                path "../../../../../../../ip-prefix-list/ip-prefix-list-name";
                                                            }
                                                            description "IP address prefix list used for match criterion";
                                                        }

                                                    }
                                                }
                                            } // container neq

                                        }
                                    }
                                } // container src-ip

                                container src-port {
                                    description "Enter the src-port context";

                                    choice match-op-choice {
                                        case eq {

                                            container eq {
                                                description "Enter the eq context";

                                                choice eq-port-choice {
                                                    case port-number {

                                                        leaf port-number {
                                                            type types-sros:tcp-udp-port;
                                                            default "0";
                                                            description "Server port number used as match criterion";
                                                        }

                                                    }
                                                    case range {

                                                        container range {
                                                            description "Enter the range context";

                                                            leaf start {
                                                                type types-sros:tcp-udp-port;
                                                                default "0";
                                                                description "TCP/UDP starting port number";
                                                            }

                                                            leaf end {
                                                                type types-sros:tcp-udp-port;
                                                                default "1";
                                                                description "TCP/UDP ending port number";
                                                            }

                                                        } // container range

                                                    }
                                                    case port-list {

                                                        leaf port-list {
                                                            type leafref {
                                                                path "../../../../../../../port-list/port-list-name";
                                                            }
                                                            description "IP port list used as match criterion";
                                                        }

                                                    }
                                                }
                                            } // container eq

                                        }
                                        case neq {

                                            container neq {
                                                description "Enter the neq context";

                                                choice neq-port-choice {
                                                    case port-number {

                                                        leaf port-number {
                                                            type types-sros:tcp-udp-port;
                                                            default "0";
                                                            description "Server port number used as match criterion";
                                                        }

                                                    }
                                                    case range {

                                                        container range {
                                                            description "Enter the range context";

                                                            leaf start {
                                                                type types-sros:tcp-udp-port;
                                                                default "0";
                                                                description "TCP/UDP starting port number";
                                                            }

                                                            leaf end {
                                                                type types-sros:tcp-udp-port;
                                                                default "1";
                                                                description "TCP/UDP ending port number";
                                                            }

                                                        } // container range

                                                    }
                                                    case port-list {

                                                        leaf port-list {
                                                            type leafref {
                                                                path "../../../../../../../port-list/port-list-name";
                                                            }
                                                            description "IP port list used as match criterion";
                                                        }

                                                    }
                                                }
                                            } // container neq

                                        }
                                    }
                                } // container src-port

                                list flow-attribute {
                                    key "flow-attribute-name";
                                    max-elements 10;
                                    description "Enter the flow-attribute list instance";

                                    leaf flow-attribute-name {
                                        type types-sros:named-item;
                                        description "Flow attribute name used as match criterion";
                                    }

                                    leaf-list apply-groups {
                                        type leafref {
                                            path "../../../../../../../../../groups/group/name";
                                        }
                                        max-elements 8;
                                        ordered-by user;
                                        description "Apply a configuration group at this level";
                                    }

                                    leaf-list apply-groups-exclude {
                                        type leafref {
                                            path "../../../../../../../../../groups/group/name";
                                        }
                                        max-elements 8;
                                        ordered-by user;
                                        description "Exclude a configuration group at this level";
                                    }

                                    container confidence {
                                        description "Enter the confidence context";

                                        choice match-op-choice {
                                            case eq {

                                                leaf eq {
                                                    type uint32 {
                                                        range "0..100";
                                                    }
                                                    description "Exact match criterion used for the flow-attribute confidence";
                                                }

                                            }
                                            case lt {

                                                leaf lt {
                                                    type uint32 {
                                                        range "1..100";
                                                    }
                                                    description "Less than value for confidence match criterion";
                                                }

                                            }
                                            case gte {

                                                leaf gte {
                                                    type uint32 {
                                                        range "0..100";
                                                    }
                                                    description "Greater than or equal to for confidence match criterion";
                                                }

                                            }
                                        }
                                    } // container confidence

                                } // list flow-attribute

                            } // container match

                            container action {
                                description "Enter the action context";

                                leaf abandon-tcp-optimization {
                                    type boolean;
                                    default "false";
                                    description "Enable abandoning TCP optimization for this entry";
                                }

                                leaf dns-ip-cache {
                                    type leafref {
                                        path "../../../../../../dns-ip-cache/dns-ip-cache-name";
                                    }
                                    description "DNS IP cache name";
                                }

                                leaf drop {
                                    type boolean;
                                    default "false";
                                    description "Enable drop action for the AQP entry";
                                }

                                leaf gtp-filter {
                                    type leafref {
                                        path "../../../../../gtp/gtp-filter/gtp-filter-name";
                                    }
                                    description "GTP filter executed for flows matching this AQP entry";
                                }

                                leaf http-enrich {
                                    type leafref {
                                        path "../../../../../../http-enrich/http-enrich-name";
                                    }
                                    description "HTTP header enrichment action for the AQP entry";
                                }

                                leaf http-error-redirect {
                                    type leafref {
                                        path "../../../../../../http-error-redirect/http-error-redirect-name";
                                    }
                                    description "HTTP error redirect for the AQP entry";
                                }

                                leaf http-notification {
                                    type leafref {
                                        path "../../../../../../http-notification/http-notification-name";
                                    }
                                    description "HTTP notification to use for flows matching AQP entry";
                                }

                                leaf sctp-filter {
                                    type leafref {
                                        path "../../../../../sctp-filter/sctp-filter-name";
                                    }
                                    description "SCTP filter to use for flows matching the AQP entry";
                                }

                                leaf session-filter {
                                    type leafref {
                                        path "../../../../../session-filter/session-filter-name";
                                    }
                                    description "Session filter to use for flows matching the AQP entry";
                                }

                                leaf tcp-mss-adjust {
                                    type types-aa:tcp-segment-size;
                                    description "TCP MSS adjustment traffic action and size";
                                }

                                leaf tcp-validate {
                                    type leafref {
                                        path "../../../../../tcp-validate/tcp-validate-name";
                                    }
                                    description "TCP validation policy action for entry matching flows";
                                }

                                leaf tls-enrich {
                                    type leafref {
                                        path "../../../../../../http-enrich/http-enrich-name";
                                    }
                                    description "HTTP TLS enrichment action for the AQP entry";
                                }

                                leaf-list apply-groups {
                                    type leafref {
                                        path "../../../../../../../../groups/group/name";
                                    }
                                    max-elements 8;
                                    ordered-by user;
                                    description "Apply a configuration group at this level";
                                }

                                leaf-list apply-groups-exclude {
                                    type leafref {
                                        path "../../../../../../../../groups/group/name";
                                    }
                                    max-elements 8;
                                    ordered-by user;
                                    description "Exclude a configuration group at this level";
                                }

                                container bandwidth-policer {
                                    description "Enter the bandwidth-policer context";

                                    choice bw-policer {
                                        case anl {

                                            leaf anl {
                                                type leafref {
                                                    path "../../../../../../../policer/anl-bandwidth-policer/policer-name";
                                                }
                                                description "Access network locator bandwidth policer";
                                            }

                                        }
                                        case dual-bucket {

                                            leaf dual-bucket {
                                                type leafref {
                                                    path "../../../../../../../policer/dual-bucket-bandwidth-policer/policer-name";
                                                }
                                                description "Dual bucket bandwidth limiting policer";
                                            }

                                        }
                                        case single-bucket {

                                            leaf single-bucket {
                                                type leafref {
                                                    path "../../../../../../../policer/single-bucket-bandwidth-policer/policer-name";
                                                }
                                                description "Single bucket bandwidth limiting policer";
                                            }

                                        }
                                    }
                                } // container bandwidth-policer

                                container error-drop {
                                    presence "Enable the error-drop context";
                                    description "Enable the error-drop context";

                                    leaf event-log {
                                        type leafref {
                                            path "../../../../../../event-log/event-log-name";
                                        }
                                        description "Event log action for the AQP entry";
                                    }

                                } // container error-drop

                                container flow-count-limit-policer {
                                    description "Enter the flow-count-limit-policer context";

                                    leaf policer-name {
                                        type leafref {
                                            path "../../../../../../../policer/flow-count-limit-policer/policer-name";
                                        }
                                        description "Policer name";
                                    }

                                    leaf event-log {
                                        type leafref {
                                            path "../../../../../../event-log/event-log-name";
                                        }
                                        description "Event log name";
                                    }

                                } // container flow-count-limit-policer

                                container flow-setup-rate-policer {
                                    description "Enter the flow-setup-rate-policer context";

                                    leaf policer-name {
                                        type leafref {
                                            path "../../../../../../../policer/flow-setup-rate-policer/policer-name";
                                        }
                                        description "Policer name";
                                    }

                                    leaf event-log {
                                        type leafref {
                                            path "../../../../../../event-log/event-log-name";
                                        }
                                        description "Flow drop events log name due to flow-setup rate policer";
                                    }

                                } // container flow-setup-rate-policer

                                container fragment-drop {
                                    description "Enter the fragment-drop context";

                                    leaf drop-scope {
                                        type types-aa:fragment-drop-scope;
                                        description "Fragment-drop scope";
                                    }

                                    leaf event-log {
                                        type leafref {
                                            path "../../../../../../event-log/event-log-name";
                                        }
                                        description "Event log name";
                                    }

                                } // container fragment-drop

                                container http-redirect {
                                    description "Enter the http-redirect context";

                                    leaf flow-type {
                                        type types-aa:http-redir-flow-type;
                                        description "Flow type for HTTP redirect of flows matching the entry";
                                    }

                                    leaf name {
                                        type leafref {
                                            path "../../../../../../../http-redirect/http-redirect-name";
                                        }
                                        description "HTTP redirect policy name";
                                    }

                                } // container http-redirect

                                container mirror-source {
                                    description "Enter the mirror-source context";

                                    leaf mirror-service {
                                        type leafref {
                                            path "../../../../../../../../../mirror/mirror-dest/service-name";
                                        }
                                        description "Mirror source service ID for flows matching the entry";
                                    }

                                    leaf all-inclusive {
                                        type boolean;
                                        default "false";
                                        description "Mirror flows matching the AQP subscriber default policy";
                                    }

                                } // container mirror-source

                                container overload-drop {
                                    presence "Enable the overload-drop context";
                                    description "Enable the overload-drop context";

                                    leaf event-log {
                                        type leafref {
                                            path "../../../../../../event-log/event-log-name";
                                        }
                                        description "Event log name";
                                    }

                                } // container overload-drop

                                container remark {
                                    description "Enter the remark context";

                                    leaf fc {
                                        type types-sros:fc-name;
                                        description "FC remark action for flows matching this entry";
                                    }

                                    leaf priority {
                                        type types-qos:priority;
                                        description "Priority to use to remark flows matching this entry";
                                    }

                                    container dscp {
                                        description "Enter the dscp context";

                                        leaf in-profile {
                                            type types-qos:dscp-name;
                                            description "DSCP name to remark matching in-profile flows";
                                        }

                                        leaf out-profile {
                                            type types-qos:dscp-name;
                                            description "DSCP name to remark matching out-of-profile flows";
                                        }

                                    } // container dscp

                                } // container remark

                                container url-filter {
                                    description "Enter the url-filter context";

                                    leaf characteristic {
                                        type leafref {
                                            path "../../../../../app-service-options/characteristic/characteristic-name";
                                        }
                                        description "URL filter characteristic used for matching AQP entries";
                                    }

                                    leaf name {
                                        type leafref {
                                            path "../../../../../../../url-filter/url-filter-name";
                                        }
                                        description "URL filter name";
                                    }

                                } // container url-filter

                            } // container action

                        } // list entry

                    } // container app-qos-policy

                } // container policy

                list transit-ip-policy {
                    key "ip-policy-id";
                    description "Enter the transit-ip-policy list instance";

                    leaf ip-policy-id {
                        type uint32 {
                            range "1..65535";
                        }
                        description "IP transit policy ID";
                    }

                    leaf description {
                        type types-sros:description;
                        description "Text description";
                    }

                    leaf default-app-profile {
                        type leafref {
                            path "../../policy/app-profile/app-profile-name";
                        }
                        description "Default AA application profile";
                    }

                    leaf detect-seen-ip {
                        type boolean;
                        default "false";
                        description "Detect transit subscribers based on IP address";
                    }

                    leaf ipv6-address-prefix-length {
                        type uint32 {
                            range "32..64";
                        }
                        description "Length of the AA transit IP policy IPv6 address prefix";
                    }

                    leaf sub-ident-policy {
                        type leafref {
                            path "../../../../../subscriber-mgmt/sub-ident-policy/name";
                        }
                        description "Subscriber identification policy";
                    }

                    leaf-list apply-groups {
                        type leafref {
                            path "../../../../../groups/group/name";
                        }
                        max-elements 8;
                        ordered-by user;
                        description "Apply a configuration group at this level";
                    }

                    leaf-list apply-groups-exclude {
                        type leafref {
                            path "../../../../../groups/group/name";
                        }
                        max-elements 8;
                        ordered-by user;
                        description "Exclude a configuration group at this level";
                    }

                    container dhcp {
                        description "Enter the dhcp context";

                        leaf admin-state {
                            type types-sros:admin-state;
                            default "disable";
                            description "Administrative state for learning DHCP dynamic transits";
                        }

                    } // container dhcp

                    container diameter {
                        description "Enter the diameter context";

                        leaf admin-state {
                            type types-sros:admin-state;
                            default "disable";
                            description "Administrative state for Diameter dynamic transits";
                        }

                        leaf application-policy {
                            type leafref {
                                path "../../../../../../subscriber-mgmt/diameter-gx-policy/name";
                            }
                            description "Diameter application policy name for IP transit policy";
                        }

                    } // container diameter

                    container radius {
                        description "Enter the radius context";

                        leaf admin-state {
                            type types-sros:admin-state;
                            default "disable";
                            description "Administrative state of learning RADIUS dynamic transit";
                        }

                        leaf authentication-policy {
                            type leafref {
                                path "../../../../../../subscriber-mgmt/radius-authentication-policy/name";
                            }
                            description "RADIUS authentication policy";
                        }

                        leaf seen-ip-radius-acct-policy {
                            type leafref {
                                path "../../../../../radius-accounting-policy/rad-acct-plcy-name";
                            }
                            description "RADIUS accounting policy to enable seen-IP notification";
                        }

                    } // container radius

                    container transit-auto-create {
                        description "Enter the transit-auto-create context";

                        leaf admin-state {
                            type types-sros:admin-state;
                            default "disable";
                            description "Administrative state of the automatic dynamic transits";
                        }

                        leaf inactivity-monitor {
                            type boolean;
                            default "false";
                            description "Monitor inactivity on auto-created transit subscribers";
                        }

                    } // container transit-auto-create

                    list static-aa-sub {
                        key "transit-aa-sub-name";
                        description "Enter the static-aa-sub list instance";

                        leaf transit-aa-sub-name {
                            type types-sros:named-item;
                            description "Static transit subscriber name";
                        }

                        leaf app-profile {
                            type leafref {
                                path "../../../policy/app-profile/app-profile-name";
                            }
                            mandatory true;
                            description "Application profile name";
                        }

                        leaf-list apply-groups {
                            type leafref {
                                path "../../../../../../groups/group/name";
                            }
                            max-elements 8;
                            ordered-by user;
                            description "Apply a configuration group at this level";
                        }

                        leaf-list apply-groups-exclude {
                            type leafref {
                                path "../../../../../../groups/group/name";
                            }
                            max-elements 8;
                            ordered-by user;
                            description "Exclude a configuration group at this level";
                        }

                        list ip {
                            key "address";
                            max-elements 32;
                            description "Add a list entry for ip";

                            leaf address {
                                type types-aa:transit-ip-policy-sub-address;
                                description "IP address for an AA static transit subscriber";
                            }

                        } // list ip

                    } // list static-aa-sub

                } // list transit-ip-policy

                list transit-prefix-policy {
                    key "prefix-policy-id";
                    description "Enter the transit-prefix-policy list instance";

                    leaf prefix-policy-id {
                        type uint32 {
                            range "1..65535";
                        }
                        description "Transit prefix policy ID";
                    }

                    leaf description {
                        type types-sros:description;
                        description "Text description";
                    }

                    leaf-list apply-groups {
                        type leafref {
                            path "../../../../../groups/group/name";
                        }
                        max-elements 8;
                        ordered-by user;
                        description "Apply a configuration group at this level";
                    }

                    leaf-list apply-groups-exclude {
                        type leafref {
                            path "../../../../../groups/group/name";
                        }
                        max-elements 8;
                        ordered-by user;
                        description "Exclude a configuration group at this level";
                    }

                    list static-aa-sub {
                        key "transit-aa-sub-name";
                        max-elements 4095;
                        description "Enter the static-aa-sub list instance";

                        leaf transit-aa-sub-name {
                            type types-sros:named-item;
                            description "Static transit subscriber name";
                        }

                        leaf app-profile {
                            type leafref {
                                path "../../../policy/app-profile/app-profile-name";
                            }
                            mandatory true;
                            description "Application profile name";
                        }

                        leaf is-remote {
                            type boolean;
                            sros-ext:immutable;
                            mandatory true;
                            description "Set transit subscriber as remote";
                        }

                        leaf-list apply-groups {
                            type leafref {
                                path "../../../../../../groups/group/name";
                            }
                            max-elements 8;
                            ordered-by user;
                            description "Apply a configuration group at this level";
                        }

                        leaf-list apply-groups-exclude {
                            type leafref {
                                path "../../../../../../groups/group/name";
                            }
                            max-elements 8;
                            ordered-by user;
                            description "Exclude a configuration group at this level";
                        }

                    } // list static-aa-sub

                    list entry {
                        key "entry-id";
                        max-elements 4095;
                        description "Enter the entry list instance";

                        leaf entry-id {
                            type uint32 {
                                range "1..max";
                            }
                            description "ID for a transit prefix policy entry";
                        }

                        leaf aa-sub {
                            type leafref {
                                path "../../static-aa-sub/transit-aa-sub-name";
                            }
                            description "Name of the transit prefix AA subscriber";
                        }

                        leaf-list apply-groups {
                            type leafref {
                                path "../../../../../../groups/group/name";
                            }
                            max-elements 8;
                            ordered-by user;
                            description "Apply a configuration group at this level";
                        }

                        leaf-list apply-groups-exclude {
                            type leafref {
                                path "../../../../../../groups/group/name";
                            }
                            max-elements 8;
                            ordered-by user;
                            description "Exclude a configuration group at this level";
                        }

                        container match {
                            description "Enter the match context";

                            leaf aa-sub-ip {
                                type types-sros:ip-prefix;
                                description "AA subscriber IP address prefix";
                            }

                            leaf network-ip {
                                type types-sros:ip-prefix;
                                description "Network IP address prefix";
                            }

                        } // container match

                    } // list entry

                } // list transit-prefix-policy

                container cflowd {
                    description "Enter the cflowd context";

                    list export-type {
                        key "flow-export-type";
                        description "Enter the export-type list instance";

                        leaf flow-export-type {
                            type types-aa:cflowd-export-type;
                            description "Cflowd flow export type for the partition";
                        }

                        leaf admin-state {
                            type types-sros:admin-state;
                            description "Administrative state of cflowd export";
                        }

                        leaf-list apply-groups {
                            type leafref {
                                path "../../../../../../groups/group/name";
                            }
                            max-elements 8;
                            ordered-by user;
                            description "Apply a configuration group at this level";
                        }

                        leaf-list apply-groups-exclude {
                            type leafref {
                                path "../../../../../../groups/group/name";
                            }
                            max-elements 8;
                            ordered-by user;
                            description "Exclude a configuration group at this level";
                        }

                        list app-group {
                            when "../flow-export-type = 'tcp-performance' or ../flow-export-type = 'rtp-performance' or ../flow-export-type = 'comprehensive'";
                            key "app-group-name";
                            description "Enter the app-group list instance";

                            leaf app-group-name {
                                type leafref {
                                    path "../../../../policy/app-group/application-group-name";
                                }
                                description "Application group name";
                            }

                            leaf rate-choice {
                                type enumeration {
                                    enum "flow-rate"                    { value 1; }
                                    enum "flow-rate-2"                  { value 2; }
                                }
                                default "flow-rate";
                                description "Cflowd rate to use for sampling";
                            }

                            leaf-list apply-groups {
                                type leafref {
                                    path "../../../../../../../groups/group/name";
                                }
                                max-elements 8;
                                ordered-by user;
                                description "Apply a configuration group at this level";
                            }

                            leaf-list apply-groups-exclude {
                                type leafref {
                                    path "../../../../../../../groups/group/name";
                                }
                                max-elements 8;
                                ordered-by user;
                                description "Exclude a configuration group at this level";
                            }

                        } // list app-group

                        list application {
                            when "../flow-export-type = 'tcp-performance' or ../flow-export-type = 'rtp-performance' or ../flow-export-type = 'comprehensive'";
                            key "application-name";
                            description "Enter the application list instance";

                            leaf application-name {
                                type leafref {
                                    path "../../../../policy/application/application-name";
                                }
                                description "Application name";
                            }

                            leaf rate-choice {
                                type enumeration {
                                    enum "flow-rate"                    { value 1; }
                                    enum "flow-rate-2"                  { value 2; }
                                }
                                default "flow-rate";
                                description "Cflowd rate to use for sampling";
                            }

                            leaf-list apply-groups {
                                type leafref {
                                    path "../../../../../../../groups/group/name";
                                }
                                max-elements 8;
                                ordered-by user;
                                description "Apply a configuration group at this level";
                            }

                            leaf-list apply-groups-exclude {
                                type leafref {
                                    path "../../../../../../../groups/group/name";
                                }
                                max-elements 8;
                                ordered-by user;
                                description "Exclude a configuration group at this level";
                            }

                        } // list application

                    } // list export-type

                } // container cflowd

                container statistics {
                    description "Enter the statistics context";

                    container aa-protocol {
                        description "Enter the aa-protocol context";

                        leaf accounting-policy {
                            type leafref {
                                path "../../../../../../log/accounting-policy/policy-id";
                            }
                            description "Accounting policy ID";
                        }

                        leaf collect-stats {
                            type boolean;
                            default "false";
                            description "Collect statistics";
                        }

                        leaf admin-state {
                            type types-sros:admin-state;
                            default "disable";
                            description "Administrative state of protocol statistics";
                        }

                        leaf-list apply-groups {
                            type leafref {
                                path "../../../../../../groups/group/name";
                            }
                            max-elements 8;
                            ordered-by user;
                            description "Apply a configuration group at this level";
                        }

                        leaf-list apply-groups-exclude {
                            type leafref {
                                path "../../../../../../groups/group/name";
                            }
                            max-elements 8;
                            ordered-by user;
                            description "Exclude a configuration group at this level";
                        }

                    } // container aa-protocol

                    container aa-application {
                        description "Enter the aa-application context";

                        leaf accounting-policy {
                            type leafref {
                                path "../../../../../../log/accounting-policy/policy-id";
                            }
                            description "Accounting policy ID";
                        }

                        leaf collect-stats {
                            type boolean;
                            default "false";
                            description "Collect statistics";
                        }

                        leaf-list apply-groups {
                            type leafref {
                                path "../../../../../../groups/group/name";
                            }
                            max-elements 8;
                            ordered-by user;
                            description "Apply a configuration group at this level";
                        }

                        leaf-list apply-groups-exclude {
                            type leafref {
                                path "../../../../../../groups/group/name";
                            }
                            max-elements 8;
                            ordered-by user;
                            description "Exclude a configuration group at this level";
                        }

                    } // container aa-application

                    container aa-app-group {
                        description "Enter the aa-app-group context";

                        leaf accounting-policy {
                            type leafref {
                                path "../../../../../../log/accounting-policy/policy-id";
                            }
                            description "Accounting policy ID";
                        }

                        leaf collect-stats {
                            type boolean;
                            default "false";
                            description "Collect statistics";
                        }

                        leaf-list apply-groups {
                            type leafref {
                                path "../../../../../../groups/group/name";
                            }
                            max-elements 8;
                            ordered-by user;
                            description "Apply a configuration group at this level";
                        }

                        leaf-list apply-groups-exclude {
                            type leafref {
                                path "../../../../../../groups/group/name";
                            }
                            max-elements 8;
                            ordered-by user;
                            description "Exclude a configuration group at this level";
                        }

                    } // container aa-app-group

                    container aa-sub {
                        description "Enter the aa-sub context";

                        leaf accounting-policy {
                            type leafref {
                                path "../../../../../../log/accounting-policy/policy-id";
                            }
                            description "Accounting policy ID";
                        }

                        leaf collect-stats {
                            type boolean;
                            default "false";
                            description "Collect statistics";
                        }

                        leaf-list aggregate-stats-export-using {
                            type enumeration {
                                enum "accounting-policy"            { value 1; }
                                enum "radius-accounting-policy"     { value 2; }
                            }
                            max-elements 2;
                            description "Method of statistics export to be used";
                        }

                        leaf exclude-tcp-retrans {
                            type boolean;
                            default "false";
                            description "Exclude TCP retransmission and error statistics";
                        }

                        leaf max-throughput-stats {
                            type boolean;
                            default "false";
                            description "Collect maximum throughput statistics";
                        }

                        leaf radius-accounting-policy {
                            type leafref {
                                path "../../../../../radius-accounting-policy/rad-acct-plcy-name";
                            }
                            description "RADIUS accounting policy name";
                        }

                        leaf usage-monitoring {
                            type boolean;
                            default "false";
                            description "Collect usage monitoring statistics";
                        }

                        leaf-list apply-groups {
                            type leafref {
                                path "../../../../../../groups/group/name";
                            }
                            max-elements 8;
                            ordered-by user;
                            description "Apply a configuration group at this level";
                        }

                        leaf-list apply-groups-exclude {
                            type leafref {
                                path "../../../../../../groups/group/name";
                            }
                            max-elements 8;
                            ordered-by user;
                            description "Exclude a configuration group at this level";
                        }

                        list charging-group {
                            key "charging-group-name";
                            description "Enter the charging-group list instance";

                            leaf charging-group-name {
                                type leafref {
                                    path "../../../../policy/charging-group/charging-group-name";
                                }
                                description "Charging group name";
                            }

                            leaf-list export-using {
                                type enumeration {
                                    enum "accounting-policy"            { value 1; }
                                    enum "radius-accounting-policy"     { value 2; }
                                }
                                max-elements 2;
                                description "Method used to export statistics";
                            }

                            leaf-list apply-groups {
                                type leafref {
                                    path "../../../../../../../groups/group/name";
                                }
                                max-elements 8;
                                ordered-by user;
                                description "Apply a configuration group at this level";
                            }

                            leaf-list apply-groups-exclude {
                                type leafref {
                                    path "../../../../../../../groups/group/name";
                                }
                                max-elements 8;
                                ordered-by user;
                                description "Exclude a configuration group at this level";
                            }

                        } // list charging-group

                        list app-group {
                            key "app-group-name";
                            description "Enter the app-group list instance";

                            leaf app-group-name {
                                type leafref {
                                    path "../../../../policy/app-group/application-group-name";
                                }
                                description "Application group name";
                            }

                            leaf-list export-using {
                                type enumeration {
                                    enum "accounting-policy"            { value 1; }
                                    enum "radius-accounting-policy"     { value 2; }
                                }
                                max-elements 2;
                                description "Method used to export statistics";
                            }

                            leaf-list apply-groups {
                                type leafref {
                                    path "../../../../../../../groups/group/name";
                                }
                                max-elements 8;
                                ordered-by user;
                                description "Apply a configuration group at this level";
                            }

                            leaf-list apply-groups-exclude {
                                type leafref {
                                    path "../../../../../../../groups/group/name";
                                }
                                max-elements 8;
                                ordered-by user;
                                description "Exclude a configuration group at this level";
                            }

                        } // list app-group

                        list application {
                            key "application-name";
                            description "Enter the application list instance";

                            leaf application-name {
                                type leafref {
                                    path "../../../../policy/application/application-name";
                                }
                                description "Application name";
                            }

                            leaf-list export-using {
                                type enumeration {
                                    enum "accounting-policy"            { value 1; }
                                    enum "radius-accounting-policy"     { value 2; }
                                }
                                max-elements 2;
                                description "Method used to export statistics";
                            }

                            leaf-list apply-groups {
                                type leafref {
                                    path "../../../../../../../groups/group/name";
                                }
                                max-elements 8;
                                ordered-by user;
                                description "Apply a configuration group at this level";
                            }

                            leaf-list apply-groups-exclude {
                                type leafref {
                                    path "../../../../../../../groups/group/name";
                                }
                                max-elements 8;
                                ordered-by user;
                                description "Exclude a configuration group at this level";
                            }

                        } // list application

                        list protocol {
                            key "protocol-name";
                            description "Enter the protocol list instance";

                            leaf protocol-name {
                                type types-sros:named-item;
                                description "AA protocol name";
                            }

                            leaf-list export-using {
                                type enumeration {
                                    enum "accounting-policy"            { value 1; }
                                    enum "radius-accounting-policy"     { value 2; }
                                }
                                max-elements 2;
                                description "Method used to export statistics";
                            }

                            leaf-list apply-groups {
                                type leafref {
                                    path "../../../../../../../groups/group/name";
                                }
                                max-elements 8;
                                ordered-by user;
                                description "Apply a configuration group at this level";
                            }

                            leaf-list apply-groups-exclude {
                                type leafref {
                                    path "../../../../../../../groups/group/name";
                                }
                                max-elements 8;
                                ordered-by user;
                                description "Exclude a configuration group at this level";
                            }

                        } // list protocol

                    } // container aa-sub

                    container aa-admit-deny {
                        description "Enter the aa-admit-deny context";

                        leaf accounting-policy {
                            type leafref {
                                path "../../../../../../log/accounting-policy/policy-id";
                            }
                            description "Accounting policy";
                        }

                        leaf collect-stats {
                            type boolean;
                            default "false";
                            description "Collect statistics";
                        }

                        leaf gtp-filter-stats {
                            type boolean;
                            default "false";
                            description "Include GTP filter statistics in admit-deny accounting records";
                        }

                        leaf policer-stats {
                            type boolean;
                            default "false";
                            description "Include admit-deny policer statistics in accounting records";
                        }

                        leaf policer-stats-resources {
                            type boolean;
                            default "false";
                            description "Allocate ISA/ ESA resources for policer admit-deny statistics";
                        }

                        leaf sctp-filter-stats {
                            type boolean;
                            default "false";
                            description "Include SCTP filter admit-deny statistics in accounting";
                        }

                        leaf session-filter-stats {
                            type boolean;
                            default "false";
                            description "Include session filter admit-deny statistics in accounting";
                        }

                        leaf tcp-validate-stats {
                            type boolean;
                            default "false";
                            description "Include TCP validate admit-deny statistics in accounting";
                        }

                        leaf-list apply-groups {
                            type leafref {
                                path "../../../../../../groups/group/name";
                            }
                            max-elements 8;
                            ordered-by user;
                            description "Apply a configuration group at this level";
                        }

                        leaf-list apply-groups-exclude {
                            type leafref {
                                path "../../../../../../groups/group/name";
                            }
                            max-elements 8;
                            ordered-by user;
                            description "Exclude a configuration group at this level";
                        }

                    } // container aa-admit-deny

                    container aa-partition {
                        description "Enter the aa-partition context";

                        leaf accounting-policy {
                            type leafref {
                                path "../../../../../../log/accounting-policy/policy-id";
                            }
                            description "Accounting policy";
                        }

                        leaf collect-stats {
                            type boolean;
                            default "false";
                            description "Collect statistics";
                        }

                        leaf tethering-stats {
                            type boolean;
                            default "false";
                            description "Collect tethering statistics";
                        }

                        leaf traffic-type-stats {
                            type boolean;
                            default "false";
                            description "Collect traffic type statistics";
                        }

                        leaf-list apply-groups {
                            type leafref {
                                path "../../../../../../groups/group/name";
                            }
                            max-elements 8;
                            ordered-by user;
                            description "Apply a configuration group at this level";
                        }

                        leaf-list apply-groups-exclude {
                            type leafref {
                                path "../../../../../../groups/group/name";
                            }
                            max-elements 8;
                            ordered-by user;
                            description "Exclude a configuration group at this level";
                        }

                    } // container aa-partition

                    list aa-sub-study {
                        key "study-type";
                        description "Enter the aa-sub-study list instance";

                        leaf study-type {
                            type types-aa:study-stats-type;
                            description "Statistic type that the study is using";
                        }

                        leaf accounting-policy {
                            type leafref {
                                path "../../../../../../log/accounting-policy/policy-id";
                            }
                            description "Accounting policy ID";
                        }

                        leaf collect-stats {
                            type boolean;
                            default "false";
                            description "Collect statistics";
                        }

                        leaf-list apply-groups {
                            type leafref {
                                path "../../../../../../groups/group/name";
                            }
                            max-elements 8;
                            ordered-by user;
                            description "Apply a configuration group at this level";
                        }

                        leaf-list apply-groups-exclude {
                            type leafref {
                                path "../../../../../../groups/group/name";
                            }
                            max-elements 8;
                            ordered-by user;
                            description "Exclude a configuration group at this level";
                        }

                        container aa-sub {
                            description "Enter the aa-sub context";

                            list esm {
                                key "esm-sub-name";
                                description "Add a list entry for esm";

                                leaf esm-sub-name {
                                    type types-sros:named-item;
                                    description "ESM subscriber name";
                                }

                            } // list esm

                            list esm-mac {
                                key "esm-mac-sub-name";
                                description "Add a list entry for esm-mac";

                                leaf esm-mac-sub-name {
                                    type types-sros:named-item;
                                    description "ESM MAC subscriber name";
                                }

                            } // list esm-mac

                            list transit {
                                key "transit-sub-name";
                                description "Add a list entry for transit";

                                leaf transit-sub-name {
                                    type types-sros:named-item;
                                    description "Transit subscriber name";
                                }

                            } // list transit

                            list sap {
                                key "sap-id";
                                description "Add a list entry for sap";

                                leaf sap-id {
                                    type types-sros:sap;
                                    description "AA subscriber SAP ID";
                                }

                            } // list sap

                            list spoke-sdp {
                                key "sdp-bind-id";
                                description "Add a list entry for spoke-sdp";

                                leaf sdp-bind-id {
                                    type types-services:sdp-bind-id;
                                    description "Spoke SDP ID for an AA subscriber";
                                }

                            } // list spoke-sdp

                        } // container aa-sub

                    } // list aa-sub-study

                } // container statistics

                container threshold-crossing-alert {
                    description "Enter the threshold-crossing-alert context";

                    list criteria {
                        key "criteria-id direction";
                        description "Enter the criteria list instance";

                        leaf criteria-id {
                            type types-aa:tca-criteria;
                            description "Statistics TCA criteria ID";
                        }

                        leaf direction {
                            type types-aa:tca-direction;
                            description "Direction of traffic for the criteria statistics TCA";
                        }

                        leaf high-watermark {
                            type uint32 {
                                range "1..4294967295";
                            }
                            default "4294967295";
                            description "High watermark threshold";
                        }

                        leaf low-watermark {
                            type uint32 {
                                range "0..4294967294";
                            }
                            default "0";
                            description "Low watermark threshold";
                        }

                        leaf-list apply-groups {
                            type leafref {
                                path "../../../../../../groups/group/name";
                            }
                            max-elements 8;
                            ordered-by user;
                            description "Apply a configuration group at this level";
                        }

                        leaf-list apply-groups-exclude {
                            type leafref {
                                path "../../../../../../groups/group/name";
                            }
                            max-elements 8;
                            ordered-by user;
                            description "Exclude a configuration group at this level";
                        }

                    } // list criteria

                    list gtp-filter {
                        key "gtp-filter-name criteria direction";
                        description "Enter the gtp-filter list instance";

                        leaf gtp-filter-name {
                            type leafref {
                                path "../../../gtp/gtp-filter/gtp-filter-name";
                            }
                            description "GTP filter name for TCA generation";
                        }

                        leaf criteria {
                            type types-aa:tca-gtp-criteria;
                            description "Criteria ID for GTP filter TCA";
                        }

                        leaf direction {
                            type types-aa:tca-direction;
                            description "Direction of traffic for the GTP filter TCA";
                        }

                        leaf high-watermark {
                            type uint32 {
                                range "1..4294967295";
                            }
                            default "4294967295";
                            description "High watermark threshold";
                        }

                        leaf low-watermark {
                            type uint32 {
                                range "0..4294967294";
                            }
                            default "0";
                            description "Low watermark threshold";
                        }

                        leaf-list apply-groups {
                            type leafref {
                                path "../../../../../../groups/group/name";
                            }
                            max-elements 8;
                            ordered-by user;
                            description "Apply a configuration group at this level";
                        }

                        leaf-list apply-groups-exclude {
                            type leafref {
                                path "../../../../../../groups/group/name";
                            }
                            max-elements 8;
                            ordered-by user;
                            description "Exclude a configuration group at this level";
                        }

                    } // list gtp-filter

                    list gtp-filter-entry {
                        key "gtp-filter-name entry-id direction";
                        description "Enter the gtp-filter-entry list instance";

                        leaf gtp-filter-name {
                            type leafref {
                                path "../../../gtp/gtp-filter/gtp-filter-name";
                            }
                            description "AA GTP filter name for TCA configuration";
                        }

                        leaf entry-id {
                            type uint32;
                            description "Entry ID";
                        }

                        leaf direction {
                            type types-aa:tca-direction;
                            description "Traffic direction for GTP filter entry TCA";
                        }

                        leaf high-watermark {
                            type uint32 {
                                range "1..4294967295";
                            }
                            default "4294967295";
                            description "High watermark threshold";
                        }

                        leaf low-watermark {
                            type uint32 {
                                range "0..4294967294";
                            }
                            default "0";
                            description "Low watermark threshold";
                        }

                        leaf-list apply-groups {
                            type leafref {
                                path "../../../../../../groups/group/name";
                            }
                            max-elements 8;
                            ordered-by user;
                            description "Apply a configuration group at this level";
                        }

                        leaf-list apply-groups-exclude {
                            type leafref {
                                path "../../../../../../groups/group/name";
                            }
                            max-elements 8;
                            ordered-by user;
                            description "Exclude a configuration group at this level";
                        }

                    } // list gtp-filter-entry

                    list session-filter {
                        key "session-filter-name criteria direction";
                        description "Enter the session-filter list instance";

                        leaf session-filter-name {
                            type leafref {
                                path "../../../session-filter/session-filter-name";
                            }
                            description "AA session filter name for TCA configuration";
                        }

                        leaf criteria {
                            type types-aa:tca-session-criteria;
                            description "ID for session filter entry TCA";
                        }

                        leaf direction {
                            type types-aa:tca-direction;
                            description "Direction of traffic for TCA configuration";
                        }

                        leaf high-watermark {
                            type uint32 {
                                range "1..4294967295";
                            }
                            default "4294967295";
                            description "High watermark threshold";
                        }

                        leaf low-watermark {
                            type uint32 {
                                range "0..4294967294";
                            }
                            default "0";
                            description "Low watermark threshold";
                        }

                        leaf-list apply-groups {
                            type leafref {
                                path "../../../../../../groups/group/name";
                            }
                            max-elements 8;
                            ordered-by user;
                            description "Apply a configuration group at this level";
                        }

                        leaf-list apply-groups-exclude {
                            type leafref {
                                path "../../../../../../groups/group/name";
                            }
                            max-elements 8;
                            ordered-by user;
                            description "Exclude a configuration group at this level";
                        }

                    } // list session-filter

                    list session-filter-entry {
                        key "session-filter-name entry-id direction";
                        description "Enter the session-filter-entry list instance";

                        leaf session-filter-name {
                            type leafref {
                                path "../../../session-filter/session-filter-name";
                            }
                            description "AA session filter name for TCA configuration";
                        }

                        leaf entry-id {
                            type leafref {
                                path "../../../session-filter[session-filter-name=current()/../session-filter-name]/entry/entry-id";
                            }
                            description "ID for session filter entry TCA";
                        }

                        leaf direction {
                            type types-aa:tca-direction;
                            description "Direction of traffic for TCA configuration";
                        }

                        leaf high-watermark {
                            type uint32 {
                                range "1..4294967295";
                            }
                            default "4294967295";
                            description "High watermark threshold";
                        }

                        leaf low-watermark {
                            type uint32 {
                                range "0..4294967294";
                            }
                            default "0";
                            description "Low watermark threshold";
                        }

                        leaf-list apply-groups {
                            type leafref {
                                path "../../../../../../groups/group/name";
                            }
                            max-elements 8;
                            ordered-by user;
                            description "Apply a configuration group at this level";
                        }

                        leaf-list apply-groups-exclude {
                            type leafref {
                                path "../../../../../../groups/group/name";
                            }
                            max-elements 8;
                            ordered-by user;
                            description "Exclude a configuration group at this level";
                        }

                    } // list session-filter-entry

                    list sctp-filter {
                        key "sctp-filter-name criteria direction";
                        description "Enter the sctp-filter list instance";

                        leaf sctp-filter-name {
                            type leafref {
                                path "../../../sctp-filter/sctp-filter-name";
                            }
                            description "SCTP filter name for TCA generation";
                        }

                        leaf criteria {
                            type types-aa:tca-sctp-criteria;
                            description "Criteria ID for SCTP filter TCA";
                        }

                        leaf direction {
                            type types-aa:tca-direction;
                            description "Direction of traffic for SCTP filter TCA";
                        }

                        leaf high-watermark {
                            type uint32 {
                                range "1..4294967295";
                            }
                            default "4294967295";
                            description "High watermark threshold";
                        }

                        leaf low-watermark {
                            type uint32 {
                                range "0..4294967294";
                            }
                            default "0";
                            description "Low watermark threshold";
                        }

                        leaf-list apply-groups {
                            type leafref {
                                path "../../../../../../groups/group/name";
                            }
                            max-elements 8;
                            ordered-by user;
                            description "Apply a configuration group at this level";
                        }

                        leaf-list apply-groups-exclude {
                            type leafref {
                                path "../../../../../../groups/group/name";
                            }
                            max-elements 8;
                            ordered-by user;
                            description "Exclude a configuration group at this level";
                        }

                    } // list sctp-filter

                    list sctp-filter-entry {
                        key "sctp-filter-name entry-id direction";
                        description "Enter the sctp-filter-entry list instance";

                        leaf sctp-filter-name {
                            type leafref {
                                path "../../../sctp-filter/sctp-filter-name";
                            }
                            description "AA SCTP filter name for TCA configuration";
                        }

                        leaf entry-id {
                            type leafref {
                                path "../../../sctp-filter[sctp-filter-name=current()/../sctp-filter-name]/ppid/entry/entry-id";
                            }
                            description "ID for SCTP filter entry TCA";
                        }

                        leaf direction {
                            type types-aa:tca-direction;
                            description "Direction of traffic for TCA configuration";
                        }

                        leaf high-watermark {
                            type uint32 {
                                range "1..4294967295";
                            }
                            default "4294967295";
                            description "High watermark threshold";
                        }

                        leaf low-watermark {
                            type uint32 {
                                range "0..4294967294";
                            }
                            default "0";
                            description "Low watermark threshold";
                        }

                        leaf-list apply-groups {
                            type leafref {
                                path "../../../../../../groups/group/name";
                            }
                            max-elements 8;
                            ordered-by user;
                            description "Apply a configuration group at this level";
                        }

                        leaf-list apply-groups-exclude {
                            type leafref {
                                path "../../../../../../groups/group/name";
                            }
                            max-elements 8;
                            ordered-by user;
                            description "Exclude a configuration group at this level";
                        }

                    } // list sctp-filter-entry

                    list policer {
                        key "policer-name direction";
                        description "Enter the policer list instance";

                        leaf policer-name {
                            type types-sros:named-item;
                            description "Policer name for TCA generation";
                        }

                        leaf direction {
                            type types-aa:tca-direction;
                            description "Direction of traffic for the policer TCA";
                        }

                        leaf high-watermark {
                            type uint32 {
                                range "1..4294967295";
                            }
                            default "4294967295";
                            description "High watermark threshold";
                        }

                        leaf low-watermark {
                            type uint32 {
                                range "0..4294967294";
                            }
                            default "0";
                            description "Low watermark threshold";
                        }

                        leaf-list apply-groups {
                            type leafref {
                                path "../../../../../../groups/group/name";
                            }
                            max-elements 8;
                            ordered-by user;
                            description "Apply a configuration group at this level";
                        }

                        leaf-list apply-groups-exclude {
                            type leafref {
                                path "../../../../../../groups/group/name";
                            }
                            max-elements 8;
                            ordered-by user;
                            description "Exclude a configuration group at this level";
                        }

                    } // list policer

                    list tcp-validate {
                        key "tcp-validate-name direction";
                        description "Enter the tcp-validate list instance";

                        leaf tcp-validate-name {
                            type leafref {
                                path "../../../tcp-validate/tcp-validate-name";
                            }
                            description "AA TCP validate name for configuration";
                        }

                        leaf direction {
                            type types-aa:tca-direction;
                            description "Direction of traffic for TCA configuration";
                        }

                        leaf high-watermark {
                            type uint32 {
                                range "1..4294967295";
                            }
                            default "4294967295";
                            description "High watermark threshold";
                        }

                        leaf low-watermark {
                            type uint32 {
                                range "0..4294967294";
                            }
                            default "0";
                            description "Low watermark threshold";
                        }

                        leaf-list apply-groups {
                            type leafref {
                                path "../../../../../../groups/group/name";
                            }
                            max-elements 8;
                            ordered-by user;
                            description "Apply a configuration group at this level";
                        }

                        leaf-list apply-groups-exclude {
                            type leafref {
                                path "../../../../../../groups/group/name";
                            }
                            max-elements 8;
                            ordered-by user;
                            description "Exclude a configuration group at this level";
                        }

                    } // list tcp-validate

                } // container threshold-crossing-alert

                container policy-override {
                    description "Enter the policy-override context";

                    container aa-sub {
                        description "Enter the aa-sub context";

                        list sap {
                            key "sap-id";
                            description "Enter the sap list instance";

                            leaf sap-id {
                                type types-sros:sap;
                                description "AA subscriber SAP ID";
                            }

                            leaf-list apply-groups {
                                type leafref {
                                    path "../../../../../../../groups/group/name";
                                }
                                max-elements 8;
                                ordered-by user;
                                description "Apply a configuration group at this level";
                            }

                            leaf-list apply-groups-exclude {
                                type leafref {
                                    path "../../../../../../../groups/group/name";
                                }
                                max-elements 8;
                                ordered-by user;
                                description "Exclude a configuration group at this level";
                            }

                            list characteristic {
                                key "characteristic-name";
                                description "Enter the characteristic list instance";

                                leaf characteristic-name {
                                    type leafref {
                                        path "../../../../../policy/app-service-options/characteristic/characteristic-name";
                                    }
                                    description "ASO characteristic name";
                                }

                                leaf value {
                                    type leafref {
                                        path "../../../../../policy/app-service-options/characteristic[characteristic-name=current()/../characteristic-name]/value/value-name";
                                    }
                                    mandatory true;
                                    description "Characteristic value used in subscriber policy override";
                                }

                                leaf-list apply-groups {
                                    type leafref {
                                        path "../../../../../../../../groups/group/name";
                                    }
                                    max-elements 8;
                                    ordered-by user;
                                    description "Apply a configuration group at this level";
                                }

                                leaf-list apply-groups-exclude {
                                    type leafref {
                                        path "../../../../../../../../groups/group/name";
                                    }
                                    max-elements 8;
                                    ordered-by user;
                                    description "Exclude a configuration group at this level";
                                }

                            } // list characteristic

                        } // list sap

                        list spoke-sdp {
                            key "sdp-bind-id";
                            description "Enter the spoke-sdp list instance";

                            leaf sdp-bind-id {
                                type types-services:sdp-bind-id;
                                description "Spoke SDP ID for an AA subscriber";
                            }

                            leaf-list apply-groups {
                                type leafref {
                                    path "../../../../../../../groups/group/name";
                                }
                                max-elements 8;
                                ordered-by user;
                                description "Apply a configuration group at this level";
                            }

                            leaf-list apply-groups-exclude {
                                type leafref {
                                    path "../../../../../../../groups/group/name";
                                }
                                max-elements 8;
                                ordered-by user;
                                description "Exclude a configuration group at this level";
                            }

                            list characteristic {
                                key "characteristic-name";
                                description "Enter the characteristic list instance";

                                leaf characteristic-name {
                                    type leafref {
                                        path "../../../../../policy/app-service-options/characteristic/characteristic-name";
                                    }
                                    description "ASO characteristic name";
                                }

                                leaf value {
                                    type leafref {
                                        path "../../../../../policy/app-service-options/characteristic[characteristic-name=current()/../characteristic-name]/value/value-name";
                                    }
                                    mandatory true;
                                    description "Characteristic value used in subscriber policy override";
                                }

                                leaf-list apply-groups {
                                    type leafref {
                                        path "../../../../../../../../groups/group/name";
                                    }
                                    max-elements 8;
                                    ordered-by user;
                                    description "Apply a configuration group at this level";
                                }

                                leaf-list apply-groups-exclude {
                                    type leafref {
                                        path "../../../../../../../../groups/group/name";
                                    }
                                    max-elements 8;
                                    ordered-by user;
                                    description "Exclude a configuration group at this level";
                                }

                            } // list characteristic

                        } // list spoke-sdp

                        list transit {
                            key "transit-sub-name";
                            description "Enter the transit list instance";

                            leaf transit-sub-name {
                                type types-sros:named-item;
                                description "Transit subscriber name";
                            }

                            leaf-list apply-groups {
                                type leafref {
                                    path "../../../../../../../groups/group/name";
                                }
                                max-elements 8;
                                ordered-by user;
                                description "Apply a configuration group at this level";
                            }

                            leaf-list apply-groups-exclude {
                                type leafref {
                                    path "../../../../../../../groups/group/name";
                                }
                                max-elements 8;
                                ordered-by user;
                                description "Exclude a configuration group at this level";
                            }

                            list characteristic {
                                key "characteristic-name";
                                description "Enter the characteristic list instance";

                                leaf characteristic-name {
                                    type leafref {
                                        path "../../../../../policy/app-service-options/characteristic/characteristic-name";
                                    }
                                    description "ASO characteristic name";
                                }

                                leaf value {
                                    type leafref {
                                        path "../../../../../policy/app-service-options/characteristic[characteristic-name=current()/../characteristic-name]/value/value-name";
                                    }
                                    mandatory true;
                                    description "Characteristic value used in subscriber policy override";
                                }

                                leaf-list apply-groups {
                                    type leafref {
                                        path "../../../../../../../../groups/group/name";
                                    }
                                    max-elements 8;
                                    ordered-by user;
                                    description "Apply a configuration group at this level";
                                }

                                leaf-list apply-groups-exclude {
                                    type leafref {
                                        path "../../../../../../../../groups/group/name";
                                    }
                                    max-elements 8;
                                    ordered-by user;
                                    description "Exclude a configuration group at this level";
                                }

                            } // list characteristic

                        } // list transit

                    } // container aa-sub

                } // container policy-override

            } // list partition

        } // list group

    } // grouping conf-aa-group

}
