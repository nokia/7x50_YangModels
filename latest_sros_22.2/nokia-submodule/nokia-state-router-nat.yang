submodule nokia-state-router-nat {

    yang-version "1.1";

    belongs-to nokia-state { prefix "state"; }

    import ietf-yang-types                { prefix "yang"; }
    import nokia-sros-yang-extensions     { prefix "sros-ext"; }
    import nokia-types-nat                { prefix "types-nat"; }
    import nokia-types-sros               { prefix "types-sros"; }

    include nokia-state-service;
    include nokia-state-svc-nat;


    sros-ext:sros-major-release "rel22";

    organization "Nokia";

    contact
        "Nokia SR OS Support
         Web: <http://www.nokia.com>";

    description
        "Nokia YANG Data model with operational state for Configure NAT on SR OS based routers.

         Copyright 2016 Nokia. All rights reserved. Reproduction of this document
         is authorized on the condition that the foregoing copyright notice is included.

         This nokia-state-router-nat YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";

    revision "2021-10-22";

    grouping state-router-nat {
        container nat {
            description "Enter the nat context";

            leaf outside-dnat-only-routes-counter {
                type yang:gauge32;
                description
                    "the actual number of routes used to direct
                     downstream traffic from this outside virtual router instance
                     to a NAT ISA card in Destination NAT operation";
            }

            container inside {
                description "Enter the inside context";

                container large-scale {
                    description "Enter the large-scale context";

                    container nat44 {
                        description "Enter the nat44 context";

                        container deterministic {
                            description "Enter the deterministic context";

                            list policy-map {
                                key "source-prefix";
                                description "Enter the policy-map list instance";

                                leaf source-prefix {
                                    type types-sros:ipv4-unicast-prefix;
                                    description "Source prefix that adds traffic to NAT pool";
                                }

                                leaf oper-state {
                                    type types-sros:up-down-status;
                                }

                                list map {
                                    key "from to";
                                    description "Enter the map list instance";

                                    leaf from {
                                        type types-sros:ipv4-address;
                                        description "Beginning of the range for IPv4 addresses";
                                    }

                                    leaf to {
                                        type types-sros:ipv4-address;
                                        description "End of the range for IPv4 addresses";
                                    }

                                    leaf oper-state {
                                        type types-sros:up-down-status;
                                    }

                                } // list map

                            } // list policy-map

                            list prefix-map {
                                key "source-prefix nat-policy";
                                description "Enter the prefix-map list instance";

                                leaf source-prefix {
                                    type types-sros:ipv4-unicast-prefix;
                                    description "Traffic sent from sources within this prefix will be NATed";
                                }

                                leaf nat-policy {
                                    type leafref {
                                        path "../../../../../../../../service/nat/nat-policy/name";
                                    }
                                    description "NAT policy";
                                }

                                leaf oper-state {
                                    type types-sros:up-down-status;
                                }

                                list map {
                                    key "from to";
                                    description "Enter the map list instance";

                                    leaf from {
                                        type types-sros:ipv4-address;
                                        description "Beginning of the range for IPv4 addresses";
                                    }

                                    leaf to {
                                        type types-sros:ipv4-address;
                                        description "End of the range for IPv4 addresses";
                                    }

                                    leaf oper-state {
                                        type types-sros:up-down-status;
                                    }

                                } // list map

                            } // list prefix-map

                        } // container deterministic

                        list subscriber {
                            key "id nat-policy";
                            description "Enter the subscriber list instance";

                            leaf id {
                                type uint32;
                                description "Identifier of this subscriber";
                            }

                            leaf nat-policy {
                                type types-sros:named-item;
                                description "NAT Policy associated with this subscriber";
                            }

                            leaf name {
                                type types-sros:named-item;
                                description
                                    "Subscriber's identification string.

                                     A string enclosed by square brackets [] indicates an automatically system-generated name";
                            }

                            leaf type {
                                type types-nat:sub-type;
                                description "Type of this subscriber";
                            }

                            leaf inside-ip-prefix {
                                type types-sros:ip-prefix;
                                description "Inside IP prefix";
                            }

                            leaf nat-group {
                                type uint8;
                                description "Identifier of the NAT Integrated Service Adaptor group";
                            }

                            leaf group-member {
                                type types-nat:bb-group-member;
                                description "Identifier of the NAT group member";
                            }

                            container statistics {
                                description "Enter the statistics context";

                                container protocol {
                                    description "Enter the protocol context";

                                    container icmp {
                                        description "Enter the icmp context";

                                        leaf port-usage {
                                            type types-sros:percent;
                                            description "ICMP port usage of this NAT subscriber and policy";
                                        }

                                        leaf port-usage-high {
                                            type boolean;
                                            description "ICMP port usage has reached configured limit";
                                        }

                                    } // container icmp

                                    container tcp {
                                        description "Enter the tcp context";

                                        leaf port-usage {
                                            type types-sros:percent;
                                            description "TCP port usage of this NAT subscriber and policy";
                                        }

                                        leaf port-usage-high {
                                            type boolean;
                                            description "TCP port usage has reached configured limit";
                                        }

                                    } // container tcp

                                    container udp {
                                        description "Enter the udp context";

                                        leaf port-usage {
                                            type types-sros:percent;
                                            description "UDP port usage of this NAT subscriber and policy";
                                        }

                                        leaf port-usage-high {
                                            type boolean;
                                            description "UDP port usage has reached configured limit";
                                        }

                                    } // container udp

                                } // container protocol

                                container sessions {
                                    description "Enter the sessions context";

                                    leaf usage {
                                        type types-sros:percent;
                                        description "Session usage of this NAT subscriber and policy";
                                    }

                                    leaf usage-high {
                                        type boolean;
                                        description "Session usage has reached configured limit";
                                    }

                                    leaf active {
                                        type uint32;
                                        description "Number of active sessions of this NAT subscriber and policy";
                                    }

                                    leaf reserved {
                                        type uint32;
                                        description "Number of active prioritized sessions of this subscriber and policy";
                                    }

                                    leaf peak {
                                        type uint32;
                                        description "Maximum number of sessions that were active together up to this point in time";
                                    }

                                } // container sessions

                            } // container statistics

                            list port-block {
                                key "outside-router-instance outside-ip-address start";
                                description "Enter the port-block list instance";

                                leaf outside-router-instance {
                                    type types-sros:router-instance;
                                    description "Outside router instance";
                                }

                                leaf outside-ip-address {
                                    type types-sros:ipv4-address;
                                    description "Outside IP address";
                                }

                                leaf start {
                                    type uint32;
                                    description "Start of the port block allocated to the subscriber";
                                }

                                leaf end {
                                    type uint32;
                                    description "End of the port block allocated to the subscriber";
                                }

                            } // list port-block

                        } // list subscriber

                        list route {
                            key "ip-prefix-length";
                            description "Enter the route list instance";

                            leaf ip-prefix-length {
                                type types-sros:ipv4-unicast-prefix;
                                description "Route destination";
                            }

                            leaf nat-policy {
                                type types-sros:named-item;
                                description "NAT policy associated with the route";
                            }

                            leaf type {
                                type enumeration {
                                    enum "dynamic"                      { value 1; }
                                    enum "static"                       { value 2; }
                                }
                                description "Type of the route";
                            }

                        } // list route

                    } // container nat44

                    container dual-stack-lite {
                        description "Enter the dual-stack-lite context";

                        container deterministic {
                            description "Enter the deterministic context";

                            list policy-map {
                                key "source-prefix";
                                description "Enter the policy-map list instance";

                                leaf source-prefix {
                                    type types-sros:ipv6-unicast-prefix;
                                    description "Source prefix that adds traffic to NAT pool";
                                }

                                leaf oper-state {
                                    type types-sros:up-down-status;
                                }

                                list map {
                                    key "from to";
                                    description "Enter the map list instance";

                                    leaf from {
                                        type types-sros:ipv6-prefix;
                                        description "Beginning of the range for IPv6 addresses";
                                    }

                                    leaf to {
                                        type types-sros:ipv6-prefix;
                                        description "Ending of the range for IPv6 addresses that is mapped on the inside to outside IPv6 addresses";
                                    }

                                    leaf oper-state {
                                        type types-sros:up-down-status;
                                    }

                                } // list map

                            } // list policy-map

                            list prefix-map {
                                key "source-prefix nat-policy";
                                description "Enter the prefix-map list instance";

                                leaf source-prefix {
                                    type types-sros:ipv6-unicast-prefix;
                                    description "Traffic sent from sources within this prefix will be NATed";
                                }

                                leaf nat-policy {
                                    type leafref {
                                        path "../../../../../../../../service/nat/nat-policy/name";
                                    }
                                    description "NAT policy";
                                }

                                leaf oper-state {
                                    type types-sros:up-down-status;
                                }

                                list map {
                                    key "from to";
                                    description "Enter the map list instance";

                                    leaf from {
                                        type types-sros:ipv6-prefix;
                                        description "Beginning of the range for IPv6 addresses";
                                    }

                                    leaf to {
                                        type types-sros:ipv6-prefix;
                                        description "End of the range for IPv6 addresses";
                                    }

                                    leaf oper-state {
                                        type types-sros:up-down-status;
                                    }

                                } // list map

                            } // list prefix-map

                        } // container deterministic

                        list subscriber {
                            key "id nat-policy";
                            description "Enter the subscriber list instance";

                            leaf id {
                                type uint32;
                                description "Identifier of this subscriber";
                            }

                            leaf nat-policy {
                                type types-sros:named-item;
                                description "NAT Policy associated with this subscriber";
                            }

                            leaf name {
                                type types-sros:named-item;
                                description
                                    "Subscriber's identification string.

                                     A string enclosed by square brackets [] indicates an automatically system-generated name";
                            }

                            leaf type {
                                type types-nat:sub-type;
                                description "Type of this subscriber";
                            }

                            leaf inside-ip-prefix {
                                type types-sros:ip-prefix;
                                description "Inside IP prefix";
                            }

                            leaf nat-group {
                                type uint8;
                                description "Identifier of the NAT Integrated Service Adaptor group";
                            }

                            leaf group-member {
                                type types-nat:bb-group-member;
                                description "Identifier of the NAT group member";
                            }

                            container statistics {
                                description "Enter the statistics context";

                                container protocol {
                                    description "Enter the protocol context";

                                    container icmp {
                                        description "Enter the icmp context";

                                        leaf port-usage {
                                            type types-sros:percent;
                                            description "ICMP port usage of this NAT subscriber and policy";
                                        }

                                        leaf port-usage-high {
                                            type boolean;
                                            description "ICMP port usage has reached configured limit";
                                        }

                                    } // container icmp

                                    container tcp {
                                        description "Enter the tcp context";

                                        leaf port-usage {
                                            type types-sros:percent;
                                            description "TCP port usage of this NAT subscriber and policy";
                                        }

                                        leaf port-usage-high {
                                            type boolean;
                                            description "TCP port usage has reached configured limit";
                                        }

                                    } // container tcp

                                    container udp {
                                        description "Enter the udp context";

                                        leaf port-usage {
                                            type types-sros:percent;
                                            description "UDP port usage of this NAT subscriber and policy";
                                        }

                                        leaf port-usage-high {
                                            type boolean;
                                            description "UDP port usage has reached configured limit";
                                        }

                                    } // container udp

                                } // container protocol

                                container sessions {
                                    description "Enter the sessions context";

                                    leaf usage {
                                        type types-sros:percent;
                                        description "Session usage of this NAT subscriber and policy";
                                    }

                                    leaf usage-high {
                                        type boolean;
                                        description "Session usage has reached configured limit";
                                    }

                                    leaf active {
                                        type uint32;
                                        description "Number of active sessions of this NAT subscriber and policy";
                                    }

                                    leaf reserved {
                                        type uint32;
                                        description "Number of active prioritized sessions of this subscriber and policy";
                                    }

                                    leaf peak {
                                        type uint32;
                                        description "Maximum number of sessions that were active together up to this point in time";
                                    }

                                } // container sessions

                            } // container statistics

                            list port-block {
                                key "outside-router-instance outside-ip-address start";
                                description "Enter the port-block list instance";

                                leaf outside-router-instance {
                                    type types-sros:router-instance;
                                    description "Outside router instance";
                                }

                                leaf outside-ip-address {
                                    type types-sros:ipv4-address;
                                    description "Outside IP address";
                                }

                                leaf start {
                                    type uint32;
                                    description "Start of the port block allocated to the subscriber";
                                }

                                leaf end {
                                    type uint32;
                                    description "End of the port block allocated to the subscriber";
                                }

                            } // list port-block

                        } // list subscriber

                    } // container dual-stack-lite

                    container nat64 {
                        description "Enter the nat64 context";

                        list subscriber {
                            key "id nat-policy";
                            description "Enter the subscriber list instance";

                            leaf id {
                                type uint32;
                                description "Identifier of this subscriber";
                            }

                            leaf nat-policy {
                                type types-sros:named-item;
                                description "NAT Policy associated with this subscriber";
                            }

                            leaf name {
                                type types-sros:named-item;
                                description
                                    "Subscriber's identification string.

                                     A string enclosed by square brackets [] indicates an automatically system-generated name";
                            }

                            leaf type {
                                type types-nat:sub-type;
                                description "Type of this subscriber";
                            }

                            leaf inside-ip-prefix {
                                type types-sros:ip-prefix;
                                description "Inside IP prefix";
                            }

                            leaf nat-group {
                                type uint8;
                                description "Identifier of the NAT Integrated Service Adaptor group";
                            }

                            leaf group-member {
                                type types-nat:bb-group-member;
                                description "Identifier of the NAT group member";
                            }

                            container statistics {
                                description "Enter the statistics context";

                                container protocol {
                                    description "Enter the protocol context";

                                    container icmp {
                                        description "Enter the icmp context";

                                        leaf port-usage {
                                            type types-sros:percent;
                                            description "ICMP port usage of this NAT subscriber and policy";
                                        }

                                        leaf port-usage-high {
                                            type boolean;
                                            description "ICMP port usage has reached configured limit";
                                        }

                                    } // container icmp

                                    container tcp {
                                        description "Enter the tcp context";

                                        leaf port-usage {
                                            type types-sros:percent;
                                            description "TCP port usage of this NAT subscriber and policy";
                                        }

                                        leaf port-usage-high {
                                            type boolean;
                                            description "TCP port usage has reached configured limit";
                                        }

                                    } // container tcp

                                    container udp {
                                        description "Enter the udp context";

                                        leaf port-usage {
                                            type types-sros:percent;
                                            description "UDP port usage of this NAT subscriber and policy";
                                        }

                                        leaf port-usage-high {
                                            type boolean;
                                            description "UDP port usage has reached configured limit";
                                        }

                                    } // container udp

                                } // container protocol

                                container sessions {
                                    description "Enter the sessions context";

                                    leaf usage {
                                        type types-sros:percent;
                                        description "Session usage of this NAT subscriber and policy";
                                    }

                                    leaf usage-high {
                                        type boolean;
                                        description "Session usage has reached configured limit";
                                    }

                                    leaf active {
                                        type uint32;
                                        description "Number of active sessions of this NAT subscriber and policy";
                                    }

                                    leaf reserved {
                                        type uint32;
                                        description "Number of active prioritized sessions of this subscriber and policy";
                                    }

                                    leaf peak {
                                        type uint32;
                                        description "Maximum number of sessions that were active together up to this point in time";
                                    }

                                } // container sessions

                            } // container statistics

                            list port-block {
                                key "outside-router-instance outside-ip-address start";
                                description "Enter the port-block list instance";

                                leaf outside-router-instance {
                                    type types-sros:router-instance;
                                    description "Outside router instance";
                                }

                                leaf outside-ip-address {
                                    type types-sros:ipv4-address;
                                    description "Outside IP address";
                                }

                                leaf start {
                                    type uint32;
                                    description "Start of the port block allocated to the subscriber";
                                }

                                leaf end {
                                    type uint32;
                                    description "End of the port block allocated to the subscriber";
                                }

                            } // list port-block

                        } // list subscriber

                    } // container nat64

                } // container large-scale

            } // container inside

            container outside {
                description "Enter the outside context";

                list pool {
                    key "name";
                    description "Enter the pool list instance";

                    leaf name {
                        type types-sros:named-item;
                        description "NAT pool name";
                    }

                    leaf oper-mode {
                        type types-nat:pool-mode;
                        description "Mode of operation";
                    }

                    container large-scale {
                        description "Enter the large-scale context";

                        container redundancy {
                            description "Enter the redundancy context";

                            leaf state {
                                type enumeration {
                                    enum "down"                         { value 0; }
                                    enum "down-held"                    { value 1; }
                                    enum "standby"                      { value 2; }
                                    enum "standby-held"                 { value 3; }
                                    enum "active"                       { value 4; }
                                    enum "active-held"                  { value 5; }
                                    enum "active-sick"                  { value 6; }
                                    enum "needs-audit"                  { value 7; }
                                    enum "disabled-up"                  { value 8; }
                                    enum "disabled-down"                { value 9; }
                                }
                                description "Dual-homing state in a multi-chassis redundancy environment";
                            }

                        } // container redundancy

                        list group-member {
                            key "group-member";
                            description "Enter the group-member list instance";

                            leaf group-member {
                                type types-nat:bb-group-member;
                                description "group member ID";
                            }

                            leaf block-usage {
                                type types-sros:percent;
                                description "Port block usage in large-scale NAT";
                            }

                            leaf high-watermark-reached {
                                type boolean;
                                description "High watermark reached for the large-scale NAT block usage";
                            }

                        } // list group-member

                    } // container large-scale

                    container l2-aware {
                        description "Enter the l2-aware context";

                        leaf block-usage {
                            type types-sros:percent;
                            description "Port block usage in L2-aware NAT";
                        }

                        leaf high-watermark-reached {
                            type boolean;
                            description "High watermark reached for the l2-aware block usage";
                        }

                        container port-block-extension {
                            description "Enter the port-block-extension context";

                            leaf shared-port-blocks-per-ip {
                                type uint32;
                                description "Number of shared port-blocks per IP";
                            }

                            container subscriber {
                                description "Enter the subscriber context";

                                leaf usage {
                                    type types-sros:percent;
                                    description "Subscriber usage in L2-aware NAT";
                                }

                                leaf high-watermark-reached {
                                    type boolean;
                                    description "High watermark reached for the l2-aware subscriber usage";
                                }

                            } // container subscriber

                        } // container port-block-extension

                        list group-member {
                            key "group-member";
                            description "Enter the group-member list instance";

                            leaf group-member {
                                type types-nat:bb-group-member;
                                description "group member ID";
                            }

                            leaf block-usage {
                                type types-sros:percent;
                                description "Port block usage in l2-aware NAT";
                            }

                            leaf high-watermark-reached {
                                type boolean;
                                description "High watermark reached for the l2-aware NAT block usage";
                            }

                        } // list group-member

                    } // container l2-aware

                    list address-range {
                        key "start end";
                        description "Enter the address-range list instance";

                        leaf start {
                            type types-sros:ipv4-unicast-address;
                            description "Lower bound of the NAT address range";
                        }

                        leaf end {
                            type types-sros:ipv4-unicast-address;
                            description "Upper bound of the NAT address range";
                        }

                        leaf allocated-blocks {
                            type uint32;
                            description "Number of allocated blocks";
                        }

                        leaf allocated-subscribers {
                            type uint32;
                            description "Number of allocated L2-aware subscribers";
                        }

                    } // list address-range

                } // list pool

                container large-scale {
                    description "Enter the large-scale context";

                    list block {
                        key "address first-port";
                        description "Enter the block list instance";

                        leaf address {
                            type types-sros:ipv4-unicast-address;
                            description "Outside IP address";
                        }

                        leaf first-port {
                            type types-nat:port-number;
                            description "First outside port";
                        }

                        leaf last-port {
                            type types-nat:port-number;
                            description "Last outside port";
                        }

                        leaf nat-policy {
                            type types-sros:named-item;
                            description "NAT policy";
                        }

                        leaf nat-pool {
                            type types-sros:named-item;
                            description "NAT pool";
                        }

                        leaf subscriber-id {
                            type uint32;
                            description "Subscriber ID";
                        }

                        leaf allocation-time {
                            type types-sros:date-time;
                            description "Allocation time";
                        }

                        container inside {
                            description "Enter the inside context";

                            leaf router-instance {
                                type types-sros:router-instance;
                                description "Inside service";
                            }

                            leaf address {
                                type types-sros:ip-address;
                                description "Inside address";
                            }

                        } // container inside

                    } // list block

                } // container large-scale

            } // container outside

            container map {
                description "Enter the map context";

                list map-domain {
                    key "domain-name";
                    description "Enter the map-domain list instance";

                    leaf domain-name {
                        type leafref {
                            path "../../../../../service/nat/map-t/domain/name";
                        }
                        description "MAP domain template name";
                    }

                    container statistics {
                        description "Enter the statistics context";

                        container upstream {
                            description "Enter the upstream context";

                            leaf forwarded-packets {
                                type yang:counter64;
                                description "Number of packets forwarded in the upstream direction";
                            }

                            leaf forwarded-octets {
                                type yang:counter64;
                                description "Number of octets forwarded in the upstream direction";
                            }

                            leaf dropped-packets {
                                type yang:counter64;
                                description "Number of packets dropped in the upstream direction";
                            }

                            leaf dropped-octets {
                                type yang:counter64;
                                description "Number of octets dropped in the upstream direction";
                            }

                        } // container upstream

                        container downstream {
                            description "Enter the downstream context";

                            leaf forwarded-packets {
                                type yang:counter64;
                                description "Number of packets forwarded in the downstream direction";
                            }

                            leaf forwarded-octets {
                                type yang:counter64;
                                description "Number of octets forwarded in the downstream direction";
                            }

                            leaf dropped-packets {
                                type yang:counter64;
                                description "Number of packets dropped in the downstream direction";
                            }

                            leaf dropped-octets {
                                type yang:counter64;
                                description "Number of octets dropped in the downstream direction";
                            }

                        } // container downstream

                    } // container statistics

                } // list map-domain

            } // container map

        } // container nat

    } // grouping state-router-nat

}
