submodule nokia-state-system-telemetry {

    yang-version "1.1";

    belongs-to nokia-state { prefix "state"; }

    import ietf-yang-types                { prefix "yang"; }
    import nokia-sros-yang-extensions     { prefix "sros-ext"; }
    import nokia-types-qos                { prefix "types-qos"; }
    import nokia-types-sros               { prefix "types-sros"; }
    import nokia-types-system             { prefix "types-system"; }


    sros-ext:sros-major-release "rel22";

    organization "Nokia";

    contact
        "Nokia SR OS Support
         Web: <http://www.nokia.com>";

    description
        "Nokia YANG Data model with operational state for system telemetry parameters. on SR OS based routers.

         Copyright 2016 Nokia. All rights reserved. Reproduction of this document
         is authorized on the condition that the foregoing copyright notice is included.

         This nokia-state-system-telemetry YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";

    revision "2021-10-04";

    grouping state-system-telemetry {
        container telemetry {
            description "Enter the telemetry context";

            container grpc {
                description "Enter the grpc context";

                list subscription {
                    key "subscription-id";
                    description "Enter the subscription list instance";

                    leaf subscription-id {
                        type uint32;
                        description
                            "System generated identifier of the telemetry
                             subscription.";
                    }

                    leaf user-name {
                        type types-sros:named-item;
                        description "The name of the user who initiated subscription.";
                    }

                    leaf destination-address {
                        type types-sros:ip-address;
                        description "IP address of the telemetry stream destination.";
                    }

                    leaf destination-port {
                        type types-sros:tcp-udp-port;
                        description
                            "Protocol (UDP or TCP) port number for the telemetry
                             stream destination.";
                    }

                    leaf mode {
                        type enumeration {
                            enum "stream"                       { value 0; }
                            enum "once"                         { value 1; }
                        }
                        description
                            "Subscription mode, indicating trigger
                             source for data notifications.

                             Value 'stream' indicates that subscription is
                             long-lived and stream data according to the triggers
                             specified within the individual subscription paths.

                             Value 'once' indicates that subscription is
                             short-lived and stream single sample of all paths
                             and is terminated afterwards.";
                    }

                    leaf encoding {
                        type types-system:telemetry-value-encoding;
                        description "The encoding of data notifications.";
                    }

                    leaf requested-qos {
                        type types-qos:dscp-name;
                        description
                            "Requested DSCP value in qos field of
                             the subscription.";
                    }

                    leaf operational-qos {
                        type types-qos:dscp-name;
                        description
                            "Operational DSCP value of subscription connection.
                             Only first qos request is accepted on connection.
                             DSCP value is reset to sgt-qos default after last
                             subscription on connection is terminated.";
                    }

                    leaf notification-count {
                        type uint64;
                        description "Number of data notifications sent.";
                    }

                    leaf context-count {
                        type uint64;
                        description "Number of data contexts sent.";
                    }

                    leaf notification-bundling-oper-state {
                        type types-sros:oper-state;
                        description "Operational state of notification bundling.";
                    }

                    leaf min-bundle-size {
                        type uint32;
                        description "Minimum number of contexts in single notification.";
                    }

                    leaf avg-bundle-size {
                        type uint32;
                        description "Average number of contexts in single notification.";
                    }

                    leaf max-bundle-size {
                        type uint32;
                        description "Maximum number of contexts in single notification.";
                    }

                    leaf max-bundle-time-granularity {
                        type uint32;
                        units "milliseconds";
                        description "Maximum time difference between contexts in single notification.";
                    }

                    list path {
                        key "path";
                        description "Enter the path list instance";

                        leaf path {
                            type string {
                                length "1..4096";
                            }
                            description
                                "Path to a section of operational state of interest
                                 (the sensor).";
                        }

                        leaf mode {
                            type types-system:telemetry-path-mode;
                            description
                                "Subscription path mode, indicating how the
                                 SROS must return values in a subscription.

                                 Value 'target-defined' indicates that the SROS
                                 selects the relevant mode for each leaf.

                                 Value 'on-change' indicates that the SROS sends
                                 an update on leaf value change.

                                 Value 'sample' indicates that the SROS samples
                                 values according to the interval.";
                        }

                        leaf sample-interval {
                            type uint64;
                            units "milliseconds";
                            description
                                "Time in milliseconds between the device's sample of a
                                 telemetry data source.";
                        }

                        leaf finished-collection-count {
                            type uint64;
                            description
                                "Finished count of collection sample of a telemetry
                                 data source.";
                        }

                        leaf deferred-collection-count {
                            type uint64;
                            description
                                "Deferred count of collection sample of a telemetry
                                 data source.";
                        }

                        leaf total-collection-time {
                            type uint64;
                            units "milliseconds";
                            description
                                "Total collection time in milliseconds of all
                                 samples of a telemetry data source.";
                        }

                        leaf min-collection-time {
                            type uint32;
                            units "milliseconds";
                            description
                                "Minimum collection time in milliseconds of single
                                 sample of a telemetry data source.";
                        }

                        leaf avg-collection-time {
                            type uint32;
                            units "milliseconds";
                            description
                                "Average collection time in milliseconds of single
                                 sample of a telemetry data source.";
                        }

                        leaf max-collection-time {
                            type uint32;
                            units "milliseconds";
                            description
                                "Maximum collection time in milliseconds of single
                                 sample of a telemetry data source.";
                        }

                    } // list path

                    list scale-path {
                        key "scale-path";
                        description "Enter the scale-path list instance";

                        leaf scale-path {
                            type string {
                                length "1..4096";
                            }
                            description "Path to the scale telemetry section of operational state of interest";
                        }

                        leaf mode {
                            type enumeration {
                                enum "once"                         { value 0; }
                                enum "on-change"                    { value 1; }
                                enum "sample"                       { value 2; }
                            }
                            description
                                "Subscription path mode, indicating how the
                                 SROS must return values in a subscription.

                                 Value 'once' indicates that subscription is
                                 short-lived and stream single sample of all paths
                                 and is terminated afterwards.

                                 Value 'on-change' indicates that the SROS sends
                                 an update on leaf value change.

                                 Value 'sample' indicates that the SROS samples
                                 values according to the interval.";
                        }

                        leaf sample-interval {
                            type uint64;
                            units "milliseconds";
                            description
                                "Time in milliseconds between the device's sample of a
                                 telemetry data source.";
                        }

                        leaf finished-collection-count {
                            type uint64;
                            description
                                "Finished count of collection sample of a telemetry
                                 data source.";
                        }

                        leaf deferred-collection-count {
                            type uint64;
                            description
                                "Deferred count of collection sample of a telemetry
                                 data source.";
                        }

                        leaf total-collection-time {
                            type uint64;
                            units "milliseconds";
                            description
                                "Total collection time in milliseconds of all
                                 samples of a telemetry data source.";
                        }

                        leaf min-collection-time {
                            type uint32;
                            units "milliseconds";
                            description
                                "Minimum collection time in milliseconds of single
                                 sample of a telemetry data source.";
                        }

                        leaf avg-collection-time {
                            type uint32;
                            units "milliseconds";
                            description
                                "Average collection time in milliseconds of single
                                 sample of a telemetry data source.";
                        }

                        leaf max-collection-time {
                            type uint32;
                            units "milliseconds";
                            description
                                "Maximum collection time in milliseconds of single
                                 sample of a telemetry data source.";
                        }

                    } // list scale-path

                } // list subscription

            } // container grpc

            container persistent-subscriptions {
                description "Enter the persistent-subscriptions context";

                list subscription {
                    key "name";
                    description "Enter the subscription list instance";

                    leaf name {
                        type types-sros:named-item;
                        description "Persistent subscription name";
                    }

                    leaf subscription-id {
                        type uint32;
                        description
                            "System generated identifier of the telemetry
                             subscription.";
                    }

                    leaf oper-state {
                        type types-sros:oper-state;
                        description "Operational state of persistent subscription.";
                    }

                    leaf oper-down-reason {
                        type string {
                            length "1..256";
                        }
                        description "The reason due to which subscription is operationally down.";
                    }

                    container statistics {
                        description "Enter the statistics context";

                        list destination {
                            key "address port";
                            description "Enter the destination list instance";

                            leaf address {
                                type union {
                                    type types-sros:ip-address;
                                    type types-sros:fully-qualified-domain-name;
                                }
                                description "Address of the destination within the destination group";
                            }

                            leaf port {
                                type types-sros:tcp-udp-port;
                                description "TCP port number for the destination";
                            }

                            leaf oper-state {
                                type types-sros:oper-state;
                                description "Operational state of destination.";
                            }

                            leaf last-oper-down-reason {
                                type string {
                                    length "1..256";
                                }
                                description
                                    "The reason due to which connection to destination
                                     was operationally down.";
                            }

                            leaf oper-router-instance {
                                type types-sros:router-instance;
                                description "Operational routing context of a connection.";
                            }

                            leaf last-oper-change {
                                type yang:date-and-time;
                                description "The time when the operational state of this destination last changed.";
                            }

                            leaf connection-attempts {
                                type uint64;
                                description "Number of tried connections towards this destination.";
                            }

                            leaf operational-qos {
                                type types-qos:dscp-name;
                                description
                                    "Operational DSCP value of destination connection.
                                     Only first qos request is accepted on connection.";
                            }

                            leaf notification-count {
                                type uint64;
                                description "Number of data notifications sent after last reconnect.";
                            }

                            leaf total-notification-count {
                                type uint64;
                                description "Total number of data notifications sent.";
                            }

                            leaf context-count {
                                type uint64;
                                description "Number of data contexts sent after last reconnect.";
                            }

                            leaf total-context-count {
                                type uint64;
                                description "Total number of data contexts sent.";
                            }

                            leaf notification-bundling-oper-state {
                                type types-sros:oper-state;
                                description "Operational state of notification bundling.";
                            }

                            leaf min-bundle-size {
                                type uint32;
                                description "Minimum number of contexts in single notification.";
                            }

                            leaf avg-bundle-size {
                                type uint32;
                                description "Average number of contexts in single notification.";
                            }

                            leaf max-bundle-size {
                                type uint32;
                                description "Maximum number of contexts in single notification.";
                            }

                            leaf max-bundle-time-granularity {
                                type uint32;
                                units "milliseconds";
                                description "Maximum time difference between contexts in single notification.";
                            }

                        } // list destination

                        list path {
                            key "xpath";
                            description "Enter the path list instance";

                            leaf xpath {
                                type string {
                                    length "1..512";
                                }
                                description "YANG model path indicating the data to be streamed";
                            }

                            leaf finished-collection-count {
                                type uint64;
                                description
                                    "Finished count of collection sample of a telemetry
                                     data source.";
                            }

                            leaf deferred-collection-count {
                                type uint64;
                                description
                                    "Deferred count of collection sample of a telemetry
                                     data source.";
                            }

                            leaf total-collection-time {
                                type uint64;
                                units "milliseconds";
                                description
                                    "Total collection time in milliseconds of all
                                     samples of a telemetry data source.";
                            }

                            leaf min-collection-time {
                                type uint32;
                                units "milliseconds";
                                description
                                    "Minimum collection time in milliseconds of single
                                     sample of a telemetry data source.";
                            }

                            leaf avg-collection-time {
                                type uint32;
                                units "milliseconds";
                                description
                                    "Average collection time in milliseconds of single
                                     sample of a telemetry data source.";
                            }

                            leaf max-collection-time {
                                type uint32;
                                units "milliseconds";
                                description
                                    "Maximum collection time in milliseconds of single
                                     sample of a telemetry data source.";
                            }

                        } // list path

                        list scale-path {
                            key "xpath";
                            description "Enter the scale-path list instance";

                            leaf xpath {
                                type string {
                                    length "1..512";
                                }
                                description "YANG model path indicating the data to be streamed";
                            }

                            leaf finished-collection-count {
                                type uint64;
                                description
                                    "Finished count of collection sample of a telemetry
                                     data source.";
                            }

                            leaf deferred-collection-count {
                                type uint64;
                                description
                                    "Deferred count of collection sample of a telemetry
                                     data source.";
                            }

                            leaf total-collection-time {
                                type uint64;
                                units "milliseconds";
                                description
                                    "Total collection time in milliseconds of all
                                     samples of a telemetry data source.";
                            }

                            leaf min-collection-time {
                                type uint32;
                                units "milliseconds";
                                description
                                    "Minimum collection time in milliseconds of single
                                     sample of a telemetry data source.";
                            }

                            leaf avg-collection-time {
                                type uint32;
                                units "milliseconds";
                                description
                                    "Average collection time in milliseconds of single
                                     sample of a telemetry data source.";
                            }

                            leaf max-collection-time {
                                type uint32;
                                units "milliseconds";
                                description
                                    "Maximum collection time in milliseconds of single
                                     sample of a telemetry data source.";
                            }

                        } // list scale-path

                    } // container statistics

                } // list subscription

            } // container persistent-subscriptions

            container sensor-groups {
                description "Enter the sensor-groups context";

                list sensor-group {
                    key "name";
                    description "Enter the sensor-group list instance";

                    leaf name {
                        type types-sros:named-item;
                        description "Sensor group name";
                    }

                    list path {
                        key "xpath";
                        description "Enter the path list instance";

                        leaf xpath {
                            type string {
                                length "1..512";
                            }
                            description "YANG model path indicating the data to be streamed";
                        }

                        leaf error-reason {
                            type string {
                                length "1..256";
                            }
                            description "The error reason of invalid xpath.";
                        }

                    } // list path

                } // list sensor-group

            } // container sensor-groups

        } // container telemetry

    } // grouping state-system-telemetry

}
