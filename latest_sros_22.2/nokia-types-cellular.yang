module nokia-types-cellular {

    yang-version "1.1";

    namespace "urn:nokia.com:sros:ns:yang:sr:types-cellular";

    prefix "types-cellular";

    import nokia-sros-yang-extensions     { prefix "sros-ext"; }

    sros-ext:sros-major-release "rel22";

    organization "Nokia";

    contact
        "Nokia SR OS Support
         Web: <http://www.nokia.com>";

    description
        "Common cellular data types used in the SR OS management system.

         Copyright 2016 Nokia. All rights reserved. Reproduction of this document
         is authorized on the condition that the foregoing copyright notice is included.

         This nokia-types-cellular YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";

    revision "2018-09-18";

    typedef imsi {
        type string {
            length "0..15";
        }
        description "Indicates an International Mobile Subscriber Identity (IMSI).";
    }

    typedef apn {
        type string {
            length "1..100";
        }
        description "Specifies an Access Point Name of a cellular Packet Data Network (PDN)";
    }

}
