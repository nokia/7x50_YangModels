submodule nokia-state-qos {

    yang-version "1.1";

    belongs-to nokia-state { prefix "state"; }

    import nokia-sros-yang-extensions     { prefix "sros-ext"; }
    import nokia-types-qos                { prefix "types-qos"; }
    import nokia-types-sros               { prefix "types-sros"; }


    sros-ext:sros-major-release "rel20";

    organization "Nokia";

    contact
        "Nokia SR OS Support
         Web: <http://www.nokia.com>";

    description
        "Nokia YANG Data model with operational state for QoS policies on SR OS based routers.

         Copyright 2016 Nokia. All rights reserved. Reproduction of this document
         is authorized on the condition that the foregoing copyright notice is included.

         This nokia-state-qos YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";

    revision "2020-03-09";

    grouping state-qos {
        container qos {
            description "Enter the qos context";

            list sap-ingress {
                key "sap-ingress-policy-name";
                description "Enter the sap-ingress list instance";

                leaf sap-ingress-policy-name {
                    type types-qos:qos-policy-name;
                    description "Name of this SAP-ingress QoS policy";
                }

                leaf oper-policy-id {
                    type types-qos:qos-any-policy-id;
                    description "The sap-ingress QoS policy identifier.";
                }

                container subscriber-mgmt {
                    description "Enter the subscriber-mgmt context";

                    leaf num-policies {
                        type uint32;
                        description
                            "Specifies the number of pcc-rule shared policies that are currently created based on
                             this policy.";
                    }

                    container pcc-rule-entry {
                        description "Enter the pcc-rule-entry context";

                        leaf num-inserted {
                            type uint32;
                            description
                                "Specifies the number of pcc-rule IP criteria entries received from
                                 DIAMETER that have been inserted in this policy.";
                        }

                    } // container pcc-rule-entry

                    container dynamic-policer {
                        description "Enter the dynamic-policer context";

                        leaf num-inserted {
                            type uint32;
                            description
                                "Specifies the number of dynamic policers required for pcc-rule IP criteria entries
                                 received from Diameter that have been inserted in this policy.";
                        }

                    } // container dynamic-policer

                } // container subscriber-mgmt

            } // list sap-ingress

            container queue-group-templates {
                description "Enter the queue-group-templates context";

                container ingress {
                    description "Enter the ingress context";

                    list queue-group {
                        key "ingress-queue-group-name";
                        description "Enter the queue-group list instance";

                        leaf ingress-queue-group-name {
                            type types-sros:named-item;
                            description "Name of Ingress Queue Group";
                        }

                        list queue {
                            key "queue-id";
                            description "Enter the queue list instance";

                            leaf queue-id {
                                type types-qos:ingress-queue-id;
                                description "Ingress Queue-Group Queue identifier";
                            }

                        } // list queue

                        list policer {
                            key "policer-id";
                            description "Enter the policer list instance";

                            leaf policer-id {
                                type types-qos:ingress-policer-id {
                                    range "1..32";
                                }
                                description "Ingress Queue-Group Policer identifier";
                            }

                        } // list policer

                    } // list queue-group

                } // container ingress

                container egress {
                    description "Enter the egress context";

                    list queue-group {
                        key "egress-queue-group-name";
                        description "Enter the queue-group list instance";

                        leaf egress-queue-group-name {
                            type types-sros:named-item;
                            description "Name of Egress Queue Group";
                        }

                        list queue {
                            key "queue-id";
                            description "Enter the queue list instance";

                            leaf queue-id {
                                type types-qos:egress-queue-id;
                                description "Egress Queue-Group queue identifier";
                            }

                        } // list queue

                    } // list queue-group

                } // container egress

            } // container queue-group-templates

            list network {
                key "network-policy-name";
                description "Enter the network list instance";

                leaf network-policy-name {
                    type types-qos:network-policy-name;
                    description "Name of this network QoS policy";
                }

                leaf oper-policy-id {
                    type types-qos:qos-any-policy-id;
                    description "Network QoS policy identifier.";
                }

            } // list network

            list sap-egress {
                key "sap-egress-policy-name";
                description "Enter the sap-egress list instance";

                leaf sap-egress-policy-name {
                    type types-qos:qos-policy-name;
                    description "Name of this sap-egress QoS policy";
                }

                leaf oper-policy-id {
                    type types-qos:qos-any-policy-id;
                    description "The sap-egress QoS policy identifier.";
                }

                container subscriber-mgmt {
                    description "Enter the subscriber-mgmt context";

                    leaf num-policies {
                        type uint32;
                        description
                            "Specifies the number of pcc-rule shared policies that are currently created based on
                             this policy.";
                    }

                    container pcc-rule-entry {
                        description "Enter the pcc-rule-entry context";

                        leaf num-inserted {
                            type uint32;
                            description
                                "Specifies the number of pcc-rule IP criteria entries received from
                                 DIAMETER that have been inserted in this policy.";
                        }

                    } // container pcc-rule-entry

                    container dynamic-policer {
                        description "Enter the dynamic-policer context";

                        leaf num-inserted {
                            type uint32;
                            description
                                "Specifies the number of dynamic policers required for pcc-rule IP criteria entries
                                 received from Diameter that have been inserted in this policy.";
                        }

                    } // container dynamic-policer

                } // container subscriber-mgmt

            } // list sap-egress

        } // container qos

    } // grouping state-qos

}
