submodule nokia-conf-svc-vprn {

    yang-version "1.1";

    belongs-to nokia-conf { prefix "conf"; }

    import ietf-inet-types                { prefix "inet"; }
    import ietf-yang-types                { prefix "yang"; }
    import nokia-sros-yang-extensions     { prefix "sros-ext"; }
    import nokia-types-bgp                { prefix "types-bgp"; }
    import nokia-types-eth-cfm            { prefix "types-eth-cfm"; }
    import nokia-types-igmp               { prefix "types-igmp"; }
    import nokia-types-ipsec              { prefix "types-ipsec"; }
    import nokia-types-l2tp               { prefix "types-l2tp"; }
    import nokia-types-log                { prefix "types-log"; }
    import nokia-types-mcast-cac          { prefix "types-mcast-cac"; }
    import nokia-types-nat                { prefix "types-nat"; }
    import nokia-types-ppp                { prefix "types-ppp"; }
    import nokia-types-qos                { prefix "types-qos"; }
    import nokia-types-redundancy         { prefix "types-redundancy"; }
    import nokia-types-router             { prefix "types-router"; }
    import nokia-types-services           { prefix "types-services"; }
    import nokia-types-sros               { prefix "types-sros"; }
    import nokia-types-subscriber-mgmt    { prefix "types-submgt"; }

    include nokia-conf-aaa;
    include nokia-conf-bfd;
    include nokia-conf-bmp;
    include nokia-conf-eth-cfm;
    include nokia-conf-filter;
    include nokia-conf-groups;
    include nokia-conf-ipsec;
    include nokia-conf-isa;
    include nokia-conf-log;
    include nokia-conf-mcast-cac;
    include nokia-conf-mcast-mgmt;
    include nokia-conf-policy-options;
    include nokia-conf-pxc;
    include nokia-conf-python;
    include nokia-conf-qos;
    include nokia-conf-redundancy;
    include nokia-conf-router;
    include nokia-conf-router-mpls;
    include nokia-conf-routing-options;
    include nokia-conf-service;
    include nokia-conf-submgt-gtp;
    include nokia-conf-submgt-local-user-db;
    include nokia-conf-subscriber-mgmt;
    include nokia-conf-svc-epipe;
    include nokia-conf-svc-nat;
    include nokia-conf-svc-vprn-dhcp-server;
    include nokia-conf-svc-vprn-isis;
    include nokia-conf-svc-vprn-msdp;
    include nokia-conf-svc-vprn-ospf;
    include nokia-conf-svc-vprn-ospf3;
    include nokia-conf-svc-vprn-radius;
    include nokia-conf-svc-vprn-rip;
    include nokia-conf-svc-vprn-ripng;
    include nokia-conf-svc-vprn-sub-if;
    include nokia-conf-svc-vprn-twamp-light;
    include nokia-conf-svc-vprn-vdo-if;
    include nokia-conf-system;
    include nokia-conf-system-security;
    include nokia-conf-system-security-aaa;
    include nokia-conf-system-security-snmp;
    include nokia-conf-vrrp;

    sros-ext:sros-major-release "rel20";

    organization "Nokia";

    contact
        "Nokia SR OS Support
         Web: <http://www.nokia.com>";

    description
        "Nokia YANG Data model to configure vprn services on SR OS based routers.

         Copyright 2016 Nokia. All rights reserved. Reproduction of this document
         is authorized on the condition that the foregoing copyright notice is included.

         This nokia-conf-svc-vprn YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";

    revision "2020-02-05";

    grouping conf-svc-vprn {
        list vprn {
            key "service-name";
            description "Enter the vprn list instance";

            leaf service-name {
                type types-services:service-name;
                description "Service name";
            }

            leaf service-id {
                type types-services:external-service-id;
                sros-ext:immutable;
                description "Unique service ID; cannot be used by any other service, regardless of service type";
            }

            leaf description {
                type types-sros:description;
                description "Text description";
            }

            leaf customer {
                type leafref {
                    path "../../customer/customer-name";
                }
                sros-ext:immutable;
                mandatory true;
                description "Service customer ID";
            }

            leaf admin-state {
                type types-sros:admin-state;
                default "disable";
                description "Administrative state of the mirror destination service";
            }

            leaf hash-label {
                type boolean;
                default "false";
                description "Include hash label";
            }

            leaf autonomous-system {
                type uint32 {
                    range "1..max";
                }
                description "AS number advertised to peers for this router";
            }

            leaf ecmp {
                type types-router:ip-ecmp;
                default "1";
                description "Maximum equal-cost routes for routing table instance";
            }

            leaf entropy-label {
                type boolean;
                default "false";
                description "Use entropy label";
            }

            leaf fib-priority {
                type enumeration {
                    enum "standard"                     { value 1; }
                    enum "high"                         { value 2; }
                }
                default "standard";
                description "FIB priority for VPRN BGP routes";
            }

            leaf multicast-info-policy {
                type leafref {
                    path "../../../multicast-management/multicast-info-policy/policy-name";
                }
                description "Multicast policy name for virtual router";
            }

            leaf router-id {
                type types-router:router-id;
                description "Unique router ID for the router in the AS";
            }

            leaf weighted-ecmp {
                type enumeration {
                    enum "false"                        { value 0; }
                    enum "true"                         { value 1; }
                    enum "strict"                       { value 2; }
                }
                default "false";
                description "Allow weighted load-balancing";
            }

            leaf route-distinguisher {
                type types-services:vpn-route-distinguisher-or-auto-rd;
                sros-ext:auto-restart-to-modify;
                description "Route distinguisher";
            }

            leaf label-mode {
                type enumeration {
                    enum "vrf"                          { value 1; }
                    enum "next-hop"                     { value 2; }
                }
                sros-ext:auto-restart-to-modify;
                default "vrf";
                description "Allocation mode for VPRN service labels";
            }

            leaf allow-export-bgp-vpn {
                type boolean;
                default "false";
                description "Include BGP-VPN routes for export";
            }

            leaf ignore-nh-metric {
                type boolean;
                default "false";
                description "Ignore next hop metric";
            }

            leaf export-inactive-bgp {
                type boolean;
                default "false";
                description "Export best BGP route as a VPN-IP route even if inactive due to a preferred route from another PE";
            }

            leaf ecmp-unequal-cost {
                type boolean;
                default "false";
                description "Enable/disable ecmp unequal cost capability. If enabled, BGP paths with unequal cost can be part of the same ECMP set.";
            }

            leaf class-forwarding {
                type boolean;
                default "false";
                description "Enable/disable class forwarding. If class forwarding is enabled, packets are forwarded based on their forwarding class.";
            }

            leaf vprn-type {
                type enumeration {
                    enum "regular"                      { value 1; }
                    enum "hub"                          { value 2; }
                    enum "spoke"                        { value 3; }
                    enum "subscriber-split-horizon"     { value 4; }
                }
                sros-ext:auto-restart-to-modify;
                default "regular";
                description "VPRN type";
            }

            leaf carrier-carrier-vpn {
                type boolean;
                default "false";
                description "Allow VPRN service to support a Carrier Supporting Carrier model";
            }

            leaf selective-fib {
                type boolean;
                default "true";
                description "Enable/disable selective FIB. If disabled, all active routes of this routing instance are installed on all line cards.";
            }

            leaf-list apply-groups {
                type leafref {
                    path "../../../groups/group/name";
                }
                max-elements 8;
                ordered-by user;
                description "Apply a configuration group at this level";
            }

            container nat {
                presence "NAT";
                description "Enter the nat context";

                leaf-list apply-groups {
                    type leafref {
                        path "../../../../groups/group/name";
                    }
                    max-elements 8;
                    ordered-by user;
                    description "Apply a configuration group at this level";
                }

                container inside {
                    description "Enter the inside context";

                    container l2-aware {
                        description "Enter the l2-aware context";

                        list subscribers {
                            key "prefix";
                            description "Add a list entry for subscribers";

                            leaf prefix {
                                type types-sros:ipv4-prefix-with-host-bits;
                                description "Layer-2 Aware NAT subscriber prefix";
                            }

                        } // list subscribers

                    } // container l2-aware

                    container large-scale {
                        description "Enter the large-scale context";

                        leaf nat-policy {
                            type leafref {
                                path "../../../../../nat/nat-policy/name";
                            }
                            sros-ext:isa-auto-clear-on-modify;
                            description "NAT policy for LSN";
                        }

                        container nat44 {
                            description "Enter the nat44 context";

                            leaf max-subscriber-limit {
                                type types-nat:lsn-max-subscriber-limit;
                                sros-ext:isa-auto-clear-on-modify;
                                description "Largest value for all subscriber limits in each deterministic pool";
                            }

                            list destination-prefix {
                                key "ip-prefix-length";
                                max-elements 1024;
                                description "Enter the destination-prefix list instance";

                                leaf ip-prefix-length {
                                    type types-sros:ipv4-unicast-prefix;
                                    description "Traffic sent to destinations within this prefix will be NATed";
                                }

                                leaf nat-policy {
                                    type leafref {
                                        path "../../../../../../../nat/nat-policy/name";
                                    }
                                    sros-ext:isa-auto-clear-on-modify;
                                    description "NAT policy";
                                }

                                leaf-list apply-groups {
                                    type leafref {
                                        path "../../../../../../../../groups/group/name";
                                    }
                                    max-elements 8;
                                    ordered-by user;
                                    description "Apply a configuration group at this level";
                                }

                            } // list destination-prefix

                            container deterministic {
                                description "Enter the deterministic context";

                                list policy-map {
                                    key "source-prefix";
                                    description "Enter the policy-map list instance";

                                    leaf source-prefix {
                                        type types-sros:ipv4-unicast-prefix;
                                        description "Source prefix that adds traffic to NAT pool";
                                    }

                                    leaf nat-policy {
                                        type leafref {
                                            path "../../../../../../../../nat/nat-policy/name";
                                        }
                                        sros-ext:immutable;
                                        sros-ext:isa-auto-clear-on-modify;
                                        mandatory true;
                                        description "NAT policy";
                                    }

                                    leaf admin-state {
                                        type types-sros:admin-state;
                                        default "disable";
                                        description "Administrative state of this prefix";
                                    }

                                    leaf-list apply-groups {
                                        type leafref {
                                            path "../../../../../../../../../groups/group/name";
                                        }
                                        max-elements 8;
                                        ordered-by user;
                                        description "Apply a configuration group at this level";
                                    }

                                    list map {
                                        key "from to";
                                        description "Enter the map list instance";

                                        leaf from {
                                            type types-sros:ipv4-address;
                                            description "Beginning of the range for IPv4 addresses that is mapped on the inside to outside IPv4 addresses";
                                        }

                                        leaf to {
                                            type types-sros:ipv4-address;
                                            description "Ending of the range for IPv4 addresses that is mapped on the inside to outside IPv4 addresses";
                                        }

                                        leaf first-outside-address {
                                            type types-sros:ipv4-address;
                                            sros-ext:immutable;
                                            mandatory true;
                                            description "IPv6 address range that is mapped to outside IPv4 address";
                                        }

                                        leaf-list apply-groups {
                                            type leafref {
                                                path "../../../../../../../../../../groups/group/name";
                                            }
                                            max-elements 8;
                                            ordered-by user;
                                            description "Apply a configuration group at this level";
                                        }

                                    } // list map

                                } // list policy-map

                            } // container deterministic

                        } // container nat44

                        container dual-stack-lite {
                            description "Enter the dual-stack-lite context";

                            leaf admin-state {
                                type types-sros:admin-state;
                                default "disable";
                                description "Administrative state of Dual Stack Lite";
                            }

                            leaf max-subscriber-limit {
                                type types-nat:lsn-max-subscriber-limit;
                                sros-ext:isa-auto-clear-on-modify;
                                description "Largest value for all subscriber limits in each deterministic pool";
                            }

                            leaf subscriber-prefix-length {
                                type types-nat:ipv6-subscriber-prefix-length;
                                sros-ext:auto-restart-to-modify;
                                sros-ext:isa-auto-clear-on-modify;
                                description "IPv6 prefix length of the Dual Stack Lite subscribers";
                            }

                            list endpoint {
                                key "address";
                                max-elements 128;
                                description "Enter the endpoint list instance";

                                leaf address {
                                    type types-sros:ipv6-address;
                                    description "Dual Stack Lite IPv6 address";
                                }

                                leaf ip-fragmentation {
                                    type types-nat:ip-fragmentation;
                                    description "Fragmentation control of the AFTR originated downstream IPv6 traffic";
                                }

                                leaf tunnel-mtu {
                                    type uint32 {
                                        range "512..9212";
                                    }
                                    default "1500";
                                    description "Maximum size of IPv4 packet inside of DS-Lite tunnel";
                                }

                                leaf reassembly {
                                    type boolean;
                                    default "false";
                                    description "Reassembly of IPv6 payload datagrams";
                                }

                                leaf-list apply-groups {
                                    type leafref {
                                        path "../../../../../../../../groups/group/name";
                                    }
                                    max-elements 8;
                                    ordered-by user;
                                    description "Apply a configuration group at this level";
                                }

                            } // list endpoint

                            container deterministic {
                                description "Enter the deterministic context";

                                list policy-map {
                                    key "source-prefix";
                                    description "Enter the policy-map list instance";

                                    leaf source-prefix {
                                        type types-sros:ipv6-unicast-prefix;
                                        description "Source prefix that adds traffic to NAT pool";
                                    }

                                    leaf nat-policy {
                                        type leafref {
                                            path "../../../../../../../../nat/nat-policy/name";
                                        }
                                        sros-ext:immutable;
                                        sros-ext:isa-auto-clear-on-modify;
                                        mandatory true;
                                        description "NAT policy";
                                    }

                                    leaf admin-state {
                                        type types-sros:admin-state;
                                        default "disable";
                                        description "Administrative state of this prefix";
                                    }

                                    leaf-list apply-groups {
                                        type leafref {
                                            path "../../../../../../../../../groups/group/name";
                                        }
                                        max-elements 8;
                                        ordered-by user;
                                        description "Apply a configuration group at this level";
                                    }

                                    list map {
                                        key "from to";
                                        description "Enter the map list instance";

                                        leaf from {
                                            type types-sros:ipv6-prefix;
                                            description "Beginning of the range for IPv6 addresses that is mapped on the inside to outside IPv6addresses";
                                        }

                                        leaf to {
                                            type types-sros:ipv6-prefix;
                                            description "Ending of the range for IPv6 addresses that is mapped on the inside to outside IPv6 addresses";
                                        }

                                        leaf first-outside-address {
                                            type types-sros:ipv4-address;
                                            sros-ext:immutable;
                                            mandatory true;
                                            description "IPv6 address range that is mapped to outside IPv4 address";
                                        }

                                        leaf-list apply-groups {
                                            type leafref {
                                                path "../../../../../../../../../../groups/group/name";
                                            }
                                            max-elements 8;
                                            ordered-by user;
                                            description "Apply a configuration group at this level";
                                        }

                                    } // list map

                                } // list policy-map

                            } // container deterministic

                        } // container dual-stack-lite

                        container nat64 {
                            presence "NAT64";
                            description "Enter the nat64 context";

                            leaf admin-state {
                                type types-sros:admin-state;
                                default "disable";
                                description "Administrative state of NAT64";
                            }

                            leaf drop-zero-ipv4-checksum {
                                type boolean;
                                default "false";
                                description "Drop UDP datagrams with zero IPv4 checksum";
                            }

                            leaf insert-ipv6-fragment-header {
                                type boolean;
                                default "false";
                                description "Include IPv6 fragment header to indicate that the sender allows fragmentation";
                            }

                            leaf ip-fragmentation {
                                type types-nat:ip-fragmentation;
                                description "Control fragmentation of originated downstream IPv6 traffic";
                            }

                            leaf ipv6-mtu {
                                type uint32 {
                                    range "1280..9212";
                                }
                                default "1520";
                                description "Size of the IPv6 downstream packet in NAT64";
                            }

                            leaf prefix {
                                type types-sros:ipv6-prefix;
                                sros-ext:isa-auto-clear-on-modify;
                                default "64:ff9b::/96";
                                description "IPv6 prefix to derive the IPv6 address from the IPv4 address";
                            }

                            leaf subscriber-prefix-length {
                                type types-nat:ipv6-subscriber-prefix-length;
                                sros-ext:isa-auto-clear-on-modify;
                                description "IPv6 prefix length for the NAT64 subscribers";
                            }

                            leaf-list apply-groups {
                                type leafref {
                                    path "../../../../../../../groups/group/name";
                                }
                                max-elements 8;
                                ordered-by user;
                                description "Apply a configuration group at this level";
                            }

                            container tos {
                                description "Enter the tos context";

                                container upstream {
                                    description "Enter the upstream context";

                                    leaf set-tos {
                                        type union {
                                            type enumeration {
                                                enum "use-ipv6"                     { value -1; }
                                            }
                                            type uint32 {
                                                range "0..255";
                                            }
                                        }
                                        default "use-ipv6";
                                        description "TOS/DSCP bits in IPv4 frame in the upstream direction";
                                    }

                                } // container upstream

                                container downstream {
                                    description "Enter the downstream context";

                                    leaf use-ipv4 {
                                        type boolean;
                                        default "false";
                                        description "Copy TOS/DSCP bits from the incoming IPv4 frame to the outgoing IPv6 frame";
                                    }

                                } // container downstream

                            } // container tos

                        } // container nat64

                        container subscriber-identification {
                            description "Enter the subscriber-identification context";

                            leaf admin-state {
                                type types-sros:admin-state;
                                default "disable";
                                description "Administrative state of subscriber identification";
                            }

                            leaf description {
                                type types-sros:description;
                                description "Text description";
                            }

                            leaf drop-unidentified-traffic {
                                type boolean;
                                default "false";
                                description "Drop traffic from unidentified flows";
                            }

                            leaf-list apply-groups {
                                type leafref {
                                    path "../../../../../../../groups/group/name";
                                }
                                max-elements 8;
                                ordered-by user;
                                description "Apply a configuration group at this level";
                            }

                            container attribute {
                                description "Enter the attribute context";

                                leaf vendor {
                                    type types-nat:nat-subscriber-identification-attr-vendor-id;
                                    default "nokia";
                                    description "The RADIUS Vendor";
                                }

                                leaf type {
                                    type types-nat:nat-subscriber-identification-attr-type;
                                    default "alc-sub-string";
                                    description "The RADIUS Vendor-Id value corresponding with this vendor.";
                                }

                            } // container attribute

                            container radius-proxy-server {
                                presence "The RADIUS Proxy server to use";
                                description "Enter the radius-proxy-server context";

                                leaf router-instance {
                                    type string;
                                    mandatory true;
                                    description "Router instance";
                                }

                                leaf server {
                                    type types-sros:named-item;
                                    mandatory true;
                                    description "Server name";
                                }

                            } // container radius-proxy-server

                        } // container subscriber-identification

                        container dnat-only {
                            description "Enter the dnat-only context";

                            leaf source-prefix-list {
                                type leafref {
                                    path "../../../../../../nat/prefix-list/name";
                                }
                                description "NAT prefix list that contains source IP addresses";
                            }

                        } // container dnat-only

                        container redundancy {
                            description "Enter the redundancy context";

                            leaf peer {
                                type types-sros:ipv4-unicast-address;
                                description "IP address of the NAT redundancy peer for this virtual router instance";
                            }

                            leaf peer6 {
                                type types-sros:ipv6-unicast-address;
                                description "IPv6 address of the NAT redundancy peer for this virtual router instance";
                            }

                            leaf steering-route {
                                type types-sros:ipv4-unicast-prefix;
                                description "IP address and prefix length of the steering route";
                            }

                        } // container redundancy

                        container filters {
                            description "Enter the filters context";

                            container downstream {
                                description "Enter the downstream context";

                                leaf ipv4 {
                                    type leafref {
                                        path "../../../../../../../../filter/ip-filter/filter-name";
                                    }
                                    description "IP filter for downstream traffic";
                                }

                            } // container downstream

                        } // container filters

                    } // container large-scale

                } // container inside

                container outside {
                    description "Enter the outside context";

                    leaf mtu {
                        type uint32 {
                            range "512..9000";
                        }
                        description "MTU for downstream traffic";
                    }

                    container filters {
                        description "Enter the filters context";

                        container downstream {
                            description "Enter the downstream context";

                            leaf ipv4 {
                                type leafref {
                                    path "../../../../../../../filter/ip-filter/filter-name";
                                }
                                description "IP filter for downstream traffic";
                            }

                            leaf ipv6 {
                                type leafref {
                                    path "../../../../../../../filter/ipv6-filter/filter-name";
                                }
                                description "IPv6 filter for downstream traffic";
                            }

                        } // container downstream

                        container upstream {
                            description "Enter the upstream context";

                            leaf ipv4 {
                                type leafref {
                                    path "../../../../../../../filter/ip-filter/filter-name";
                                }
                                description "IP filter for upstream traffic";
                            }

                            leaf ipv6 {
                                type leafref {
                                    path "../../../../../../../filter/ipv6-filter/filter-name";
                                }
                                description "IPv6 filter for upstream traffic";
                            }

                        } // container upstream

                    } // container filters

                    container dnat-only {
                        description "Enter the dnat-only context";

                        leaf route-limit {
                            type uint32 {
                                range "1..131072";
                            }
                            default "32768";
                            description "Number that is used to limit internal routes for downstream traffic";
                        }

                    } // container dnat-only

                    list pool {
                        key "name";
                        max-elements 1024;
                        description "Enter the pool list instance";

                        leaf name {
                            type types-sros:named-item;
                            description "NAT pool name";
                        }

                        leaf type {
                            type types-nat:pool-type;
                            sros-ext:immutable;
                            sros-ext:isa-auto-clear-on-modify;
                            mandatory true;
                            description "NAT pool type";
                        }

                        leaf description {
                            type types-sros:description;
                            description "Text description";
                        }

                        leaf mode {
                            type types-nat:pool-mode;
                            sros-ext:isa-auto-clear-on-modify;
                            description "Mode of operation of this NAT address pool";
                        }

                        leaf admin-state {
                            type types-sros:admin-state;
                            default "disable";
                            description "Administrative state of the outside NAT pool";
                        }

                        leaf-list apply-groups {
                            type leafref {
                                path "../../../../../../groups/group/name";
                            }
                            max-elements 8;
                            ordered-by user;
                            description "Apply a configuration group at this level";
                        }

                        choice isa {
                            mandatory true;
                            case nat {

                                leaf nat-group {
                                    type leafref {
                                        path "../../../../../../isa/nat-group/id";
                                    }
                                    sros-ext:immutable;
                                    sros-ext:isa-auto-clear-on-modify;
                                    description "Create a NAT group";
                                }

                            }
                            case wlan-gw {

                                leaf wlan-gw-group {
                                    type leafref {
                                        path "../../../../../../isa/wlan-gw-group/id";
                                    }
                                    sros-ext:immutable;
                                    sros-ext:isa-auto-clear-on-modify;
                                    description "Create a WLAN GW group for NAT";
                                }

                            }
                        }
                        container applications {
                            description "Enter the applications context";

                            leaf agnostic {
                                when "../../type = 'large-scale'";
                                type boolean;
                                sros-ext:immutable;
                                sros-ext:isa-auto-clear-on-modify;
                                default "false";
                                description "NAT pool to create in the outside routing context";
                            }

                        } // container applications

                        container port-forwarding {
                            description "Enter the port-forwarding context";

                            leaf dynamic-block-reservation {
                                when "not(../../type = 'l2-aware')";
                                type boolean;
                                sros-ext:isa-auto-clear-on-modify;
                                default "false";
                                description "Dynamic block to reserve for each subscriber with a forwarding port";
                            }

                            leaf range-end {
                                type uint16 {
                                    range "0|1023..65535";
                                }
                                sros-ext:isa-auto-clear-on-modify;
                                description "End of the wildcard range for port forwards";
                            }

                        } // container port-forwarding

                        container port-reservation {
                            description "Enter the port-reservation context";

                            choice port-reservation {
                                default "port-blocks";
                                case port-blocks {

                                    leaf port-blocks {
                                        type uint16 {
                                            range "1..64512";
                                        }
                                        sros-ext:isa-auto-clear-on-modify;
                                        description "Number of dynamic port blocks per outside IP address";
                                    }

                                }
                                case ports {

                                    leaf ports {
                                        type uint16 {
                                            range "1..32256";
                                        }
                                        sros-ext:isa-auto-clear-on-modify;
                                        description "Number of ports in each dynamic port block within the pool";
                                    }

                                }
                            }
                        } // container port-reservation

                        container watermarks {
                            presence "The watermarks.";
                            description "Enter the watermarks context";

                            leaf high {
                                type types-sros:percent;
                                mandatory true;
                                description "Percentage for high watermark";
                            }

                            leaf low {
                                type types-sros:percent;
                                mandatory true;
                                description "Percentage for low watermark";
                            }

                        } // container watermarks

                        container large-scale {
                            when "../type = 'large-scale'";
                            description "Enter the large-scale context";

                            leaf subscriber-limit {
                                type uint32 {
                                    range "1..65535";
                                }
                                sros-ext:isa-auto-clear-on-modify;
                                description "Maximum number of subscribers per IP address";
                            }

                            container redundancy {
                                description "Enter the redundancy context";

                                choice redundancy {
                                    default "export-monitor-route";
                                    case follow-pool {

                                        container follow {
                                            description "Enter the follow context";

                                            leaf router-instance {
                                                type string;
                                                description "The virtual router instance of the pool.";
                                            }

                                            leaf name {
                                                type types-sros:named-item;
                                                description "NAT pool name";
                                            }

                                        } // container follow

                                    }
                                    case export-monitor-route {

                                        leaf export-route {
                                            type types-sros:ipv4-unicast-prefix;
                                            description "Route to export to the peer";
                                        }

                                        leaf monitor-route {
                                            type types-sros:ipv4-unicast-prefix;
                                            description "Monitor the peer route";
                                        }

                                        leaf admin-state {
                                            type types-sros:admin-state;
                                            default "disable";
                                            description "Administrative state of multi-chassis redundancy";
                                        }

                                    }
                                }
                            } // container redundancy

                            container deterministic {
                                description "Enter the deterministic context";

                                leaf port-reservation {
                                    type types-nat:port-number;
                                    sros-ext:isa-auto-clear-on-modify;
                                    description "Number of ports per deterministic port-block";
                                }

                            } // container deterministic

                        } // container large-scale

                        container l2-aware {
                            when "../type = 'l2-aware'";
                            description "Enter the l2-aware context";

                            leaf external-assignment {
                                type boolean;
                                sros-ext:isa-auto-clear-on-modify;
                                default "false";
                                description "External IP address for Layer-2-aware";
                            }

                        } // container l2-aware

                        list address-range {
                            key "start end";
                            max-elements 4096;
                            description "Enter the address-range list instance";

                            leaf start {
                                type types-sros:ipv4-unicast-address;
                                description "Start address of this range";
                            }

                            leaf end {
                                type types-sros:ipv4-unicast-address;
                                description "End address of this range";
                            }

                            leaf description {
                                type types-sros:description;
                                description "Text description";
                            }

                            leaf drain {
                                type boolean;
                                default "false";
                                description "Start or stop draining this NAT address range";
                            }

                            leaf-list apply-groups {
                                type leafref {
                                    path "../../../../../../../groups/group/name";
                                }
                                max-elements 8;
                                ordered-by user;
                                description "Apply a configuration group at this level";
                            }

                        } // list address-range

                    } // list pool

                } // container outside

                container map {
                    description "Enter the map context";

                    list map-domain {
                        key "domain-name";
                        description "Add a list entry for map-domain";

                        leaf domain-name {
                            type leafref {
                                path "../../../../../nat/map-t/domain/name";
                            }
                            description "MAP domain name";
                        }

                    } // list map-domain

                } // container map

            } // container nat

            container firewall {
                description "Enter the firewall context";

                leaf-list apply-groups {
                    type leafref {
                        path "../../../../groups/group/name";
                    }
                    max-elements 8;
                    ordered-by user;
                    description "Apply a configuration group at this level";
                }

                list domain {
                    key "name";
                    max-elements 1024;
                    description "Enter the domain list instance";

                    leaf name {
                        type types-sros:named-item;
                        description "Firewall domain name";
                    }

                    leaf admin-state {
                        type types-sros:admin-state;
                        default "disable";
                        description "Administrative state of the firewall domain";
                    }

                    leaf-list apply-groups {
                        type leafref {
                            path "../../../../../groups/group/name";
                        }
                        max-elements 8;
                        ordered-by user;
                        description "Apply a configuration group at this level";
                    }

                    choice isa {
                        mandatory true;
                        case nat {

                            leaf nat-group {
                                type leafref {
                                    path "../../../../../isa/nat-group/id";
                                }
                                sros-ext:immutable;
                                description "NAT group for this domain";
                            }

                        }
                        case wlan-gw {

                            leaf wlan-gw-group {
                                type leafref {
                                    path "../../../../../isa/wlan-gw-group/id";
                                }
                                sros-ext:immutable;
                                description "WLAN GW group used for NAT in this domain";
                            }

                        }
                    }
                    container dhcpv6-server {
                        description "Enter the dhcpv6-server context";

                        leaf router-instance {
                            type string;
                            sros-ext:auto-restart-to-modify;
                            description "Router name";
                        }

                        leaf name {
                            type types-sros:named-item;
                            sros-ext:auto-restart-to-modify;
                            description "DHCPv6 server name";
                        }

                    } // container dhcpv6-server

                    list prefix {
                        key "ip-prefix";
                        max-elements 4096;
                        description "Enter the prefix list instance";

                        leaf ip-prefix {
                            type types-sros:ipv6-unicast-prefix;
                            description "IP prefix and prefix length for the domain firewall";
                        }

                        leaf description {
                            type types-sros:description;
                            description "Text description";
                        }

                        leaf-list apply-groups {
                            type leafref {
                                path "../../../../../../groups/group/name";
                            }
                            max-elements 8;
                            ordered-by user;
                            description "Apply a configuration group at this level";
                        }

                    } // list prefix

                } // list domain

            } // container firewall

            container gtp {
                description "Enter the gtp context";

                container s11 {
                    description "Enter the s11 context";

                    list interface {
                        key "interface-name";
                        description "Enter the interface list instance";

                        leaf interface-name {
                            type leafref {
                                path "../../../../../vprn[service-name=current()/../../../../service-name]/interface/interface-name";
                            }
                            description "Interface where s11 is enabled.";
                        }

                        leaf apn-policy {
                            type leafref {
                                path "../../../../../../subscriber-mgmt/gtp/apn-policy/name";
                            }
                            description "The APN policy for this interface.";
                        }

                        leaf-list apply-groups {
                            type leafref {
                                path "../../../../../../groups/group/name";
                            }
                            max-elements 8;
                            ordered-by user;
                            description "Apply a configuration group at this level";
                        }

                    } // list interface

                    container peer-profile-map {
                        description "Enter the peer-profile-map context";

                        list prefix {
                            key "peer-prefix";
                            description "Enter the prefix list instance";

                            leaf peer-prefix {
                                type types-sros:ip-unicast-prefix;
                                description "Attribute ip-prefix/ip-prefix-length for address.";
                            }

                            leaf peer-profile {
                                type leafref {
                                    path "../../../../../../../subscriber-mgmt/gtp/peer-profile/name";
                                }
                                mandatory true;
                                description "Peer profile used for peers in this prefix";
                            }

                            leaf-list apply-groups {
                                type leafref {
                                    path "../../../../../../../groups/group/name";
                                }
                                max-elements 8;
                                ordered-by user;
                                description "Apply a configuration group at this level";
                            }

                        } // list prefix

                    } // container peer-profile-map

                } // container s11

                container uplink {
                    presence "GTP uplink connectivity to a PGW or GGSN";
                    description "Enter the uplink context";

                    leaf apn {
                        type string {
                            length "1..80";
                            pattern "([a-zA-Z0-9]+-+)*([a-zA-Z0-9]+\\.([a-zA-Z0-9]+-+)*)*[a-zA-Z0-9]+" {
                                error-message "wrong format of apn name";
                            }
                        }
                        description "Network Identifier part of APN";
                    }

                    leaf pdn-type {
                        type enumeration {
                            enum "ipv4"                         { value 0; }
                            enum "ipv6"                         { value 1; }
                            enum "ipv4v6"                       { value 2; }
                        }
                        default "ipv4";
                        description "Default 3GPP PDN in GTP";
                    }

                    leaf-list apply-groups {
                        type leafref {
                            path "../../../../../groups/group/name";
                        }
                        max-elements 8;
                        ordered-by user;
                        description "Apply a configuration group at this level";
                    }

                    container peer-profile-map {
                        description "Enter the peer-profile-map context";

                        list prefix {
                            key "peer-prefix";
                            description "Enter the prefix list instance";

                            leaf peer-prefix {
                                type types-sros:ip-unicast-prefix;
                                description "Attribute ip-prefix/ip-prefix-length for address.";
                            }

                            leaf peer-profile {
                                type leafref {
                                    path "../../../../../../../subscriber-mgmt/gtp/peer-profile/name";
                                }
                                mandatory true;
                                description "Peer profile name";
                            }

                            leaf-list apply-groups {
                                type leafref {
                                    path "../../../../../../../groups/group/name";
                                }
                                max-elements 8;
                                ordered-by user;
                                description "Apply a configuration group at this level";
                            }

                        } // list prefix

                    } // container peer-profile-map

                } // container uplink

            } // container gtp

            container l2tp {
                presence "L2TP for VPRN services.";
                description "Enter the l2tp context";

                leaf admin-state {
                    type types-sros:admin-state;
                    default "disable";
                    description "Administrative state of L2TP";
                }

                leaf local-address {
                    type types-sros:ipv4-unicast-address;
                    description "Local address";
                }

                leaf receive-window-size {
                    type types-l2tp:base-receive-window-size;
                    description "L2TP receive window size";
                }

                leaf hello-interval {
                    type types-l2tp:base-hello-interval;
                    description "Hello interval";
                }

                leaf idle-timeout {
                    type types-l2tp:base-idle-timeout;
                    description "Idle timeout";
                }

                leaf destruct-timeout {
                    type types-l2tp:base-destruct-timeout;
                    description "Destruction timeout";
                }

                leaf max-retries-estab {
                    type types-l2tp:base-max-retries;
                    description "Maximum retries for established tunnels";
                }

                leaf max-retries-not-estab {
                    type types-l2tp:base-max-retries;
                    description "Maximum retries for unestablished tunnels";
                }

                leaf rtm-debounce-time {
                    type types-l2tp:rtm-debounce-time;
                    description "Debounce timer that declares L2TP action for route table management events";
                }

                leaf radius-accounting-policy {
                    type leafref {
                        path "../../../../aaa/radius/l2tp-accounting-policy/name";
                    }
                    description "RADIUS accounting policy";
                }

                leaf peer-address-change-policy {
                    type types-l2tp:peer-address-change-policy-option;
                    description "Reaction when a L2TP response is received from a different address";
                }

                leaf local-name {
                    type types-l2tp:host-name;
                    description "Local host name";
                }

                leaf password {
                    type types-sros:encrypted-leaf {
                        length "1..115";
                    }
                    description "L2TP password";
                }

                leaf challenge {
                    type boolean;
                    default "false";
                    description "Use challenge-response authentication";
                }

                leaf avp-hiding {
                    type types-l2tp:base-avp-hiding;
                    description "Attribute of the Value Pair (AVP) hiding algorithm";
                }

                leaf session-limit {
                    type types-l2tp:base-session-limit;
                    description "L2TP session limit of this router";
                }

                leaf group-session-limit {
                    type types-l2tp:base-session-limit;
                    description "L2TP session limit for each group of this router";
                }

                leaf tunnel-session-limit {
                    type types-l2tp:base-tunnel-session-limit;
                    description "L2TP session limit for each tunnel of this router";
                }

                leaf session-assign-method {
                    type types-l2tp:base-session-assign-method;
                    description "Session assignment method";
                }

                leaf next-attempt {
                    type enumeration {
                        enum "same-preference-level"        { value 0; }
                        enum "next-preference-level"        { value 1; }
                    }
                    default "next-preference-level";
                    description "Tunnel that is selected when previous session setup failed";
                }

                leaf-list apply-groups {
                    type leafref {
                        path "../../../../groups/group/name";
                    }
                    max-elements 8;
                    ordered-by user;
                    description "Apply a configuration group at this level";
                }

                container exclude-avps {
                    description "Enter the exclude-avps context";

                    leaf calling-number {
                        type boolean;
                        default "false";
                        description "Calling Number AVP to exclude";
                    }

                    leaf initial-rx-lcp-conf-req {
                        type boolean;
                        default "false";
                        description "Exclude the Initial Received LCP CONFREQ AVP";
                    }

                } // container exclude-avps

                container ignore-avps {
                    description "Enter the ignore-avps context";

                    leaf sequencing-required {
                        type boolean;
                        default "false";
                        description "Ignore Sequencing Required AVP";
                    }

                } // container ignore-avps

                container replace-result-code {
                    description "Enter the replace-result-code context";

                    leaf cdn-invalid-dst {
                        type boolean;
                        default "false";
                        description "Enable/disable replacing result code 'Invalid destination' by result code 'General error' and general error code 'Insufficient resources to handle this operation now'.";
                    }

                    leaf cdn-permanent-no-facilities {
                        type boolean;
                        default "false";
                        description "Enable/disable replacing result code 'Call failed due to lack of appropriate facilities being available (permanent condition)''Invalid destination' by result code 'General error' and general error code 'Insufficient resources to handle this operation now'.";
                    }

                    leaf cdn-temporary-no-facilities {
                        type boolean;
                        default "false";
                        description "Enable/disable replacing result code 'Call failed due to lack of appropriate facilities being available (temporary condition)' by result code 'General error' and general error code 'Insufficient resources to handle this operation now'.";
                    }

                } // container replace-result-code

                container lac {
                    description "Enter the lac context";

                    leaf df-bit {
                        type boolean;
                        default "true";
                        description "Send all L2TP packets with DF bit set to 1";
                    }

                    leaf calling-number-format {
                        type types-sros:ascii-specification {
                            length "1..255";
                            pattern "([^%]+|%[Scrsl%])+";
                        }
                        default "%S %s";
                        description "Calling Number AVP for L2TP control messages";
                    }

                    container cisco-nas-port {
                        description "Enter the cisco-nas-port context";

                        leaf ethernet {
                            type types-sros:binary-specification {
                                pattern "([01]|(\\*[0123456789]+)?[smpoi])+";
                            }
                            description "L2TP Cisco NAS port AVP with binary patterns for Ethernet";
                        }

                    } // container cisco-nas-port

                } // container lac

                container tunnel-selection-blacklist {
                    description "Enter the tunnel-selection-blacklist context";

                    leaf max-time {
                        type int32 {
                            range "1..60";
                        }
                        units "minutes";
                        default "5";
                        description "Maximum time that a tunnel or peer can remain in the tunnel selection blacklist";
                    }

                    leaf max-list-length {
                        type union {
                            type int32 {
                                range "1..65535";
                            }
                            type enumeration {
                                enum "infinite"                     { value -1; }
                            }
                        }
                        default "infinite";
                        description "Tunnels or peers in the blacklist";
                    }

                    leaf timeout-action {
                        type enumeration {
                            enum "remove-from-blacklist"        { value 0; }
                            enum "try-one-session"              { value 1; }
                        }
                        default "remove-from-blacklist";
                        description "Action when a tunnel or peer remained in the blacklist for maximum time";
                    }

                    container add-tunnel-on {
                        description "Enter the add-tunnel-on context";

                        leaf address-change-timeout {
                            type boolean;
                            default "false";
                            description "Add to the blacklist in case of an address change timeout.";
                        }

                        leaf cdn-err-code {
                            type boolean;
                            default "false";
                            description "Add to blacklist if a CDN is received with code: General error";
                        }

                        leaf cdn-invalid-dst {
                            type boolean;
                            default "false";
                            description "Add to the blacklist in case a CDN is received with result code 'Invalid destination'.";
                        }

                        leaf cdn-permanent-no-facilities {
                            type boolean;
                            default "false";
                            description "Add to the blacklist in case a CDN is received with result code 'Call failed due to lack of appropriate facilities being available (permanent condition)'.";
                        }

                        leaf cdn-temporary-no-facilities {
                            type boolean;
                            default "false";
                            description "Add to the blacklist in case a CDN is received with result code 'Call failed due to lack of appropriate facilities being available (temporary condition)'.";
                        }

                        leaf stop-ccn-err-code {
                            type boolean;
                            default "false";
                            description "Add to blacklist if a StopCNN is received with code: General error";
                        }

                        leaf stop-ccn-other {
                            type boolean;
                            default "false";
                            description "Add to blacklist if a StopCNN is received with code: other than general error";
                        }

                        leaf tx-cdn-not-established-in-time {
                            type boolean;
                            default "false";
                            description "Add to blacklist if CDN transmitted with code: Call not established within time allotted by LAC";
                        }

                    } // container add-tunnel-on

                } // container tunnel-selection-blacklist

                container failover {
                    description "Enter the failover context";

                    leaf recovery-method {
                        type types-l2tp:base-failover-recovery-method;
                        description "Recovery method of the sequence numbers after failover";
                    }

                    leaf recovery-time {
                        type types-l2tp:base-failover-recovery-time;
                        description "Time requested from the L2TP peer before assuming failover as failed";
                    }

                    leaf recovery-max-session-lifetime {
                        type uint32 {
                            range "2..4294967295";
                        }
                        units "centiseconds";
                        default "2";
                        description "Subset of sessions that this system attempts to synchronize in the Session State Synchronization phase";
                    }

                    list track-srrp {
                        key "id";
                        description "Enter the track-srrp list instance";

                        leaf id {
                            type leafref {
                                path "../../../../../../redundancy/multi-chassis/peer/sync/track-srrp/id";
                            }
                            description "SRRP instance ID for multi-chassis redundancy failover";
                        }

                        leaf peer {
                            type leafref {
                                path "../../../../../../redundancy/multi-chassis/peer/ip-address";
                            }
                            mandatory true;
                            description "Multi-chassis peer address";
                        }

                        leaf sync-tag {
                            type types-sros:named-item;
                            mandatory true;
                            description "Synchronization tag on the multi-chassis peer";
                        }

                        leaf-list apply-groups {
                            type leafref {
                                path "../../../../../../groups/group/name";
                            }
                            max-elements 8;
                            ordered-by user;
                            description "Apply a configuration group at this level";
                        }

                    } // list track-srrp

                } // container failover

                container l2tpv3 {
                    description "Enter the l2tpv3 context";

                    leaf password {
                        type types-sros:encrypted-leaf {
                            length "1..115";
                        }
                        description "L2TPv3 password";
                    }

                    leaf cookie-length {
                        type types-l2tp:base-v3-cookie-length;
                        description "Cookie field length";
                    }

                    leaf digest-type {
                        type types-l2tp:base-v3-digest-type;
                        description "Hashing algorithm that calculates the message digest";
                    }

                    leaf nonce-length {
                        type types-l2tp:base-v3-nonce-length;
                        description "Length of the local L2TPv3 nonce (random number)";
                    }

                    leaf public-tcp-mss-adjust {
                        type types-l2tp:base-v3-tcp-mss-adjust;
                        description "TCP maximum segment size (MSS) on public network";
                    }

                    leaf private-tcp-mss-adjust {
                        type types-l2tp:base-v3-tcp-mss-adjust;
                        description "TCP maximum segment size (MSS) on private network";
                    }

                    container transport-type {
                        description "Enter the transport-type context";

                        leaf ip {
                            type boolean;
                            default "false";
                            description "Transport type that carries L2TPv3 tunnel";
                        }

                    } // container transport-type

                } // container l2tpv3

                container ethernet-tunnel {
                    description "Enter the ethernet-tunnel context";

                    leaf reconnect-timeout {
                        type types-l2tp:base-v3-reconnect-timeout;
                        description "Timeout for a session setup retry";
                    }

                } // container ethernet-tunnel

                list group {
                    key "tunnel-group-name";
                    description "Enter the group list instance";

                    leaf tunnel-group-name {
                        type types-sros:named-item-64 {
                            length "1..63";
                        }
                        description "Tunnel group name";
                    }

                    leaf admin-state {
                        type types-sros:admin-state;
                        default "disable";
                        description "Administrative state of the L2TP tunnel group";
                    }

                    leaf description {
                        type types-sros:description;
                        description "Text description";
                    }

                    leaf protocol {
                        type types-l2tp:protocol-version;
                        sros-ext:immutable;
                        description "Protocol version";
                    }

                    leaf local-address {
                        type types-sros:ipv4-unicast-address;
                        description "Local address";
                    }

                    leaf receive-window-size {
                        type types-l2tp:child-receive-window-size;
                        description "L2TP receive window size";
                    }

                    leaf hello-interval {
                        type types-l2tp:child-hello-interval;
                        description "Hello interval";
                    }

                    leaf idle-timeout {
                        type types-l2tp:child-idle-timeout;
                        description "Idle timeout";
                    }

                    leaf destruct-timeout {
                        type types-l2tp:child-destruct-timeout;
                        description "Destruction timeout";
                    }

                    leaf max-retries-estab {
                        type types-l2tp:child-max-retries;
                        description "Maximum retries for established tunnels";
                    }

                    leaf max-retries-not-estab {
                        type types-l2tp:child-max-retries;
                        description "Maximum retries for unestablished tunnels";
                    }

                    leaf radius-accounting-policy {
                        type leafref {
                            path "../../../../../aaa/radius/l2tp-accounting-policy/name";
                        }
                        description "RADIUS accounting policy";
                    }

                    leaf local-name {
                        type types-l2tp:host-name;
                        description "The local host name.";
                    }

                    leaf password {
                        type types-sros:encrypted-leaf {
                            length "1..115";
                        }
                        description "The password.";
                    }

                    leaf challenge {
                        type types-sros:bool-with-inherit;
                        description "Enable/disable the use of challenge-response authentication.";
                    }

                    leaf avp-hiding {
                        type types-l2tp:child-avp-hiding;
                        description "The AVP hiding algorithm";
                    }

                    leaf session-limit {
                        type types-l2tp:child-session-limit;
                        description "Session limit";
                    }

                    leaf session-assign-method {
                        type types-l2tp:child-session-assign-method;
                        description "Session assignment method";
                    }

                    leaf-list apply-groups {
                        type leafref {
                            path "../../../../../groups/group/name";
                        }
                        max-elements 8;
                        ordered-by user;
                        description "Apply a configuration group at this level";
                    }

                    container failover {
                        when "../protocol = 'v2'";
                        description "Enter the failover context";

                        leaf recovery-method {
                            type types-l2tp:child-failover-recovery-method;
                            description "Recovery method of the sequence numbers after failover";
                        }

                        leaf recovery-time {
                            type types-l2tp:child-failover-recovery-time;
                            description "Time requested from the L2TP peer before assuming failover as failed";
                        }

                    } // container failover

                    container lac {
                        when "../protocol = 'v2'";
                        description "Enter the lac context";

                        leaf df-bit {
                            type types-sros:bool-with-inherit;
                            description "DF (do not fragment) bit in data traffic transmitted as LAC";
                        }

                    } // container lac

                    container l2tpv3 {
                        when "not(../protocol = 'v2')";
                        description "Enter the l2tpv3 context";

                        leaf rem-router-id {
                            type types-sros:ipv4-address;
                            default "0.0.0.0";
                            description "Filter on remote router ID";
                        }

                        leaf password {
                            type types-sros:encrypted-leaf {
                                length "1..115";
                            }
                            description "L2TPv3 password";
                        }

                        leaf track-password-change {
                            type boolean;
                            default "false";
                            description "Enable tracking of password changes";
                        }

                        leaf cookie-length {
                            type types-l2tp:child-v3-cookie-length;
                            description "Cookie field length";
                        }

                        leaf digest-type {
                            type types-l2tp:child-v3-digest-type;
                            description "Hashing algorithm that calculates the message digest";
                        }

                        leaf nonce-length {
                            type types-l2tp:child-v3-nonce-length;
                            description "Length for the local L2TPv3 nonce (random number)";
                        }

                        leaf public-tcp-mss-adjust {
                            type types-l2tp:child-v3-tcp-mss-adjust;
                            description "TCP Maximum Segment Size (MSS) on public network";
                        }

                        leaf private-tcp-mss-adjust {
                            type types-l2tp:child-v3-tcp-mss-adjust;
                            description "TCP maximum segment size (MSS) on private network";
                        }

                        container pw-cap-list {
                            description "Enter the pw-cap-list context";

                            leaf ethernet {
                                type boolean;
                                sros-ext:auto-restart-to-modify;
                                default "false";
                                description "Advertise Ethernet pseudowire type";
                            }

                            leaf ethernet-vlan {
                                type boolean;
                                sros-ext:auto-restart-to-modify;
                                default "false";
                                description "Advertise Ethernet VLAN pseudowire type";
                            }

                        } // container pw-cap-list

                    } // container l2tpv3

                    container ethernet-tunnel {
                        when "not(../protocol = 'v2')";
                        description "Enter the ethernet-tunnel context";

                        leaf reconnect-timeout {
                            type types-l2tp:child-v3-reconnect-timeout;
                            description "Timeout for a session setup retry at group level";
                        }

                    } // container ethernet-tunnel

                    container lns {
                        when "../protocol = 'v2'";
                        description "Enter the lns context";

                        leaf load-balance-method {
                            type types-l2tp:base-load-balance-method;
                            default "per-session";
                            description "New sessions for L2TP ISA MDA";
                        }

                        leaf lns-group {
                            type leafref {
                                path "../../../../../../isa/lns-group/id";
                            }
                            description "ISA LNS group";
                        }

                        container ppp {
                            description "Enter the ppp context";

                            leaf authentication-policy {
                                type types-sros:named-item;
                                description "Authentication policy when a DHCP message is received";
                            }

                            leaf user-db {
                                type types-sros:named-item;
                                description "Local user database for PPP PAP and CHAP authentication";
                            }

                            leaf proxy-lcp {
                                type boolean;
                                default "false";
                                description "Proxy LCP AVPs that are received from LAC";
                            }

                            leaf lcp-ignore-magic-numbers {
                                type boolean;
                                default "false";
                                description "Check Magic-Number field in LCP Echo-Request and LCP Echo-Reply messages";
                            }

                            leaf lcp-force-ack-accm {
                                type boolean;
                                default "false";
                                description "Force acknowledgement of the LCP Asynchronous Control Character Map (ACCM) option";
                            }

                            leaf reject-disabled-ncp {
                                type boolean;
                                default "false";
                                description "Enable/disable rejection of disabled Network Control Protocols (NCP)";
                            }

                            leaf mtu {
                                type types-l2tp:base-ppp-mtu;
                                default "1500";
                                description "Maximum PPP MTU size";
                            }

                            leaf proxy-authentication {
                                type boolean;
                                default "false";
                                description "Use authentication AVPs that are received from LAC";
                            }

                            leaf authentication {
                                type types-l2tp:base-ppp-auth-protocol;
                                default "pref-chap";
                                description "PPP authentication protocol to negotiate";
                            }

                            leaf ipcp-subnet-negotiation {
                                type boolean;
                                default "false";
                                description "Allow IPCP subnet negotiation for PPPoE hosts";
                            }

                            container default-group-interface {
                                description "Enter the default-group-interface context";

                                leaf interface {
                                    type types-sros:named-item;
                                    description "Group interface";
                                }

                                leaf service-name {
                                    type types-services:service-name;
                                    description "Service name";
                                }

                            } // container default-group-interface

                            container keepalive {
                                description "Enter the keepalive context";

                                leaf interval {
                                    type types-l2tp:base-lcp-keepalive-interval;
                                    default "30";
                                    description "PPP keepalive interval";
                                }

                                leaf multiplier {
                                    type types-l2tp:base-lcp-keepalive-multiplier;
                                    default "3";
                                    description "PPP keepalive multiplier";
                                }

                            } // container keepalive

                            container chap-challenge-length {
                                description "Enter the chap-challenge-length context";

                                leaf start {
                                    type types-l2tp:base-chap-challenge-length;
                                    default "32";
                                    description "Minimum PPP CHAP challenge length";
                                }

                                leaf end {
                                    type types-l2tp:base-chap-challenge-length;
                                    default "64";
                                    description "Maximum PPP CHAP challenge length";
                                }

                            } // container chap-challenge-length

                        } // container ppp

                        container mlppp {
                            description "Enter the mlppp context";

                            leaf admin-state {
                                type types-sros:admin-state;
                                default "disable";
                                description "Administrative state of MLPPP in this L2TP tunnel group";
                            }

                            leaf max-links {
                                type types-l2tp:base-mlppp-max-links;
                                default "1";
                                description "Maximum MLPPP links";
                            }

                            leaf interleave {
                                type boolean;
                                default "false";
                                description "Enable link fragmentation and interleaving";
                            }

                            leaf max-fragment-delay {
                                type types-l2tp:base-mlppp-max-frag-delay;
                                default "no-fragmentation";
                                description "Maximum fragment delay caused by transmission on a link";
                            }

                            leaf reassembly-timeout {
                                type types-l2tp:base-mlppp-reassembly-timeout;
                                default "1000";
                                description "Reassembly timeout";
                            }

                            leaf short-sequence-numbers {
                                type boolean;
                                default "false";
                                description "Request a peer to send short sequence numbers";
                            }

                            leaf-list apply-groups {
                                type leafref {
                                    path "../../../../../../../groups/group/name";
                                }
                                max-elements 8;
                                ordered-by user;
                                description "Apply a configuration group at this level";
                            }

                            container endpoint {
                                description "Enter the endpoint context";

                                choice endpoint {
                                    case ip {

                                        leaf ip {
                                            type types-ppp:mlppp-ip-endpoint;
                                            description "Endpoint ID as an IP address";
                                        }

                                    }
                                    case mac {

                                        leaf mac {
                                            type types-ppp:mlppp-mac-endpoint;
                                            description "Endpoint ID as a MAC address";
                                        }

                                    }
                                }
                            } // container endpoint

                        } // container mlppp

                    } // container lns

                    list tunnel {
                        key "tunnel-name";
                        max-elements 31;
                        description "Enter the tunnel list instance";

                        leaf tunnel-name {
                            type types-sros:named-item {
                                length "1..32";
                            }
                            description "Tunnel name";
                        }

                        leaf admin-state {
                            type types-sros:admin-state;
                            default "disable";
                            description "Administrative state of the L2TP tunnel";
                        }

                        leaf description {
                            type types-sros:description;
                            description "Text description";
                        }

                        leaf preference {
                            type uint32 {
                                range "0..16777215";
                            }
                            default "50";
                            description "Tunnel preference number with its group";
                        }

                        leaf auto-establish {
                            type boolean;
                            default "false";
                            description "Allow the tunnel to be automatically set up by the system";
                        }

                        leaf peer {
                            type types-sros:ipv4-unicast-address;
                            description "Peer address";
                        }

                        leaf local-address {
                            type types-sros:ipv4-unicast-address;
                            description "Local address";
                        }

                        leaf receive-window-size {
                            type types-l2tp:child-receive-window-size;
                            description "L2TP receive window size";
                        }

                        leaf hello-interval {
                            type types-l2tp:child-hello-interval;
                            description "Hello interval";
                        }

                        leaf idle-timeout {
                            type types-l2tp:child-idle-timeout;
                            description "Idle timeout";
                        }

                        leaf destruct-timeout {
                            type types-l2tp:child-destruct-timeout;
                            description "Destruction timeout";
                        }

                        leaf max-retries-estab {
                            type types-l2tp:child-max-retries;
                            description "Maximum retries for established tunnels";
                        }

                        leaf max-retries-not-estab {
                            type types-l2tp:child-max-retries;
                            description "Maximum retries for unestablished tunnels";
                        }

                        leaf radius-accounting-policy {
                            type leafref {
                                path "../../../../../../aaa/radius/l2tp-accounting-policy/name";
                            }
                            description "RADIUS accounting policy";
                        }

                        leaf remote-name {
                            type types-l2tp:host-name;
                            description "Remote host name for tunnel";
                        }

                        leaf local-name {
                            type types-l2tp:host-name;
                            description "The local host name.";
                        }

                        leaf password {
                            type types-sros:encrypted-leaf {
                                length "1..115";
                            }
                            description "The password.";
                        }

                        leaf challenge {
                            type types-sros:bool-with-inherit;
                            description "Enable/disable the use of challenge-response authentication.";
                        }

                        leaf avp-hiding {
                            type types-l2tp:child-avp-hiding;
                            description "The AVP hiding algorithm";
                        }

                        leaf session-limit {
                            type types-l2tp:child-tunnel-session-limit;
                            description "L2TP session limit for each tunnel of this router";
                        }

                        leaf-list apply-groups {
                            type leafref {
                                path "../../../../../../groups/group/name";
                            }
                            max-elements 8;
                            ordered-by user;
                            description "Apply a configuration group at this level";
                        }

                        container failover {
                            when "../../protocol = 'v2'";
                            description "Enter the failover context";

                            leaf recovery-method {
                                type types-l2tp:child-failover-recovery-method;
                                description "Recovery method of the sequence numbers after failover";
                            }

                            leaf recovery-time {
                                type types-l2tp:child-failover-recovery-time;
                                description "Time requested from the L2TP peer before assuming failover as failed";
                            }

                        } // container failover

                        container lac {
                            when "../../protocol = 'v2'";
                            description "Enter the lac context";

                            leaf df-bit {
                                type types-sros:bool-with-inherit;
                                description "DF (do not fragment) bit in data traffic transmitted as LAC";
                            }

                        } // container lac

                        container l2tpv3 {
                            when "not(../../protocol = 'v2')";
                            description "Enter the l2tpv3 context";

                            leaf public-tcp-mss-adjust {
                                type types-l2tp:child-v3-tcp-mss-adjust;
                                description "TCP maximum segment size (MSS) on public network";
                            }

                            leaf private-tcp-mss-adjust {
                                type types-l2tp:child-v3-tcp-mss-adjust;
                                description "TCP maximum segment size (MSS) on private network";
                            }

                        } // container l2tpv3

                        container lns {
                            when "../../protocol = 'v2'";
                            description "Enter the lns context";

                            leaf load-balance-method {
                                type types-l2tp:child-load-balance-method;
                                description "New sessions for L2TP ISA MDA";
                            }

                            leaf lns-group {
                                type leafref {
                                    path "../../../../../../../isa/lns-group/id";
                                }
                                description "ISA LNS group";
                            }

                            container ppp {
                                description "Enter the ppp context";

                                leaf authentication-policy {
                                    type types-sros:named-item;
                                    description "Authentication policy when a DHCP message is received";
                                }

                                leaf user-db {
                                    type types-sros:named-item;
                                    description "Local user database for PPP PAP and CHAP authentication";
                                }

                                leaf proxy-lcp {
                                    type types-sros:bool-with-inherit;
                                    description "Use the Proxy LCP AVPs that are received from the LAC";
                                }

                                leaf lcp-ignore-magic-numbers {
                                    type types-sros:bool-with-inherit;
                                    description "Magic-Number field in LCP Echo-Request and LCP Echo-Reply messages that are checked";
                                }

                                leaf lcp-force-ack-accm {
                                    type types-sros:bool-with-inherit;
                                    description "Forced acknowledgement of the LCP Asynchronous Control Character Map (ACCM) option";
                                }

                                leaf reject-disabled-ncp {
                                    type types-sros:bool-with-inherit;
                                    description "Enable/disable rejection of disabled Network Control Protocols (NCP)";
                                }

                                leaf mtu {
                                    type types-l2tp:child-ppp-mtu;
                                    description "Maximum PPP MTU size";
                                }

                                leaf proxy-authentication {
                                    type types-sros:bool-with-inherit;
                                    description "Authentication AVPs that are received from LAC";
                                }

                                leaf authentication {
                                    type types-l2tp:child-ppp-auth-protocol;
                                    description "PPP authentication protocol to negotiate";
                                }

                                leaf ipcp-subnet-negotiation {
                                    type types-sros:bool-with-inherit;
                                    description "Use of IPCP subnet negotiation for PPPoE hosts";
                                }

                                container default-group-interface {
                                    description "Enter the default-group-interface context";

                                    leaf interface {
                                        type types-sros:named-item;
                                        description "Group interface";
                                    }

                                    leaf service-name {
                                        type types-services:service-name;
                                        description "Service name";
                                    }

                                } // container default-group-interface

                                container keepalive {
                                    description "Enter the keepalive context";

                                    leaf interval {
                                        type types-l2tp:child-lcp-keepalive-interval;
                                        description "PPP keepalive interval";
                                    }

                                    leaf multiplier {
                                        type types-l2tp:child-lcp-keepalive-multiplier;
                                        description "PPP keepalive multiplier";
                                    }

                                } // container keepalive

                                container chap-challenge-length {
                                    description "Enter the chap-challenge-length context";

                                    leaf start {
                                        type types-l2tp:child-chap-challenge-length;
                                        description "Minimum PPP CHAP challenge length";
                                    }

                                    leaf end {
                                        type types-l2tp:child-chap-challenge-length;
                                        description "Minimum PPP CHAP challenge length";
                                    }

                                } // container chap-challenge-length

                            } // container ppp

                            container mlppp {
                                description "Enter the mlppp context";

                                leaf admin-state {
                                    type types-sros:admin-state-with-inherit;
                                    description "Administrative state of MLPPP in the L2TP tunnel";
                                }

                                leaf max-links {
                                    type types-l2tp:child-mlppp-max-links;
                                    description "Maximum MLPPP links";
                                }

                                leaf interleave {
                                    type types-sros:bool-with-inherit;
                                    description "Use of Link fragmentation and interleaving";
                                }

                                leaf max-fragment-delay {
                                    type types-l2tp:child-mlppp-max-frag-delay;
                                    description "Maximum fragment delay caused by transmission on a link";
                                }

                                leaf reassembly-timeout {
                                    type types-l2tp:child-mlppp-reassembly-timeout;
                                    description "Reassembly timeout";
                                }

                                leaf short-sequence-numbers {
                                    type types-sros:bool-with-inherit;
                                    description "Request a peer to send short sequence numbers";
                                }

                                leaf-list apply-groups {
                                    type leafref {
                                        path "../../../../../../../../groups/group/name";
                                    }
                                    max-elements 8;
                                    ordered-by user;
                                    description "Apply a configuration group at this level";
                                }

                                container endpoint {
                                    description "Enter the endpoint context";

                                    choice endpoint {
                                        case ip {

                                            leaf ip {
                                                type types-ppp:mlppp-ip-endpoint;
                                                description "Endpoint ID as an IP address";
                                            }

                                        }
                                        case mac {

                                            leaf mac {
                                                type types-ppp:mlppp-mac-endpoint;
                                                description "Endpoint ID as a MAC address";
                                            }

                                        }
                                    }
                                } // container endpoint

                            } // container mlppp

                        } // container lns

                    } // list tunnel

                } // list group

            } // container l2tp

            container igmp {
                presence "Enables IGMP functionality on this service.";
                description "Enter the igmp context";

                leaf group-if-query-source-address {
                    type types-sros:ipv4-unicast-address;
                    description "Default query-source address for all group interfaces";
                }

                leaf query-interval {
                    type uint32 {
                        range "2..1024";
                    }
                    units "seconds";
                    default "125";
                    description "Time between two consecutive host-query messages";
                }

                leaf query-last-member-interval {
                    type uint32 {
                        range "1..1023";
                    }
                    units "seconds";
                    default "1";
                    description "Time between group-specific query messages";
                }

                leaf query-response-interval {
                    type uint32 {
                        range "1..1023";
                    }
                    units "seconds";
                    default "10";
                    description "Time to wait for a response to the host-query messages";
                }

                leaf robust-count {
                    type uint32 {
                        range "2..10";
                    }
                    default "2";
                    description "Number of retries after message loss";
                }

                leaf admin-state {
                    type types-sros:admin-state;
                    default "enable";
                    description "Administrative state of IGMP";
                }

                leaf-list apply-groups {
                    type leafref {
                        path "../../../../groups/group/name";
                    }
                    max-elements 8;
                    ordered-by user;
                    description "Apply a configuration group at this level";
                }

                container ssm-translate {
                    description "Enter the ssm-translate context";

                    list group-range {
                        key "start end";
                        description "Enter the group-range list instance";

                        leaf start {
                            type types-sros:ipv4-multicast-address;
                            description "IP address that specifies the start of the group range";
                        }

                        leaf end {
                            type types-sros:ipv4-multicast-address;
                            description "IP address that specifies the end of the group range";
                        }

                        leaf-list apply-groups {
                            type leafref {
                                path "../../../../../../groups/group/name";
                            }
                            max-elements 8;
                            ordered-by user;
                            description "Apply a configuration group at this level";
                        }

                        list source {
                            key "source-address";
                            min-elements 1;
                            description "Add a list entry for source";

                            leaf source-address {
                                type types-sros:ipv4-unicast-address;
                                description "Source IP address of multicast channel sending data";
                            }

                        } // list source

                    } // list group-range

                } // container ssm-translate

                list interface {
                    key "ip-interface-name";
                    description "Enter the interface list instance";

                    leaf ip-interface-name {
                        type types-sros:interface-name;
                        description "Interface name.";
                    }

                    leaf router-alert-check {
                        type boolean;
                        default "true";
                        description "Enable router alert checking for IGMP or MLD messages";
                    }

                    leaf maximum-number-groups {
                        type uint32 {
                            range "1..16000";
                        }
                        description "Maximum number of groups for this interface";
                    }

                    leaf maximum-number-group-sources {
                        type uint32 {
                            range "1..32000";
                        }
                        description "Maximum number of group sources for this interface";
                    }

                    leaf maximum-number-sources {
                        type uint32 {
                            range "1..1000";
                        }
                        description "Maximum number of sources that are allowed per group";
                    }

                    leaf query-interval {
                        type uint32 {
                            range "2..1024";
                        }
                        description "Time between two consecutive host-query messages";
                    }

                    leaf query-response-interval {
                        type uint32 {
                            range "1..1023";
                        }
                        description "Time to wait for a response to the host-query messages";
                    }

                    leaf query-last-member-interval {
                        type uint32 {
                            range "1..1023";
                        }
                        description "Time between group-specific query messages";
                    }

                    leaf admin-state {
                        type types-sros:admin-state;
                        default "enable";
                        description "Administrative state of IGMP in this context";
                    }

                    leaf import-policy {
                        type leafref {
                            path "../../../../../policy-options/policy-statement/name";
                        }
                        description "Import policy that filters IGMP packets";
                    }

                    leaf subnet-check {
                        type boolean;
                        default "true";
                        description "Allow subnet checking";
                    }

                    leaf version {
                        type types-igmp:igmp-version;
                        default "3";
                        description "IGMP protocol version";
                    }

                    leaf redundant-mcast {
                        type boolean;
                        default "false";
                        description "Use interface as a redundant-pair member for multicast";
                    }

                    leaf-list apply-groups {
                        type leafref {
                            path "../../../../../groups/group/name";
                        }
                        max-elements 8;
                        ordered-by user;
                        description "Apply a configuration group at this level";
                    }

                    container mcac {
                        description "Enter the mcac context";

                        leaf interface-policy {
                            type leafref {
                                path "../../../../../../mcac/interface-policy/policy-name";
                            }
                            description "Name of multicast CAC interface policy";
                        }

                        leaf policy {
                            type leafref {
                                path "../../../../../../mcac/policy/policy-name";
                            }
                            description "Multicast CAC policy name";
                        }

                        container mc-constraints {
                            description "Enter the mc-constraints context";

                            leaf use-lag-port-weight {
                                type boolean;
                                default "false";
                                description "Use LAG port weight in calculating MCAC constraints";
                            }

                            list level {
                                key "level-id";
                                description "Enter the level list instance";

                                leaf level-id {
                                    type types-mcast-cac:constraints-level;
                                    description "Bandwidth level ID for a multicast CAC constraint";
                                }

                                leaf bandwidth {
                                    type types-mcast-cac:bandwidth {
                                        range "0..2147483647";
                                    }
                                    mandatory true;
                                    description "Bandwidth available for this level";
                                }

                                leaf-list apply-groups {
                                    type leafref {
                                        path "../../../../../../../../groups/group/name";
                                    }
                                    max-elements 8;
                                    ordered-by user;
                                    description "Apply a configuration group at this level";
                                }

                            } // list level

                            list number-down {
                                key "number-lag-port-down";
                                description "Enter the number-down list instance";

                                leaf number-lag-port-down {
                                    type uint32 {
                                        range "1..64";
                                    }
                                    description "Number of ports that are down in this LAG link";
                                }

                                leaf level {
                                    type types-mcast-cac:constraints-level;
                                    mandatory true;
                                    description "Level ID to associate with number of down LAG ports";
                                }

                                leaf-list apply-groups {
                                    type leafref {
                                        path "../../../../../../../../groups/group/name";
                                    }
                                    max-elements 8;
                                    ordered-by user;
                                    description "Apply a configuration group at this level";
                                }

                            } // list number-down

                        } // container mc-constraints

                        container bandwidth {
                            description "Enter the bandwidth context";

                            leaf total {
                                type types-mcast-cac:bandwidth-limit;
                                description "Maximum allowed bandwidth";
                            }

                            leaf mandatory {
                                type types-mcast-cac:bandwidth-limit;
                                description "Pre-reserved bandwidth for all mandatory channels";
                            }

                        } // container bandwidth

                    } // container mcac

                    container ssm-translate {
                        description "Enter the ssm-translate context";

                        list group-range {
                            key "start end";
                            description "Enter the group-range list instance";

                            leaf start {
                                type types-sros:ipv4-multicast-address;
                                description "IP address that specifies the start of the group range";
                            }

                            leaf end {
                                type types-sros:ipv4-multicast-address;
                                description "IP address that specifies the end of the group range";
                            }

                            leaf-list apply-groups {
                                type leafref {
                                    path "../../../../../../../groups/group/name";
                                }
                                max-elements 8;
                                ordered-by user;
                                description "Apply a configuration group at this level";
                            }

                            list source {
                                key "source-address";
                                min-elements 1;
                                description "Add a list entry for source";

                                leaf source-address {
                                    type types-sros:ipv4-unicast-address;
                                    description "Source IP address of multicast channel sending data";
                                }

                            } // list source

                        } // list group-range

                    } // container ssm-translate

                    container static {
                        description "Enter the static context";

                        list group {
                            key "group-address";
                            description "Enter the group list instance";

                            leaf group-address {
                                type types-sros:ipv4-multicast-address;
                                description "Group address of static IGMP multicast channel";
                            }

                            leaf-list apply-groups {
                                type leafref {
                                    path "../../../../../../../groups/group/name";
                                }
                                max-elements 8;
                                ordered-by user;
                                description "Apply a configuration group at this level";
                            }

                            choice source-or-starg {
                                mandatory true;
                                case source {

                                    list source {
                                        key "source-address";
                                        description "Add a list entry for source";

                                        leaf source-address {
                                            type types-sros:ipv4-unicast-address;
                                            description "Source IP address of multicast channel sending data";
                                        }

                                    } // list source

                                }
                                case starg {

                                    leaf starg {
                                        type empty;
                                        description "any source address (*,G)";
                                    }

                                }
                            }
                        } // list group

                        list group-range {
                            key "start end step";
                            description "Enter the group-range list instance";

                            leaf start {
                                type types-sros:ipv4-multicast-address;
                                description "IP address for the start of the static group range";
                            }

                            leaf end {
                                type types-sros:ipv4-multicast-address;
                                description "IP address for the end of the static group range";
                            }

                            leaf step {
                                type types-sros:ipv4-address;
                                description "Step interval in the group-range address";
                            }

                            leaf-list apply-groups {
                                type leafref {
                                    path "../../../../../../../groups/group/name";
                                }
                                max-elements 8;
                                ordered-by user;
                                description "Apply a configuration group at this level";
                            }

                            choice source-or-starg {
                                mandatory true;
                                case source {

                                    list source {
                                        key "source-address";
                                        description "Add a list entry for source";

                                        leaf source-address {
                                            type types-sros:ipv4-unicast-address;
                                            description "Source IP address of multicast channel sending data";
                                        }

                                    } // list source

                                }
                                case starg {

                                    leaf starg {
                                        type empty;
                                        description "any source address (*,G)";
                                    }

                                }
                            }
                        } // list group-range

                    } // container static

                } // list interface

                list group-interface {
                    key "group-interface-name";
                    description "Enter the group-interface list instance";

                    leaf group-interface-name {
                        type leafref {
                            path "../../../subscriber-interface/group-interface/group-interface-name";
                        }
                        description "Group interface name";
                    }

                    leaf router-alert-check {
                        type boolean;
                        default "true";
                        description "Enable router alert checking for IGMP or MLD messages";
                    }

                    leaf maximum-number-groups {
                        type uint32 {
                            range "1..16000";
                        }
                        description "Maximum number of groups for this interface";
                    }

                    leaf maximum-number-group-sources {
                        type uint32 {
                            range "1..32000";
                        }
                        description "Maximum number of group sources for this interface";
                    }

                    leaf maximum-number-sources {
                        type uint32 {
                            range "1..1000";
                        }
                        description "Maximum number of sources that are allowed per group";
                    }

                    leaf query-interval {
                        type uint32 {
                            range "2..1024";
                        }
                        description "Time between two consecutive host-query messages";
                    }

                    leaf query-response-interval {
                        type uint32 {
                            range "1..1023";
                        }
                        description "Time to wait for a response to the host-query messages";
                    }

                    leaf query-last-member-interval {
                        type uint32 {
                            range "1..1023";
                        }
                        description "Time between group-specific query messages";
                    }

                    leaf admin-state {
                        type types-sros:admin-state;
                        default "enable";
                        description "Administrative state of IGMP in this context";
                    }

                    leaf import-policy {
                        type leafref {
                            path "../../../../../policy-options/policy-statement/name";
                        }
                        description "Import policy that filters IGMP packets";
                    }

                    leaf subnet-check {
                        type boolean;
                        default "true";
                        description "Allow subnet checking";
                    }

                    leaf version {
                        type types-igmp:igmp-version;
                        default "3";
                        description "IGMP protocol version";
                    }

                    leaf sub-hosts-only {
                        type boolean;
                        default "true";
                        description "Allow IGMP traffic from known hosts only";
                    }

                    leaf query-source-address {
                        type types-sros:ipv4-unicast-address;
                        description "Source address for IGMP queries";
                    }

                    leaf-list apply-groups {
                        type leafref {
                            path "../../../../../groups/group/name";
                        }
                        max-elements 8;
                        ordered-by user;
                        description "Apply a configuration group at this level";
                    }

                    container mcac {
                        description "Enter the mcac context";

                        leaf interface-policy {
                            type leafref {
                                path "../../../../../../mcac/interface-policy/policy-name";
                            }
                            description "Name of multicast CAC interface policy";
                        }

                        leaf policy {
                            type leafref {
                                path "../../../../../../mcac/policy/policy-name";
                            }
                            description "Multicast CAC policy name";
                        }

                        container bandwidth {
                            description "Enter the bandwidth context";

                            leaf total {
                                type types-mcast-cac:bandwidth-limit;
                                description "Maximum allowed bandwidth";
                            }

                            leaf mandatory {
                                type types-mcast-cac:bandwidth-limit;
                                description "Pre-reserved bandwidth for all mandatory channels";
                            }

                        } // container bandwidth

                    } // container mcac

                } // list group-interface

                list forwarding-group-interface {
                    key "forwarding-service group-interface-name";
                    description "Enter the forwarding-group-interface list instance";

                    leaf forwarding-service {
                        type types-services:service-name;
                        description "Forwarding service for a subscriber interface in a retailer context";
                    }

                    leaf group-interface-name {
                        type leafref {
                            path "../../../../vprn[service-name=current()/../forwarding-service]/subscriber-interface/group-interface/group-interface-name";
                        }
                        description "Group interface name";
                    }

                    leaf router-alert-check {
                        type boolean;
                        default "true";
                        description "Enable router alert checking for IGMP or MLD messages";
                    }

                    leaf maximum-number-groups {
                        type uint32 {
                            range "1..16000";
                        }
                        description "Maximum number of groups for this interface";
                    }

                    leaf maximum-number-group-sources {
                        type uint32 {
                            range "1..32000";
                        }
                        description "Maximum number of group sources for this interface";
                    }

                    leaf maximum-number-sources {
                        type uint32 {
                            range "1..1000";
                        }
                        description "Maximum number of sources that are allowed per group";
                    }

                    leaf query-interval {
                        type uint32 {
                            range "2..1024";
                        }
                        description "Time between two consecutive host-query messages";
                    }

                    leaf query-response-interval {
                        type uint32 {
                            range "1..1023";
                        }
                        description "Time to wait for a response to the host-query messages";
                    }

                    leaf query-last-member-interval {
                        type uint32 {
                            range "1..1023";
                        }
                        description "Time between group-specific query messages";
                    }

                    leaf admin-state {
                        type types-sros:admin-state;
                        default "enable";
                        description "Administrative state of IGMP in this context";
                    }

                    leaf import-policy {
                        type leafref {
                            path "../../../../../policy-options/policy-statement/name";
                        }
                        description "Import policy that filters IGMP packets";
                    }

                    leaf subnet-check {
                        type boolean;
                        default "true";
                        description "Allow subnet checking";
                    }

                    leaf version {
                        type types-igmp:igmp-version;
                        default "3";
                        description "IGMP protocol version";
                    }

                    leaf sub-hosts-only {
                        type boolean;
                        default "true";
                        description "Allow IGMP traffic from known hosts only";
                    }

                    leaf query-source-address {
                        type types-sros:ipv4-unicast-address;
                        description "Source address for IGMP queries";
                    }

                    leaf-list apply-groups {
                        type leafref {
                            path "../../../../../groups/group/name";
                        }
                        max-elements 8;
                        ordered-by user;
                        description "Apply a configuration group at this level";
                    }

                    container mcac {
                        description "Enter the mcac context";

                        leaf interface-policy {
                            type leafref {
                                path "../../../../../../mcac/interface-policy/policy-name";
                            }
                            description "Name of multicast CAC interface policy";
                        }

                        leaf policy {
                            type leafref {
                                path "../../../../../../mcac/policy/policy-name";
                            }
                            description "Multicast CAC policy name";
                        }

                        container bandwidth {
                            description "Enter the bandwidth context";

                            leaf total {
                                type types-mcast-cac:bandwidth-limit;
                                description "Maximum allowed bandwidth";
                            }

                            leaf mandatory {
                                type types-mcast-cac:bandwidth-limit;
                                description "Pre-reserved bandwidth for all mandatory channels";
                            }

                        } // container bandwidth

                    } // container mcac

                } // list forwarding-group-interface

            } // container igmp

            container ipsec {
                description "Enter the ipsec context";

                leaf allow-reverse-route-override-type {
                    type enumeration {
                        enum "same-idi"                     { value 1; }
                        enum "any-idi"                      { value 2; }
                    }
                    description "Override the reverse route.";
                }

                leaf allow-reverse-route-override {
                    status obsolete;
                    type boolean;
                    default "false";
                    description "Override the reverse route.";
                }

                list security-policy {
                    key "id";
                    description "Enter the security-policy list instance";

                    leaf id {
                        type uint32 {
                            range "1..32768";
                        }
                        description "IPsec security policy ID.";
                    }

                    leaf-list apply-groups {
                        type leafref {
                            path "../../../../../groups/group/name";
                        }
                        max-elements 8;
                        ordered-by user;
                        description "Apply a configuration group at this level";
                    }

                    list entry {
                        key "entry-id";
                        description "Enter the entry list instance";

                        leaf entry-id {
                            type uint32 {
                                range "1..16";
                            }
                            description "IPsec security policy entry ID.";
                        }

                        leaf-list apply-groups {
                            type leafref {
                                path "../../../../../../groups/group/name";
                            }
                            max-elements 8;
                            ordered-by user;
                            description "Apply a configuration group at this level";
                        }

                        container local-ip {
                            description "Enter the local-ip context";

                            choice any-or-ip {
                                default "any";
                                case any {

                                    leaf any {
                                        type boolean;
                                        default "false";
                                        description "Any IP address.";
                                    }

                                }
                                case ip {

                                    leaf address {
                                        type types-sros:ipv4-prefix;
                                        description "The IP address.";
                                    }

                                }
                            }
                        } // container local-ip

                        container local-ipv6 {
                            description "Enter the local-ipv6 context";

                            choice any-or-ip {
                                default "any";
                                case any {

                                    leaf any {
                                        type boolean;
                                        default "false";
                                        description "Any IP address.";
                                    }

                                }
                                case ip {

                                    leaf address {
                                        type types-sros:ipv6-prefix;
                                        description "The IP address.";
                                    }

                                }
                            }
                        } // container local-ipv6

                        container remote-ip {
                            description "Enter the remote-ip context";

                            choice any-or-ip {
                                default "any";
                                case any {

                                    leaf any {
                                        type boolean;
                                        default "false";
                                        description "Any IP address.";
                                    }

                                }
                                case ip {

                                    leaf address {
                                        type types-sros:ipv4-prefix;
                                        description "The IP address.";
                                    }

                                }
                            }
                        } // container remote-ip

                        container remote-ipv6 {
                            description "Enter the remote-ipv6 context";

                            choice any-or-ip {
                                default "any";
                                case any {

                                    leaf any {
                                        type boolean;
                                        default "false";
                                        description "Any IP address.";
                                    }

                                }
                                case ip {

                                    leaf address {
                                        type types-sros:ipv6-prefix;
                                        description "The IP address.";
                                    }

                                }
                            }
                        } // container remote-ipv6

                    } // list entry

                } // list security-policy

            } // container ipsec

            container mld {
                presence "Enables MLD functionality on this service.";
                description "Enter the mld context";

                leaf group-if-query-source-address {
                    type types-sros:ipv6-unicast-or-linklocal-address;
                    description "Source address in queries for group interfaces when not configured at group interface level";
                }

                leaf query-interval {
                    type uint32 {
                        range "2..1024";
                    }
                    units "seconds";
                    default "125";
                    description "Time between two consecutive host-query messages";
                }

                leaf query-last-member-interval {
                    type uint32 {
                        range "1..1023";
                    }
                    units "seconds";
                    default "1";
                    description "Time between group-specific query messages";
                }

                leaf query-response-interval {
                    type uint32 {
                        range "1..1023";
                    }
                    units "seconds";
                    default "10";
                    description "Time to wait for a response to the host-query messages";
                }

                leaf robust-count {
                    type uint32 {
                        range "2..10";
                    }
                    default "2";
                    description "Robust count to tune for the expected packet loss on a subnet";
                }

                leaf admin-state {
                    type types-sros:admin-state;
                    default "enable";
                    description "Administrative state of MLD operation";
                }

                leaf-list apply-groups {
                    type leafref {
                        path "../../../../groups/group/name";
                    }
                    max-elements 8;
                    ordered-by user;
                    description "Apply a configuration group at this level";
                }

                container ssm-translate {
                    description "Enter the ssm-translate context";

                    list group-range {
                        key "start end";
                        description "Enter the group-range list instance";

                        leaf start {
                            type types-sros:ipv6-multicast-address;
                            description "Start of group range";
                        }

                        leaf end {
                            type types-sros:ipv6-multicast-address;
                            description "End of group range";
                        }

                        leaf-list apply-groups {
                            type leafref {
                                path "../../../../../../groups/group/name";
                            }
                            max-elements 8;
                            ordered-by user;
                            description "Apply a configuration group at this level";
                        }

                        list source {
                            key "source-address";
                            min-elements 1;
                            description "Add a list entry for source";

                            leaf source-address {
                                type types-sros:ipv6-unicast-address;
                                description "Source address of multicast channel.";
                            }

                        } // list source

                    } // list group-range

                } // container ssm-translate

                list interface {
                    key "ip-interface-name";
                    description "Enter the interface list instance";

                    leaf ip-interface-name {
                        type types-sros:interface-name;
                        description "Interface name.";
                    }

                    leaf router-alert-check {
                        type boolean;
                        default "true";
                        description "Enable router alert checking for IGMP or MLD messages";
                    }

                    leaf maximum-number-groups {
                        type uint32 {
                            range "1..16000";
                        }
                        description "Maximum number of groups for this interface";
                    }

                    leaf maximum-number-group-sources {
                        type uint32 {
                            range "1..32000";
                        }
                        description "Maximum number of group sources for this interface";
                    }

                    leaf maximum-number-sources {
                        type uint32 {
                            range "1..1000";
                        }
                        description "Maximum number of sources that are allowed per group";
                    }

                    leaf query-interval {
                        type uint32 {
                            range "2..1024";
                        }
                        description "Time between two consecutive host-query messages";
                    }

                    leaf query-response-interval {
                        type uint32 {
                            range "1..1023";
                        }
                        description "Time to wait for a response to the host-query messages";
                    }

                    leaf query-last-member-interval {
                        type uint32 {
                            range "1..1023";
                        }
                        description "Time between group-specific query messages";
                    }

                    leaf import-policy {
                        type leafref {
                            path "../../../../../policy-options/policy-statement/name";
                        }
                        description "Import policy to filter MLD packets";
                    }

                    leaf admin-state {
                        type types-sros:admin-state;
                        default "enable";
                        description "Administrative state of this interface";
                    }

                    leaf version {
                        type types-igmp:mld-version;
                        default "2";
                        description "MLD protocol version";
                    }

                    leaf-list apply-groups {
                        type leafref {
                            path "../../../../../groups/group/name";
                        }
                        max-elements 8;
                        ordered-by user;
                        description "Apply a configuration group at this level";
                    }

                    container mcac {
                        description "Enter the mcac context";

                        leaf interface-policy {
                            type leafref {
                                path "../../../../../../mcac/interface-policy/policy-name";
                            }
                            description "Name of multicast CAC interface policy";
                        }

                        leaf policy {
                            type leafref {
                                path "../../../../../../mcac/policy/policy-name";
                            }
                            description "Multicast CAC policy name";
                        }

                        container mc-constraints {
                            description "Enter the mc-constraints context";

                            leaf use-lag-port-weight {
                                type boolean;
                                default "false";
                                description "Use LAG port weight in calculating MCAC constraints";
                            }

                            list level {
                                key "level-id";
                                description "Enter the level list instance";

                                leaf level-id {
                                    type types-mcast-cac:constraints-level;
                                    description "Bandwidth level ID for a multicast CAC constraint";
                                }

                                leaf bandwidth {
                                    type types-mcast-cac:bandwidth {
                                        range "0..2147483647";
                                    }
                                    mandatory true;
                                    description "Bandwidth available for this level";
                                }

                                leaf-list apply-groups {
                                    type leafref {
                                        path "../../../../../../../../groups/group/name";
                                    }
                                    max-elements 8;
                                    ordered-by user;
                                    description "Apply a configuration group at this level";
                                }

                            } // list level

                            list number-down {
                                key "number-lag-port-down";
                                description "Enter the number-down list instance";

                                leaf number-lag-port-down {
                                    type uint32 {
                                        range "1..64";
                                    }
                                    description "Number of ports that are down in this LAG link";
                                }

                                leaf level {
                                    type types-mcast-cac:constraints-level;
                                    mandatory true;
                                    description "Level ID to associate with number of down LAG ports";
                                }

                                leaf-list apply-groups {
                                    type leafref {
                                        path "../../../../../../../../groups/group/name";
                                    }
                                    max-elements 8;
                                    ordered-by user;
                                    description "Apply a configuration group at this level";
                                }

                            } // list number-down

                        } // container mc-constraints

                        container bandwidth {
                            description "Enter the bandwidth context";

                            leaf total {
                                type types-mcast-cac:bandwidth-limit;
                                description "Maximum allowed bandwidth";
                            }

                            leaf mandatory {
                                type types-mcast-cac:bandwidth-limit;
                                description "Pre-reserved bandwidth for all mandatory channels";
                            }

                        } // container bandwidth

                    } // container mcac

                    container ssm-translate {
                        description "Enter the ssm-translate context";

                        list group-range {
                            key "start end";
                            description "Enter the group-range list instance";

                            leaf start {
                                type types-sros:ipv6-multicast-address;
                                description "Start of group range";
                            }

                            leaf end {
                                type types-sros:ipv6-multicast-address;
                                description "End of group range";
                            }

                            leaf-list apply-groups {
                                type leafref {
                                    path "../../../../../../../groups/group/name";
                                }
                                max-elements 8;
                                ordered-by user;
                                description "Apply a configuration group at this level";
                            }

                            list source {
                                key "source-address";
                                min-elements 1;
                                description "Add a list entry for source";

                                leaf source-address {
                                    type types-sros:ipv6-unicast-address;
                                    description "Source address of multicast channel.";
                                }

                            } // list source

                        } // list group-range

                    } // container ssm-translate

                    container static {
                        description "Enter the static context";

                        list group {
                            key "group-address";
                            description "Enter the group list instance";

                            leaf group-address {
                                type types-sros:ipv6-multicast-address;
                                description "Group address of multicast channel";
                            }

                            leaf-list apply-groups {
                                type leafref {
                                    path "../../../../../../../groups/group/name";
                                }
                                max-elements 8;
                                ordered-by user;
                                description "Apply a configuration group at this level";
                            }

                            choice source-or-starg {
                                mandatory true;
                                case source {

                                    list source {
                                        key "source-address";
                                        description "Add a list entry for source";

                                        leaf source-address {
                                            type types-sros:ipv6-unicast-address;
                                            description "Source address of multicast channel.";
                                        }

                                    } // list source

                                }
                                case starg {

                                    leaf starg {
                                        type empty;
                                        description "any source address (*,G)";
                                    }

                                }
                            }
                        } // list group

                        list group-range {
                            key "start end step";
                            description "Enter the group-range list instance";

                            leaf start {
                                type types-sros:ipv6-multicast-address;
                                description "Start of group range of multicast channel";
                            }

                            leaf end {
                                type types-sros:ipv6-multicast-address;
                                description "End of group range for multicast channel";
                            }

                            leaf step {
                                type types-sros:ipv6-address;
                                description "Step interval for the group-range addresses";
                            }

                            leaf-list apply-groups {
                                type leafref {
                                    path "../../../../../../../groups/group/name";
                                }
                                max-elements 8;
                                ordered-by user;
                                description "Apply a configuration group at this level";
                            }

                            choice source-or-starg {
                                mandatory true;
                                case source {

                                    list source {
                                        key "source-address";
                                        description "Add a list entry for source";

                                        leaf source-address {
                                            type types-sros:ipv6-unicast-address;
                                            description "Source address of multicast channel.";
                                        }

                                    } // list source

                                }
                                case starg {

                                    leaf starg {
                                        type empty;
                                        description "any source address (*,G)";
                                    }

                                }
                            }
                        } // list group-range

                    } // container static

                } // list interface

                list group-interface {
                    key "group-interface-name";
                    description "Enter the group-interface list instance";

                    leaf group-interface-name {
                        type leafref {
                            path "../../../subscriber-interface/group-interface/group-interface-name";
                        }
                        description "Group interface name";
                    }

                    leaf router-alert-check {
                        type boolean;
                        default "true";
                        description "Enable router alert checking for IGMP or MLD messages";
                    }

                    leaf maximum-number-groups {
                        type uint32 {
                            range "1..16000";
                        }
                        description "Maximum number of groups for this interface";
                    }

                    leaf maximum-number-group-sources {
                        type uint32 {
                            range "1..32000";
                        }
                        description "Maximum number of group sources for this interface";
                    }

                    leaf maximum-number-sources {
                        type uint32 {
                            range "1..1000";
                        }
                        description "Maximum number of sources that are allowed per group";
                    }

                    leaf query-interval {
                        type uint32 {
                            range "2..1024";
                        }
                        description "Time between two consecutive host-query messages";
                    }

                    leaf query-response-interval {
                        type uint32 {
                            range "1..1023";
                        }
                        description "Time to wait for a response to the host-query messages";
                    }

                    leaf query-last-member-interval {
                        type uint32 {
                            range "1..1023";
                        }
                        description "Time between group-specific query messages";
                    }

                    leaf import-policy {
                        type leafref {
                            path "../../../../../policy-options/policy-statement/name";
                        }
                        description "Import policy to filter MLD packets";
                    }

                    leaf admin-state {
                        type types-sros:admin-state;
                        default "enable";
                        description "Administrative state of this interface";
                    }

                    leaf version {
                        type types-igmp:mld-version;
                        default "2";
                        description "MLD protocol version";
                    }

                    leaf subnet-check {
                        type boolean;
                        default "true";
                        description "Enable subnet checking";
                    }

                    leaf sub-hosts-only {
                        type boolean;
                        default "true";
                        description "Allow MLD traffic from known hosts only";
                    }

                    leaf query-source-address {
                        type types-sros:ipv6-unicast-or-linklocal-address;
                        description "Source address for MLD queries";
                    }

                    leaf-list apply-groups {
                        type leafref {
                            path "../../../../../groups/group/name";
                        }
                        max-elements 8;
                        ordered-by user;
                        description "Apply a configuration group at this level";
                    }

                    container mcac {
                        description "Enter the mcac context";

                        leaf interface-policy {
                            type leafref {
                                path "../../../../../../mcac/interface-policy/policy-name";
                            }
                            description "Name of multicast CAC interface policy";
                        }

                        leaf policy {
                            type leafref {
                                path "../../../../../../mcac/policy/policy-name";
                            }
                            description "Multicast CAC policy name";
                        }

                        container bandwidth {
                            description "Enter the bandwidth context";

                            leaf total {
                                type types-mcast-cac:bandwidth-limit;
                                description "Maximum allowed bandwidth";
                            }

                            leaf mandatory {
                                type types-mcast-cac:bandwidth-limit;
                                description "Pre-reserved bandwidth for all mandatory channels";
                            }

                        } // container bandwidth

                    } // container mcac

                } // list group-interface

                list forwarding-group-interface {
                    key "forwarding-service group-interface-name";
                    description "Enter the forwarding-group-interface list instance";

                    leaf forwarding-service {
                        type types-services:service-name;
                        description "Forwarding service for a subscriber interface in a retailer context";
                    }

                    leaf group-interface-name {
                        type leafref {
                            path "../../../../vprn[service-name=current()/../forwarding-service]/subscriber-interface/group-interface/group-interface-name";
                        }
                        description "Group interface name";
                    }

                    leaf router-alert-check {
                        type boolean;
                        default "true";
                        description "Enable router alert checking for IGMP or MLD messages";
                    }

                    leaf maximum-number-groups {
                        type uint32 {
                            range "1..16000";
                        }
                        description "Maximum number of groups for this interface";
                    }

                    leaf maximum-number-group-sources {
                        type uint32 {
                            range "1..32000";
                        }
                        description "Maximum number of group sources for this interface";
                    }

                    leaf maximum-number-sources {
                        type uint32 {
                            range "1..1000";
                        }
                        description "Maximum number of sources that are allowed per group";
                    }

                    leaf query-interval {
                        type uint32 {
                            range "2..1024";
                        }
                        description "Time between two consecutive host-query messages";
                    }

                    leaf query-response-interval {
                        type uint32 {
                            range "1..1023";
                        }
                        description "Time to wait for a response to the host-query messages";
                    }

                    leaf query-last-member-interval {
                        type uint32 {
                            range "1..1023";
                        }
                        description "Time between group-specific query messages";
                    }

                    leaf import-policy {
                        type leafref {
                            path "../../../../../policy-options/policy-statement/name";
                        }
                        description "Import policy to filter MLD packets";
                    }

                    leaf admin-state {
                        type types-sros:admin-state;
                        default "enable";
                        description "Administrative state of this interface";
                    }

                    leaf version {
                        type types-igmp:mld-version;
                        default "2";
                        description "MLD protocol version";
                    }

                    leaf subnet-check {
                        type boolean;
                        default "true";
                        description "Enable subnet checking";
                    }

                    leaf sub-hosts-only {
                        type boolean;
                        default "true";
                        description "Allow MLD traffic from known hosts only";
                    }

                    leaf query-source-address {
                        type types-sros:ipv6-unicast-or-linklocal-address;
                        description "Source address for MLD queries";
                    }

                    leaf-list apply-groups {
                        type leafref {
                            path "../../../../../groups/group/name";
                        }
                        max-elements 8;
                        ordered-by user;
                        description "Apply a configuration group at this level";
                    }

                    container mcac {
                        description "Enter the mcac context";

                        leaf interface-policy {
                            type leafref {
                                path "../../../../../../mcac/interface-policy/policy-name";
                            }
                            description "Name of multicast CAC interface policy";
                        }

                        leaf policy {
                            type leafref {
                                path "../../../../../../mcac/policy/policy-name";
                            }
                            description "Multicast CAC policy name";
                        }

                        container bandwidth {
                            description "Enter the bandwidth context";

                            leaf total {
                                type types-mcast-cac:bandwidth-limit;
                                description "Maximum allowed bandwidth";
                            }

                            leaf mandatory {
                                type types-mcast-cac:bandwidth-limit;
                                description "Pre-reserved bandwidth for all mandatory channels";
                            }

                        } // container bandwidth

                    } // container mcac

                } // list forwarding-group-interface

            } // container mld

            container pim {
                presence "Enables PIM functionality.";
                description "Enter the pim context";

                leaf admin-state {
                    type types-sros:admin-state;
                    default "enable";
                    description "Administrative state of PIM";
                }

                leaf apply-to {
                    type enumeration {
                        enum "all"                          { value 3; }
                        enum "none"                         { value 4; }
                    }
                    default "none";
                    description "IES and non-IES interfaces to create in PIM";
                }

                leaf mc-ecmp-balance {
                    type boolean;
                    default "true";
                    description "Enable/disable multicast balancing of traffic over ECMP links.";
                }

                leaf mc-ecmp-balance-hold {
                    type uint32 {
                        range "2..600";
                    }
                    units "minutes";
                    description "Hold time for multicast balancing over ECMP links";
                }

                leaf non-dr-attract-traffic {
                    type boolean;
                    default "false";
                    description "Attract traffic when the router is not the designated one";
                }

                leaf bgp-nh-override {
                    type boolean;
                    default "false";
                    description "Disable VRF import EC support for next-hop resolution";
                }

                leaf-list apply-groups {
                    type leafref {
                        path "../../../../groups/group/name";
                    }
                    max-elements 8;
                    ordered-by user;
                    description "Apply a configuration group at this level";
                }

                container ipv4 {
                    description "Enter the ipv4 context";

                    leaf ssm-assert-compatible-mode {
                        type boolean;
                        default "false";
                        description "Enable SSM assert compatible mode";
                    }

                    leaf admin-state {
                        type types-sros:admin-state;
                        default "enable";
                        description "Administrative state of PIM operation for IPv4";
                    }

                    leaf rpf-table {
                        type enumeration {
                            enum "rtable-m"                     { value 0; }
                            enum "rtable-u"                     { value 1; }
                            enum "both"                         { value 2; }
                        }
                        default "rtable-u";
                        description "Route table(s) for RPF lookup";
                    }

                    leaf ssm-default-range {
                        type boolean;
                        default "true";
                        description "SSM default range";
                    }

                    container grt-extranet {
                        description "Enter the grt-extranet context";

                        choice prefix {
                            case any {

                                leaf any {
                                    type empty;
                                    description "GRT or VRF extranet for this instance";
                                }

                            }
                            case group-prefix {

                                list group-prefix {
                                    key "ip-prefix";
                                    description "Enter the group-prefix list instance";

                                    leaf ip-prefix {
                                        type types-sros:ip-multicast-prefix;
                                        description "IP address and mask length";
                                    }

                                    leaf starg {
                                        type boolean;
                                        default "false";
                                        description "Add a static (*,G) entry";
                                    }

                                    leaf-list apply-groups {
                                        type leafref {
                                            path "../../../../../../../groups/group/name";
                                        }
                                        max-elements 8;
                                        ordered-by user;
                                        description "Apply a configuration group at this level";
                                    }

                                } // list group-prefix

                            }
                        }
                    } // container grt-extranet

                } // container ipv4

                container ipv6 {
                    description "Enter the ipv6 context";

                    leaf admin-state {
                        type types-sros:admin-state;
                        default "disable";
                        description "Administrative state of PIM operation for IPv6";
                    }

                    leaf rpf-table {
                        type enumeration {
                            enum "rtable-m"                     { value 0; }
                            enum "rtable-u"                     { value 1; }
                            enum "both"                         { value 2; }
                        }
                        default "rtable-u";
                        description "Route table(s) for RPF lookup";
                    }

                    leaf ssm-default-range {
                        type boolean;
                        default "true";
                        description "SSM default range";
                    }

                } // container ipv6

                container mc-ecmp-hashing {
                    presence "Hash based multicast balancing of traffic over ECMP links.";
                    description "Enter the mc-ecmp-hashing context";

                    leaf rebalance {
                        type boolean;
                        default "false";
                        description "Rebalance flows to newly added links immediately instead of waiting until they are pruned";
                    }

                } // container mc-ecmp-hashing

                container import {
                    description "Enter the import context";

                    leaf-list join-policy {
                        type leafref {
                            path "../../../../../policy-options/policy-statement/name";
                        }
                        max-elements 5;
                        ordered-by user;
                        description "Name of the policy is limited to 32 characters.";
                    }

                    leaf-list register-policy {
                        type leafref {
                            path "../../../../../policy-options/policy-statement/name";
                        }
                        max-elements 5;
                        ordered-by user;
                        description "Name of the policy is limited to 32 characters.";
                    }

                } // container import

                list interface {
                    key "interface-name";
                    description "Enter the interface list instance";

                    leaf interface-name {
                        type types-sros:interface-name;
                        description "Service VPRN interface name.";
                    }

                    leaf admin-state {
                        type types-sros:admin-state;
                        default "enable";
                        description "Administrative state of this interface";
                    }

                    leaf assert-period {
                        type int32 {
                            range "1..300";
                        }
                        default "60";
                        description "Time for periodic refreshes of PIM Assert messages on an interface";
                    }

                    leaf hello-interval {
                        type int32 {
                            range "0..255";
                        }
                        default "30";
                        description "Frequency at which PIM Hello messages are sent over this interface";
                    }

                    leaf hello-multiplier {
                        type uint32 {
                            range "20..100";
                        }
                        default "35";
                        description "Multiplier of Hello in multiples of 0.1";
                    }

                    leaf instant-prune-echo {
                        type boolean;
                        default "false";
                        description "Allow PIM to send an instant prune echo when router starts the prune pending timer for PIM interface";
                    }

                    leaf max-groups {
                        type uint32 {
                            range "0|1..16000";
                        }
                        default "0";
                        description "Max number of groups for which PIM can have local receiver information based on received PIM reports";
                    }

                    leaf priority {
                        type uint32 {
                            range "1..max";
                        }
                        default "1";
                        description "DR election priority for this interface";
                    }

                    leaf three-way-hello {
                        type boolean;
                        default "false";
                        description "Allow three-way hello compatibility mode";
                    }

                    leaf tracking-support {
                        type boolean;
                        default "false";
                        description "Allow upstream routers to explicitly track join membership";
                    }

                    leaf bsm-check-rtr-alert {
                        type boolean;
                        default "false";
                        description "Check router alert option in bootstrap messages received";
                    }

                    leaf improved-assert {
                        type boolean;
                        default "true";
                        description "Allow improved assert processing on interface";
                    }

                    leaf multicast-senders {
                        type enumeration {
                            enum "auto"                         { value 0; }
                            enum "always"                       { value 1; }
                            enum "never"                        { value 2; }
                        }
                        default "auto";
                        description "Subnet matching for the incoming data packets";
                    }

                    leaf-list apply-groups {
                        type leafref {
                            path "../../../../../groups/group/name";
                        }
                        max-elements 8;
                        ordered-by user;
                        description "Apply a configuration group at this level";
                    }

                    container p2mp-ldp-tree-join {
                        description "Enter the p2mp-ldp-tree-join context";

                        leaf ipv4 {
                            type boolean;
                            default "false";
                            description "Allow dynamic mLDP in-band signaling for IPv4 PIM joins";
                        }

                        leaf ipv6 {
                            type boolean;
                            default "false";
                            description "Allow dynamic mLDP in-band signaling for IPv6 PIM joins";
                        }

                    } // container p2mp-ldp-tree-join

                    container bfd-liveness {
                        description "Enter the bfd-liveness context";

                        leaf ipv4 {
                            type boolean;
                            default "false";
                            description "Use Bidirectional Forwarding Detection for IPv4 on PIM interface";
                        }

                        leaf ipv6 {
                            type boolean;
                            default "false";
                            description "Use Bidirectional Forwarding Detection for IPv6 on PIM interface";
                        }

                    } // container bfd-liveness

                    container ipv4 {
                        description "Enter the ipv4 context";

                        leaf multicast {
                            type boolean;
                            default "true";
                            description "Enable PIM interface operation";
                        }

                        leaf-list apply-groups {
                            type leafref {
                                path "../../../../../../groups/group/name";
                            }
                            max-elements 8;
                            ordered-by user;
                            description "Apply a configuration group at this level";
                        }

                        container monitor-oper-group {
                            description "Enter the monitor-oper-group context";

                            leaf name {
                                type leafref {
                                    path "../../../../../../oper-group/name";
                                }
                                description "Operational group to monitor for address family";
                            }

                            leaf operation {
                                type enumeration {
                                    enum "add"                          { value 1; }
                                    enum "subtract"                     { value 2; }
                                    enum "set"                          { value 3; }
                                }
                                description "Perform given operation when oper-group is active.";
                            }

                            leaf priority-delta {
                                type uint32 {
                                    range "1..4294967295";
                                }
                                description "Delta priority with operation when operational group is active";
                            }

                        } // container monitor-oper-group

                    } // container ipv4

                    container ipv6 {
                        description "Enter the ipv6 context";

                        leaf multicast {
                            type boolean;
                            default "true";
                            description "Enable PIM interface operation";
                        }

                        leaf-list apply-groups {
                            type leafref {
                                path "../../../../../../groups/group/name";
                            }
                            max-elements 8;
                            ordered-by user;
                            description "Apply a configuration group at this level";
                        }

                        container monitor-oper-group {
                            description "Enter the monitor-oper-group context";

                            leaf name {
                                type leafref {
                                    path "../../../../../../oper-group/name";
                                }
                                description "Operational group to monitor for address family";
                            }

                            leaf operation {
                                type enumeration {
                                    enum "add"                          { value 1; }
                                    enum "subtract"                     { value 2; }
                                    enum "set"                          { value 3; }
                                }
                                description "Perform given operation when oper-group is active.";
                            }

                            leaf priority-delta {
                                type uint32 {
                                    range "1..4294967295";
                                }
                                description "Delta priority with operation when operational group is active";
                            }

                        } // container monitor-oper-group

                    } // container ipv6

                    container sticky-dr {
                        presence "Enable/disable sticky-DR and configure DR priority for sticky-DR.";
                        description "Enter the sticky-dr context";

                        leaf priority {
                            type uint32 {
                                range "1..max";
                            }
                            default "1024";
                            description "DR election priority for this interface";
                        }

                    } // container sticky-dr

                    container mcac {
                        description "Enter the mcac context";

                        leaf interface-policy {
                            type leafref {
                                path "../../../../../../mcac/interface-policy/policy-name";
                            }
                            description "Name of multicast CAC interface policy";
                        }

                        leaf policy {
                            type leafref {
                                path "../../../../../../mcac/policy/policy-name";
                            }
                            description "Multicast CAC policy name";
                        }

                        container bandwidth {
                            description "Enter the bandwidth context";

                            leaf total {
                                type types-mcast-cac:bandwidth-limit;
                                description "Maximum allowed bandwidth";
                            }

                            leaf mandatory {
                                type types-mcast-cac:bandwidth-limit;
                                description "Pre-reserved bandwidth for all mandatory channels";
                            }

                        } // container bandwidth

                        container mc-constraints {
                            description "Enter the mc-constraints context";

                            leaf use-lag-port-weight {
                                type boolean;
                                default "false";
                                description "Use LAG port weight in calculating MCAC constraints";
                            }

                            leaf admin-state {
                                type types-sros:admin-state;
                                default "enable";
                                description "Administrative state of constraint for multicast CAC policy";
                            }

                            list level {
                                key "level-id";
                                description "Enter the level list instance";

                                leaf level-id {
                                    type types-mcast-cac:constraints-level;
                                    description "Bandwidth level ID for a multicast CAC constraint";
                                }

                                leaf bandwidth {
                                    type types-mcast-cac:bandwidth {
                                        range "0..2147483647";
                                    }
                                    mandatory true;
                                    description "Bandwidth available for this level";
                                }

                                leaf-list apply-groups {
                                    type leafref {
                                        path "../../../../../../../../groups/group/name";
                                    }
                                    max-elements 8;
                                    ordered-by user;
                                    description "Apply a configuration group at this level";
                                }

                            } // list level

                            list number-down {
                                key "number-lag-port-down";
                                description "Enter the number-down list instance";

                                leaf number-lag-port-down {
                                    type uint32 {
                                        range "1..64";
                                    }
                                    description "Number of ports that are down in this LAG link";
                                }

                                leaf level {
                                    type types-mcast-cac:constraints-level;
                                    mandatory true;
                                    description "Level ID to associate with number of down LAG ports";
                                }

                                leaf-list apply-groups {
                                    type leafref {
                                        path "../../../../../../../../groups/group/name";
                                    }
                                    max-elements 8;
                                    ordered-by user;
                                    description "Apply a configuration group at this level";
                                }

                            } // list number-down

                        } // container mc-constraints

                    } // container mcac

                } // list interface

                container rp {
                    description "Enter the rp context";

                    container bootstrap {
                        description "Enter the bootstrap context";

                        leaf-list import {
                            type leafref {
                                path "../../../../../../policy-options/policy-statement/name";
                            }
                            max-elements 5;
                            ordered-by user;
                            description "Name of the policy is limited to 32 characters.";
                        }

                        leaf-list export {
                            type leafref {
                                path "../../../../../../policy-options/policy-statement/name";
                            }
                            max-elements 5;
                            ordered-by user;
                            description "Name of the policy is limited to 32 characters.";
                        }

                    } // container bootstrap

                    container ipv4 {
                        description "Enter the ipv4 context";

                        leaf auto-rp-discovery {
                            type boolean;
                            default "false";
                            description "Enable auto RP discovery";
                        }

                        list anycast {
                            key "ipv4-address rp-set-peer";
                            description "Add a list entry for anycast";

                            leaf ipv4-address {
                                type types-sros:ipv4-unicast-address;
                                description "Anycast RP address";
                            }

                            leaf rp-set-peer {
                                type types-sros:ipv4-unicast-address;
                                description "Configure a peer in the anycast rp-set.";
                            }

                        } // list anycast

                        container bsr-candidate {
                            description "Enter the bsr-candidate context";

                            leaf admin-state {
                                type types-sros:admin-state;
                                default "disable";
                                description "Administrative state of the Candidate BSR";
                            }

                            leaf priority {
                                type int32 {
                                    range "0..255";
                                }
                                default "0";
                                description "Bootstrap priority of the router";
                            }

                            leaf address {
                                type types-sros:ipv4-unicast-address;
                                description "Candidate BSR IP address for Bootstrap Router election";
                            }

                            leaf hash-mask-len {
                                type int32 {
                                    range "0..32";
                                }
                                default "30";
                                description "Length for bootstrap hash mask";
                            }

                        } // container bsr-candidate

                        container rp-candidate {
                            description "Enter the rp-candidate context";

                            leaf admin-state {
                                type types-sros:admin-state;
                                default "disable";
                                description "Administrative state of the Candidate RP";
                            }

                            leaf holdtime {
                                type int32 {
                                    range "5..255";
                                }
                                units "seconds";
                                default "150";
                                description "Time during which the neighboring router considers this router to be up";
                            }

                            leaf priority {
                                type int32 {
                                    range "0..255";
                                }
                                default "192";
                                description "Candidate RP priority";
                            }

                            leaf address {
                                type types-sros:ipv4-unicast-address;
                                description "Local RP address";
                            }

                            list group-range {
                                key "ipv4-prefix";
                                description "Add a list entry for group-range";

                                leaf ipv4-prefix {
                                    type types-sros:ipv4-multicast-prefix;
                                    description "IPv4 address and prefix length";
                                }

                            } // list group-range

                        } // container rp-candidate

                        container static {
                            description "Enter the static context";

                            list address {
                                key "ipv4-address";
                                description "Enter the address list instance";

                                leaf ipv4-address {
                                    type types-sros:ipv4-unicast-address;
                                    description "Configure the address of the statically configured RP.";
                                }

                                leaf override {
                                    type boolean;
                                    default "false";
                                    description "Change the precedence for static RP over dynamically learnt RP";
                                }

                                leaf-list apply-groups {
                                    type leafref {
                                        path "../../../../../../../../groups/group/name";
                                    }
                                    max-elements 8;
                                    ordered-by user;
                                    description "Apply a configuration group at this level";
                                }

                                list group-prefix {
                                    key "ipv4-prefix";
                                    description "Add a list entry for group-prefix";

                                    leaf ipv4-prefix {
                                        type types-sros:ipv4-multicast-prefix;
                                        description "IPv4 address and prefix length";
                                    }

                                } // list group-prefix

                            } // list address

                        } // container static

                    } // container ipv4

                    container ipv6 {
                        description "Enter the ipv6 context";

                        list anycast {
                            key "ipv6-address rp-set-peer";
                            description "Add a list entry for anycast";

                            leaf ipv6-address {
                                type types-sros:ipv6-unicast-address;
                                description "Anycast RP address";
                            }

                            leaf rp-set-peer {
                                type types-sros:ipv6-unicast-address;
                                description "Configure a peer in the anycast rp-set.";
                            }

                        } // list anycast

                        container bsr-candidate {
                            description "Enter the bsr-candidate context";

                            leaf admin-state {
                                type types-sros:admin-state;
                                default "disable";
                                description "Administrative state of the Candidate BSR";
                            }

                            leaf priority {
                                type int32 {
                                    range "0..255";
                                }
                                default "0";
                                description "Bootstrap priority of the router";
                            }

                            leaf address {
                                type types-sros:ipv6-unicast-address;
                                description "Candidate BSR IP address for Bootstrap Router election";
                            }

                            leaf hash-mask-len {
                                type int32 {
                                    range "0..128";
                                }
                                default "126";
                                description "Length for bootstrap hash mask";
                            }

                        } // container bsr-candidate

                        container embedded-rp {
                            presence "Enables embedded RP parameters configuration.";
                            description "Enter the embedded-rp context";

                            leaf admin-state {
                                type types-sros:admin-state;
                                default "disable";
                                description "Administrative state of embedded RP";
                            }

                            list group-range {
                                key "ipv6-prefix";
                                description "Add a list entry for group-range";

                                leaf ipv6-prefix {
                                    type types-sros:ipv6-multicast-prefix;
                                    description "IPv6 address and prefix length";
                                }

                            } // list group-range

                        } // container embedded-rp

                        container rp-candidate {
                            description "Enter the rp-candidate context";

                            leaf admin-state {
                                type types-sros:admin-state;
                                default "disable";
                                description "Administrative state of the Candidate RP";
                            }

                            leaf holdtime {
                                type int32 {
                                    range "5..255";
                                }
                                units "seconds";
                                default "150";
                                description "Time during which the neighboring router considers this router to be up";
                            }

                            leaf priority {
                                type int32 {
                                    range "0..255";
                                }
                                default "192";
                                description "Candidate RP priority";
                            }

                            leaf address {
                                type types-sros:ipv6-unicast-address;
                                description "Local RP address";
                            }

                            list group-range {
                                key "ipv6-prefix";
                                description "Add a list entry for group-range";

                                leaf ipv6-prefix {
                                    type types-sros:ipv6-multicast-prefix;
                                    description "IPv6 address and prefix length";
                                }

                            } // list group-range

                        } // container rp-candidate

                        container static {
                            description "Enter the static context";

                            list address {
                                key "ipv6-address";
                                description "Enter the address list instance";

                                leaf ipv6-address {
                                    type types-sros:ipv6-unicast-address;
                                    description "Static IP address of the RP";
                                }

                                leaf override {
                                    type boolean;
                                    default "false";
                                    description "Change the precedence for static RP over dynamically learnt RP";
                                }

                                leaf-list apply-groups {
                                    type leafref {
                                        path "../../../../../../../../groups/group/name";
                                    }
                                    max-elements 8;
                                    ordered-by user;
                                    description "Apply a configuration group at this level";
                                }

                                list group-prefix {
                                    key "ipv6-prefix";
                                    description "Add a list entry for group-prefix";

                                    leaf ipv6-prefix {
                                        type types-sros:ipv6-multicast-prefix;
                                        description "IPv6 address and prefix length";
                                    }

                                } // list group-prefix

                            } // list address

                        } // container static

                    } // container ipv6

                } // container rp

                list spt-switchover {
                    key "ip-prefix";
                    description "Enter the spt-switchover list instance";

                    leaf ip-prefix {
                        type types-sros:ip-multicast-prefix;
                        description "IP address and mask length";
                    }

                    leaf threshold {
                        type union {
                            type uint32 {
                                range "1..4294967294";
                            }
                            type enumeration {
                                enum "infinity"                     { value -1; }
                            }
                        }
                        units "kilobps";
                        mandatory true;
                        description "SPT switchover threshold";
                    }

                    leaf-list apply-groups {
                        type leafref {
                            path "../../../../../groups/group/name";
                        }
                        max-elements 8;
                        ordered-by user;
                        description "Apply a configuration group at this level";
                    }

                } // list spt-switchover

                container ssm-groups {
                    description "Enter the ssm-groups context";

                    list group-range {
                        key "ip-prefix";
                        description "Add a list entry for group-range";

                        leaf ip-prefix {
                            type types-sros:ip-multicast-prefix;
                            description "IP address and mask length";
                        }

                    } // list group-range

                } // container ssm-groups

            } // container pim

            container vrf-target {
                description "Enter the vrf-target context";

                choice vrf-target {
                    case vrf-both-target {

                        leaf community {
                            type types-services:route-target;
                            description "Specify a extended BGP community in the form type:x:y. Type can be only target, x and y are 16 bit integers.";
                        }

                    }
                    case vrf-ovr-target {

                        leaf import-community {
                            type types-services:route-target;
                            description "Communities that are accepted from remote PE neighbors";
                        }

                        leaf export-community {
                            type types-services:route-target;
                            description "Communities to be sent to remote PE neighbors";
                        }

                    }
                }
            } // container vrf-target

            container bgp-shared-queue {
                presence "Enable/Disable BGP Shared Queue.";
                description "Enter the bgp-shared-queue context";

                leaf cir {
                    type types-qos:bgp-shared-queue-cir-rate;
                    units "kilobps";
                    default "4000";
                    description "Committed information rate for shared queue";
                }

                leaf pir {
                    type types-qos:bgp-shared-queue-pir-rate;
                    units "kilobps";
                    default "4000";
                    description "Peak information rate for shared queue";
                }

            } // container bgp-shared-queue

            container vrf-import {
                presence "Import route policies used to determine which routes are imported from all peers.";
                description "Enter the vrf-import context";

                leaf-list policy {
                    type string {
                        length "1..255";
                        pattern "(.{1,64})|(.*[\\[].*)" {
                            error-message "Policy name too long or expression not valid";
                        }
                    }
                    min-elements 1;
                    max-elements 15;
                    ordered-by user;
                    description "Name of the import policy. The name of the policy is limited to 64 characters except for the first policy.";
                }

                leaf-list apply-groups {
                    type leafref {
                        path "../../../../groups/group/name";
                    }
                    max-elements 8;
                    ordered-by user;
                    description "Apply a configuration group at this level";
                }

            } // container vrf-import

            container vrf-export {
                presence "Export route policies used to determine which routes are advertised to all peers.";
                description "Enter the vrf-export context";

                leaf-list policy {
                    type string {
                        length "1..255";
                        pattern "(.{1,64})|(.*[\\[].*)" {
                            error-message "Policy name too long or expression not valid";
                        }
                    }
                    min-elements 1;
                    max-elements 15;
                    ordered-by user;
                    description "Name of the export policy. The name of the policy is limited to 64 characters except for the first policy.";
                }

                leaf-list apply-groups {
                    type leafref {
                        path "../../../../groups/group/name";
                    }
                    max-elements 8;
                    ordered-by user;
                    description "Apply a configuration group at this level";
                }

            } // container vrf-export

            container wpp {
                presence "L2TP for VPRN services.";
                description "Enter the wpp context";

                leaf admin-state {
                    type types-sros:admin-state;
                    default "disable";
                    description "Administrative state of WPP";
                }

                leaf-list apply-groups {
                    type leafref {
                        path "../../../../groups/group/name";
                    }
                    max-elements 8;
                    ordered-by user;
                    description "Apply a configuration group at this level";
                }

                list portal {
                    key "name";
                    description "Enter the portal list instance";

                    leaf name {
                        type types-sros:named-item;
                        description "WPP portal name";
                    }

                    leaf address {
                        type types-sros:ip-unicast-without-local-address;
                        sros-ext:immutable;
                        mandatory true;
                        description "WPP portal address";
                    }

                    leaf admin-state {
                        type types-sros:admin-state;
                        default "disable";
                        description "Administrative state of the WPP portal";
                    }

                    leaf secret {
                        type types-sros:encrypted-leaf {
                            length "1..115";
                        }
                        description "Message authentication between portal and BRAS by applying the secret used by WPPv2";
                    }

                    leaf version {
                        type uint32 {
                            range "1|2";
                        }
                        default "1";
                        description "Protocol version to be expected by the WPP portal";
                    }

                    leaf retry-interval {
                        type uint32 {
                            range "10..2000";
                        }
                        units "milliseconds";
                        default "2000";
                        description "Time between two consecutive retransmissions";
                    }

                    leaf ntf-logout-retry-count {
                        type uint32 {
                            range "0..5";
                        }
                        default "5";
                        description "Number of retransmissions of an NTF_LOGOUT message";
                    }

                    leaf ack-auth-retry-count {
                        type uint32 {
                            range "0..5";
                        }
                        default "5";
                        description "Number of retransmissions of an ACK_OUT message";
                    }

                    leaf port-format {
                        type enumeration {
                            enum "standard"                     { value 1; }
                            enum "vendor-specific"              { value 2; }
                        }
                        default "standard";
                        description "Format of the port in the ACK_INO message";
                    }

                    leaf-list apply-groups {
                        type leafref {
                            path "../../../../../groups/group/name";
                        }
                        max-elements 8;
                        ordered-by user;
                        description "Apply a configuration group at this level";
                    }

                } // list portal

            } // container wpp

            container mvpn {
                presence "The multicast VPN.";
                description "Enter the mvpn context";

                leaf c-mcast-signaling {
                    type enumeration {
                        enum "bgp"                          { value 0; }
                        enum "pim"                          { value 1; }
                    }
                    default "pim";
                    description "Specifies the protocol to use for PE-to-PE signaling of CE multicast states.";
                }

                leaf mdt-type {
                    type enumeration {
                        enum "sender-only"                  { value 0; }
                        enum "receiver-only"                { value 1; }
                        enum "sender-receiver"              { value 2; }
                    }
                    default "sender-receiver";
                    description "Specifies the type of the PE node (for P2MP only).";
                }

                leaf umh-selection {
                    type enumeration {
                        enum "highest-ip"                   { value 0; }
                        enum "hash-based"                   { value 1; }
                        enum "tunnel-status"                { value 2; }
                        enum "unicast-rt-pref"              { value 3; }
                    }
                    default "highest-ip";
                    description "Specifies the algorithm for selecting the UMH from the UMH route candidate set.";
                }

                leaf-list apply-groups {
                    type leafref {
                        path "../../../../groups/group/name";
                    }
                    max-elements 8;
                    ordered-by user;
                    description "Apply a configuration group at this level";
                }

                container auto-discovery {
                    description "Enter the auto-discovery context";

                    leaf type {
                        type enumeration {
                            enum "bgp"                          { value 1; }
                            enum "mdt-safi"                     { value 2; }
                        }
                        description "Whether multicast VPN membership auto-discovery via BGP is enabled.";
                    }

                    leaf source-address {
                        type types-sros:ipv4-address;
                        default "0.0.0.0";
                        description "a.b.c.d - source address.";
                    }

                } // container auto-discovery

                container intersite-shared {
                    description "Enter the intersite-shared context";

                    leaf admin-state {
                        type types-sros:admin-state;
                        default "enable";
                        description "Administrative state of inter-site shared C-trees use";
                    }

                    leaf persistent-type5-advertisement {
                        type boolean;
                        default "false";
                        description "Whether to advertise of source active route by RP.";
                    }

                    leaf kat-type5-advertisement-withdraw {
                        type boolean;
                        default "false";
                        description "Whether the withdrawal of Type 5 routes is enabled.";
                    }

                } // container intersite-shared

                container redundant-source-list {
                    description "Enter the redundant-source-list context";

                    list source-prefix {
                        key "ip-prefix";
                        max-elements 16;
                        description "Add a list entry for source-prefix";

                        leaf ip-prefix {
                            type types-sros:ip-unicast-prefix;
                            description "Attribute ip-prefix/prefix-length.";
                        }

                    } // list source-prefix

                } // container redundant-source-list

                container rpf-select {
                    description "Enter the rpf-select context";

                    list core-mvpn {
                        key "core-mvpn-service-name";
                        description "Enter the core-mvpn list instance";

                        leaf core-mvpn-service-name {
                            type leafref {
                                path "../../../../service-name";
                            }
                            description "Core-mvpn instance.";
                        }

                        leaf-list apply-groups {
                            type leafref {
                                path "../../../../../../groups/group/name";
                            }
                            max-elements 8;
                            ordered-by user;
                            description "Apply a configuration group at this level";
                        }

                        list group-prefix {
                            key "ip-group-prefix";
                            min-elements 1;
                            description "Enter the group-prefix list instance";

                            leaf ip-group-prefix {
                                type types-sros:ipv4-multicast-prefix;
                                description "Multicast group-prefix/prefix-length.";
                            }

                            leaf starg {
                                type boolean;
                                sros-ext:immutable;
                                default "false";
                                description "Starg flag.";
                            }

                            leaf-list apply-groups {
                                type leafref {
                                    path "../../../../../../../groups/group/name";
                                }
                                max-elements 8;
                                ordered-by user;
                                description "Apply a configuration group at this level";
                            }

                        } // list group-prefix

                    } // list core-mvpn

                } // container rpf-select

                container umh-pe-backup {
                    description "Enter the umh-pe-backup context";

                    list umh-pe {
                        key "ip-address";
                        description "Enter the umh-pe list instance";

                        leaf ip-address {
                            type types-sros:ipv4-unicast-address;
                            description "[a.b.c.d].";
                        }

                        leaf standby {
                            type types-sros:ipv4-unicast-address;
                            mandatory true;
                            description "ip-address.";
                        }

                        leaf-list apply-groups {
                            type leafref {
                                path "../../../../../../groups/group/name";
                            }
                            max-elements 8;
                            ordered-by user;
                            description "Apply a configuration group at this level";
                        }

                    } // list umh-pe

                } // container umh-pe-backup

                container vrf-import {
                    description "Enter the vrf-import context";

                    choice vrf-import {
                        case policy {

                            leaf-list policy {
                                type string {
                                    length "1..255";
                                    pattern "(.{1,64})|(.*[\\[].*)" {
                                        error-message "Policy name too long or expression not valid.";
                                    }
                                }
                                min-elements 1;
                                max-elements 15;
                                ordered-by user;
                                description "Name of the import policy. The name of the policy is limited to 64 characters except for the first policy.";
                            }

                        }
                        case unicast {

                            leaf unicast {
                                type boolean;
                                default "false";
                                description "The unicast boolean.";
                            }

                        }
                    }
                } // container vrf-import

                container vrf-export {
                    description "Enter the vrf-export context";

                    choice vrf-export {
                        case policy {

                            leaf-list policy {
                                type string {
                                    length "1..255";
                                    pattern "(.{1,64})|(.*[\\[].*)" {
                                        error-message "Policy name too long or expression not valid.";
                                    }
                                }
                                min-elements 1;
                                max-elements 15;
                                ordered-by user;
                                description "Name of the export policy. The name of the policy is limited to 64 characters except for the first policy.";
                            }

                        }
                        case unicast {

                            leaf unicast {
                                type boolean;
                                default "false";
                                description "The unicast boolean.";
                            }

                        }
                    }
                } // container vrf-export

                container vrf-target {
                    description "Enter the vrf-target context";

                    leaf community {
                        type types-services:route-target;
                        description "Extended community name for the Multicast VPN (MVPN) vrf-import or vrf-export policy.";
                    }

                    leaf unicast {
                        type boolean;
                        default "false";
                        description "The boolean to specify whether unicast vrf-target extended community is used for the Multicast VPN.";
                    }

                    container import {
                        description "Enter the import context";

                        leaf community {
                            type types-services:route-target;
                            description "Extended community name for the Multicast VPN vrf-import policy.";
                        }

                        leaf unicast {
                            type boolean;
                            default "false";
                            description "The boolean to specify whether unicast vrf-target import extended community is used for the Multicast VPN.";
                        }

                    } // container import

                    container export {
                        description "Enter the export context";

                        leaf community {
                            type types-services:route-target;
                            description "Extended community name for the Multicast VPN vrf-export policy.";
                        }

                        leaf unicast {
                            type boolean;
                            default "false";
                            description "The boolean to specify whether unicast vrf-target export extended community is used for the Multicast VPN.";
                        }

                    } // container export

                } // container vrf-target

                container provider-tunnel {
                    description "Enter the provider-tunnel context";

                    container inclusive {
                        description "Enter the inclusive context";

                        leaf bsr {
                            type enumeration {
                                enum "unicast"                      { value 1; }
                                enum "spmsi"                        { value 2; }
                            }
                            description "The bsr signaling.";
                        }

                        leaf wildcard-spmsi {
                            type boolean;
                            default "false";
                            description "Whether the wildcard spmsi is enabled.";
                        }

                        choice ipmsi {
                            case rsvp {

                                container rsvp {
                                    presence "Whether the context for specifiying RSVP P2MP LSP for the provider tunnel is enabled.";
                                    description "Enter the rsvp context";

                                    leaf admin-state {
                                        type types-sros:admin-state;
                                        default "disable";
                                        description "Administrative state of RSVP use for provider tunnels";
                                    }

                                    leaf bfd-leaf {
                                        type boolean;
                                        default "false";
                                        description "Whether the bfd-leaf is enabled.";
                                    }

                                    leaf lsp-template {
                                        type leafref {
                                            path "../../../../../../../router/mpls/lsp-template/template-name";
                                        }
                                        description "Specify the Lsp Template.";
                                    }

                                    container bfd-root {
                                        presence "Whether the bfd-root is enabled.";
                                        description "Enter the bfd-root context";

                                        leaf transmit-interval {
                                            type uint32 {
                                                range "10..100000";
                                            }
                                            mandatory true;
                                            description "[10..100000] in milliseconds.";
                                        }

                                        leaf multiplier {
                                            type uint32 {
                                                range "1..20";
                                            }
                                            default "3";
                                            description "[3..20].";
                                        }

                                    } // container bfd-root

                                } // container rsvp

                            }
                            case mldp {

                                container mldp {
                                    presence "Whether the context for specifiying MLDP for the provider tunnel is enabled.";
                                    description "Enter the mldp context";

                                    leaf admin-state {
                                        type types-sros:admin-state;
                                        default "disable";
                                        description "Administrative state of MLDP LSP use for tunnels";
                                    }

                                } // container mldp

                            }
                            case pim {

                                container pim {
                                    presence "The PIM mode and group address for PIM based inclusive provider tunnels.";
                                    description "Enter the pim context";

                                    leaf mode {
                                        type enumeration {
                                            enum "asm"                          { value 1; }
                                            enum "ssm"                          { value 2; }
                                        }
                                        mandatory true;
                                        description "keyword - PIM mode.";
                                    }

                                    leaf group-address {
                                        type types-sros:ipv4-multicast-address;
                                        mandatory true;
                                        description "a.b.c.d - multicast group address.";
                                    }

                                    leaf hello-interval {
                                        type uint32 {
                                            range "0..255";
                                        }
                                        default "30";
                                        description "The frequency at which PIM hello messages are sent over this interface.";
                                    }

                                    leaf hello-multiplier {
                                        type uint32 {
                                            range "20..100";
                                        }
                                        default "35";
                                        description "Hello-multiplier in multiples of 0.1 (deci-units).";
                                    }

                                    leaf improved-assert {
                                        type boolean;
                                        default "true";
                                        description "Whether the improved assert processing is enabled.";
                                    }

                                    leaf three-way-hello {
                                        type boolean;
                                        default "false";
                                        description "Compatibility mode for three-way-hello.";
                                    }

                                    leaf tracking-support {
                                        type boolean;
                                        default "false";
                                        description "Whether the tracking support is enabled.";
                                    }

                                    leaf admin-state {
                                        type types-sros:admin-state;
                                        default "enable";
                                        description "Administrative state of PIM use for provider tunnels";
                                    }

                                } // container pim

                            }
                            case bier {

                                container bier {
                                    presence "The BIER for inclusive provider tunnel.";
                                    description "Enter the bier context";

                                    leaf admin-state {
                                        type types-sros:admin-state;
                                        default "disable";
                                        description "Administrative state of the use of BIER.";
                                    }

                                    leaf sub-domain {
                                        type int32 {
                                            range "0..255";
                                        }
                                        description "The BIER sub domain.";
                                    }

                                } // container bier

                            }
                        }
                    } // container inclusive

                    container selective {
                        description "Enter the selective context";

                        leaf auto-discovery {
                            type boolean;
                            default "false";
                            description "Whether the multicast VPN membership auto-discovery via BGP is enabled.";
                        }

                        leaf data-delay-interval {
                            type uint32 {
                                range "3..180";
                            }
                            default "3";
                            description "The data delay interval.";
                        }

                        leaf join-tlv-packing {
                            type boolean;
                            default "true";
                            description "Disable/enable packing of multiple MDT join tlvs.";
                        }

                        leaf asm-mdt {
                            type boolean;
                            default "false";
                            description "Whether the mdt-range check at egress for classic draft-rosen only is enabled.";
                        }

                        choice spmsi {
                            case rsvp {

                                container rsvp {
                                    presence "Whether the context for specifying RSVP P2MP LSP for the provider tunnel is enabled.";
                                    description "Enter the rsvp context";

                                    leaf lsp-template {
                                        type leafref {
                                            path "../../../../../../../router/mpls/lsp-template/template-name";
                                        }
                                        description "Specify the Lsp Template.";
                                    }

                                    leaf admin-state {
                                        type types-sros:admin-state;
                                        default "disable";
                                        description "Administrative state of RSVP use for provider tunnels";
                                    }

                                    leaf maximum-p2mp-spmsi {
                                        type uint32 {
                                            range "1..4000";
                                        }
                                        default "10";
                                        description "Specify the maximum number of p2mp s-pmsi tunnels for the mvpn.";
                                    }

                                } // container rsvp

                            }
                            case mldp {

                                container mldp {
                                    presence "Whether the context for specifying MLDP for the provider tunnel is enabled.";
                                    description "Enter the mldp context";

                                    leaf admin-state {
                                        type types-sros:admin-state;
                                        default "disable";
                                        description "Administrative state of MLDP LSP use for tunnels";
                                    }

                                    leaf maximum-p2mp-spmsi {
                                        type uint32 {
                                            range "1..4000";
                                        }
                                        default "10";
                                        description "Specify the maximum number of p2mp s-pmsi tunnels for the mvpn.";
                                    }

                                } // container mldp

                            }
                            case pim {

                                container pim {
                                    presence "Whether the context for specifying PIM for the provider tunnel is enabled.";
                                    description "Enter the pim context";

                                    leaf mode {
                                        type enumeration {
                                            enum "asm"                          { value 1; }
                                            enum "ssm"                          { value 2; }
                                        }
                                        mandatory true;
                                        description "PIM mode.";
                                    }

                                    leaf group-prefix {
                                        type types-sros:ipv4-multicast-prefix;
                                        mandatory true;
                                        description "Multicast group-prefix.";
                                    }

                                } // container pim

                            }
                            case bier {

                                container bier {
                                    presence "The BIER for selective provider tunnel.";
                                    description "Enter the bier context";

                                    leaf admin-state {
                                        type types-sros:admin-state;
                                        default "disable";
                                        description "Administrative state of the use of BIER.";
                                    }

                                    leaf sub-domain {
                                        type int32 {
                                            range "0..255";
                                        }
                                        description "The BIER sub domain.";
                                    }

                                } // container bier

                            }
                        }
                        container data-threshold {
                            description "Enter the data-threshold context";

                            list group-prefix {
                                key "ip-group-prefix";
                                description "Enter the group-prefix list instance";

                                leaf ip-group-prefix {
                                    type types-sros:ip-multicast-prefix;
                                    description "Multicast group-prefix.";
                                }

                                leaf threshold {
                                    type int64 {
                                        range "0..4294967294";
                                    }
                                    units "kilobps";
                                    mandatory true;
                                    description "The threshold in kbps for a group prefix.";
                                }

                                leaf pe-threshold-add {
                                    type uint32 {
                                        range "1..65535";
                                    }
                                    default "65535";
                                    description "The threshold.";
                                }

                                leaf pe-threshold-delete {
                                    type uint32 {
                                        range "2..65535";
                                    }
                                    default "65535";
                                    description "The threshold.";
                                }

                                leaf-list apply-groups {
                                    type leafref {
                                        path "../../../../../../../../groups/group/name";
                                    }
                                    max-elements 8;
                                    ordered-by user;
                                    description "Apply a configuration group at this level";
                                }

                            } // list group-prefix

                        } // container data-threshold

                        list multistream-spmsi {
                            key "multistream-id";
                            description "Enter the multistream-spmsi list instance";

                            leaf multistream-id {
                                type uint32 {
                                    range "1..1024";
                                }
                                description "Multistream spmsi id";
                            }

                            leaf admin-state {
                                type types-sros:admin-state;
                                default "disable";
                                description "Administrative state of multi-stream S-PMSI";
                            }

                            leaf-list apply-groups {
                                type leafref {
                                    path "../../../../../../../groups/group/name";
                                }
                                max-elements 8;
                                ordered-by user;
                                description "Apply a configuration group at this level";
                            }

                            choice spsmi {
                                case lsp-template {

                                    leaf lsp-template {
                                        type leafref {
                                            path "../../../../../../../router/mpls/lsp-template/template-name";
                                        }
                                        description "Specify the Lsp Template.";
                                    }

                                }
                                case pim {

                                    container pim {
                                        presence "Whether the configuration of mdt pim is enabled.";
                                        description "Enter the pim context";

                                        leaf mode {
                                            type enumeration {
                                                enum "asm"                          { value 1; }
                                                enum "ssm"                          { value 2; }
                                            }
                                            description "The mode.";
                                        }

                                        leaf group-address {
                                            type types-sros:ipv4-multicast-address;
                                            description "a.b.c.d - multicast group address.";
                                        }

                                    } // container pim

                                }
                            }
                            list group-prefix {
                                key "ip-group-prefix source-prefix";
                                description "Add a list entry for group-prefix";

                                leaf ip-group-prefix {
                                    type types-sros:ip-multicast-prefix;
                                    description "Multicast group-prefix/prefix-length.";
                                }

                                leaf source-prefix {
                                    type types-sros:ip-unicast-prefix;
                                    description "Multicast source-prefix/prefix-length.";
                                }

                            } // list group-prefix

                        } // list multistream-spmsi

                    } // container selective

                } // container provider-tunnel

            } // container mvpn

            container ntp {
                presence "Enables/disables NTP server in this VPRN";
                description "Enter the ntp context";

                leaf authentication-check {
                    type boolean;
                    default "true";
                    description "Reject NTP PDUs that do not match the authentication key-id, type, or key requirements";
                }

                leaf admin-state {
                    type types-sros:admin-state;
                    default "disable";
                    description "Administrative state of NTP execution";
                }

                leaf authenticate {
                    type boolean;
                    default "false";
                    description "Authentication of NTP PDUs when acting as a server";
                }

                leaf-list apply-groups {
                    type leafref {
                        path "../../../../groups/group/name";
                    }
                    max-elements 8;
                    ordered-by user;
                    description "Apply a configuration group at this level";
                }

                list authentication-key {
                    key "key-id";
                    description "Enter the authentication-key list instance";

                    leaf key-id {
                        type uint32 {
                            range "1..255";
                        }
                        description "Index of the NTP authentication key table that uniquely identifies an authentication key and type";
                    }

                    leaf key {
                        type types-sros:encrypted-leaf {
                            length "1..71";
                        }
                        mandatory true;
                        description "Key to authenticate NTP packets";
                    }

                    leaf type {
                        type enumeration {
                            enum "des"                          { value 1; }
                            enum "message-digest"               { value 2; }
                        }
                        mandatory true;
                        description "Type of authentication method to authenticate NTP packet";
                    }

                    leaf-list apply-groups {
                        type leafref {
                            path "../../../../../groups/group/name";
                        }
                        max-elements 8;
                        ordered-by user;
                        description "Apply a configuration group at this level";
                    }

                } // list authentication-key

                list broadcast {
                    key "interface-name";
                    description "Enter the broadcast list instance";

                    leaf interface-name {
                        type leafref {
                            path "../../../../vprn[service-name=current()/../../../service-name]/interface/interface-name";
                        }
                        description "Router interface name.";
                    }

                    leaf version {
                        type uint32 {
                            range "2..4";
                        }
                        default "4";
                        description "NTP version number generated or accepted by this node in NTP packets";
                    }

                    leaf ttl {
                        type uint32 {
                            range "1..255";
                        }
                        default "127";
                        description "TTL value of messages transmitted by this broadcast address";
                    }

                    leaf key-id {
                        type leafref {
                            path "../../authentication-key/key-id";
                        }
                        description "Specifies the key-id of the authentication key and its authentication type used by this node to receive and transmit NTP packets to and from an NTP node.";
                    }

                    leaf-list apply-groups {
                        type leafref {
                            path "../../../../../groups/group/name";
                        }
                        max-elements 8;
                        ordered-by user;
                        description "Apply a configuration group at this level";
                    }

                } // list broadcast

            } // container ntp

            container aaa {
                description "Enter the aaa context";

                container remote-servers {
                    description "Enter the remote-servers context";

                    container tacplus {
                        presence "TACACS+ authentication parameters";
                        description "Enter the tacplus context";

                        leaf interactive-authentication {
                            type boolean;
                            default "false";
                            description "Enable/disable TACACS+ interactive authentication.";
                        }

                        leaf admin-state {
                            type types-sros:admin-state;
                            default "enable";
                            description "Administrative state of the TACACS+ protocol operation";
                        }

                        leaf server-timeout {
                            type types-sros:time-duration {
                                range "1..90";
                            }
                            units "seconds";
                            default "3";
                            description "Timeout for a response from an TACACS+ server.";
                        }

                        leaf use-default-template {
                            type boolean;
                            default "true";
                            description "Enable/disable TACACS+ default template.";
                        }

                        leaf-list apply-groups {
                            type leafref {
                                path "../../../../../../groups/group/name";
                            }
                            max-elements 8;
                            ordered-by user;
                            description "Apply a configuration group at this level";
                        }

                        container accounting {
                            presence "Enable/disable TACACS+ command accounting for the service VPRN";
                            description "Enter the accounting context";

                            leaf record-type {
                                type enumeration {
                                    enum "start-stop"                   { value 1; }
                                    enum "stop-only"                    { value 2; }
                                }
                                default "stop-only";
                                description "Configure the type of accounting record packet that is to be sent to the TACACS+ server.";
                            }

                        } // container accounting

                        container authorization {
                            presence "Enable/disable TACACS+ command authorization.";
                            description "Enter the authorization context";

                            leaf use-priv-lvl {
                                type boolean;
                                default "false";
                                description "Enable/disable the privilege level mapping.";
                            }

                        } // container authorization

                        container priv-lvl-map {
                            description "Enter the priv-lvl-map context";

                            list priv-lvl {
                                key "level";
                                description "Enter the priv-lvl list instance";

                                leaf level {
                                    type uint32 {
                                        range "0..15";
                                    }
                                    description "Specifies the privilege level for this mapping.";
                                }

                                leaf user-profile-name {
                                    type leafref {
                                        path "../../../../../../../../system/security/aaa/local-profiles/profile/user-profile-name";
                                    }
                                    mandatory true;
                                    description "Specifies the user profile for this mapping.";
                                }

                                leaf-list apply-groups {
                                    type leafref {
                                        path "../../../../../../../../groups/group/name";
                                    }
                                    max-elements 8;
                                    ordered-by user;
                                    description "Apply a configuration group at this level";
                                }

                            } // list priv-lvl

                        } // container priv-lvl-map

                        list server {
                            key "index";
                            max-elements 5;
                            description "Enter the server list instance";

                            leaf index {
                                type uint32 {
                                    range "1..5";
                                }
                                description "Identifies a specific TACACS+ server.";
                            }

                            leaf address {
                                type types-sros:ip-unicast-address;
                                mandatory true;
                                description "IP address of TACACS+ server.";
                            }

                            leaf port {
                                type types-qos:tcp-udp-match-port;
                                default "49";
                                description "TCP port number on which to contact TACACS+ server.";
                            }

                            leaf secret {
                                type types-sros:encrypted-leaf {
                                    length "1..199";
                                }
                                mandatory true;
                                description "The secret key associated with the TACACS+ server. The value of secret cannot be set to an empty string.";
                            }

                            leaf-list apply-groups {
                                type leafref {
                                    path "../../../../../../../groups/group/name";
                                }
                                max-elements 8;
                                ordered-by user;
                                description "Apply a configuration group at this level";
                            }

                        } // list server

                    } // container tacplus

                    container radius {
                        presence "RADIUS authentication parameters";
                        description "Enter the radius context";

                        leaf admin-state {
                            type types-sros:admin-state;
                            default "enable";
                            description "Administrative state of RADIUS authentication";
                        }

                        leaf accounting {
                            type boolean;
                            default "false";
                            description "Enable/disable RADIUS command accounting.";
                        }

                        leaf accounting-port {
                            type uint32 {
                                range "1..65535";
                            }
                            default "1813";
                            description "Port number on which to contact RADIUS server for accounting requests.";
                        }

                        leaf authorization {
                            type boolean;
                            default "false";
                            description "Enable/disable RADIUS command authorization.";
                        }

                        leaf interactive-authentication {
                            type boolean;
                            default "false";
                            description "Enable/disable RADIUS interactive authentication.";
                        }

                        leaf server-retry {
                            type uint32 {
                                range "1..10";
                            }
                            default "3";
                            description "Number of attempts to retry contacting RADIUS.";
                        }

                        leaf server-timeout {
                            type uint32 {
                                range "1..90";
                            }
                            units "seconds";
                            default "3";
                            description "Timeout for a response from RADIUS server.";
                        }

                        leaf port {
                            type uint32 {
                                range "1..65535";
                            }
                            default "1812";
                            description "Port number on which to contact RADIUS server.";
                        }

                        leaf use-default-template {
                            type boolean;
                            default "false";
                            description "Enable/disable RADIUS default template.";
                        }

                        leaf access-algorithm {
                            type enumeration {
                                enum "direct"                       { value 1; }
                                enum "round-robin"                  { value 2; }
                            }
                            default "direct";
                            description "Configure the algorithm used to access the set of RADIUS servers.";
                        }

                        leaf-list apply-groups {
                            type leafref {
                                path "../../../../../../groups/group/name";
                            }
                            max-elements 8;
                            ordered-by user;
                            description "Apply a configuration group at this level";
                        }

                        list server {
                            key "index";
                            max-elements 5;
                            description "Enter the server list instance";

                            leaf index {
                                type uint32 {
                                    range "1..5";
                                }
                                description "Unique number which identifies a specific RADIUS server.";
                            }

                            leaf address {
                                type types-sros:ip-unicast-address;
                                mandatory true;
                                description "IP address of Radius server.";
                            }

                            leaf secret {
                                type types-sros:encrypted-leaf {
                                    length "1..115";
                                }
                                mandatory true;
                                description "The secret key associated with RADIUS server. The value of secret cannot be set to an empty string.";
                            }

                            leaf-list apply-groups {
                                type leafref {
                                    path "../../../../../../../groups/group/name";
                                }
                                max-elements 8;
                                ordered-by user;
                                description "Apply a configuration group at this level";
                            }

                        } // list server

                    } // container radius

                } // container remote-servers

            } // container aaa

            container aggregates {
                description "Enter the aggregates context";

                leaf-list apply-groups {
                    type leafref {
                        path "../../../../groups/group/name";
                    }
                    max-elements 8;
                    ordered-by user;
                    description "Apply a configuration group at this level";
                }

                list aggregate {
                    key "ip-prefix";
                    description "Enter the aggregate list instance";

                    leaf ip-prefix {
                        type types-sros:ip-unicast-prefix;
                        description "Destination IP address prefix of the aggregate route";
                    }

                    leaf as-set {
                        type boolean;
                        default "false";
                        description "Use AS_SET path segment type for the aggregate route";
                    }

                    leaf-list community {
                        type types-sros:community;
                        max-elements 12;
                        ordered-by user;
                        description "Community name that is added to the aggregate route";
                    }

                    leaf description {
                        type types-sros:description;
                        description "Text description";
                    }

                    leaf summary-only {
                        type boolean;
                        default "false";
                        description "Advertise the aggregate route only";
                    }

                    leaf local-preference {
                        type int64 {
                            range "0..4294967295";
                        }
                        description "Local preference used when aggregate route is exported";
                    }

                    leaf discard-component-communities {
                        type boolean;
                        default "false";
                        description "Advertise aggregate with aggregate route community set";
                    }

                    leaf-list apply-groups {
                        type leafref {
                            path "../../../../../groups/group/name";
                        }
                        max-elements 8;
                        ordered-by user;
                        description "Apply a configuration group at this level";
                    }

                    choice next-hop {
                        case blackhole {

                            container blackhole {
                                presence "blackhole";
                                description "Enter the blackhole context";

                                leaf generate-icmp {
                                    type boolean;
                                    default "false";
                                    description "Send ICMP unreachable messages for aggregate routes";
                                }

                            } // container blackhole

                        }
                        case indirect {

                            leaf indirect {
                                type types-sros:ip-unicast-address;
                                sros-ext:immutable;
                                description "Address of the indirect next hop";
                            }

                        }
                    }
                    container aggregator {
                        description "Enter the aggregator context";

                        leaf as-number {
                            type uint32 {
                                range "1..max";
                            }
                            description "Aggregator AS number";
                        }

                        leaf address {
                            type types-sros:ipv4-unicast-address;
                            description "Aggregator IP address";
                        }

                    } // container aggregator

                } // list aggregate

            } // container aggregates

            container wlan-gw {
                presence "WLAN Gateway functionality for VPRN services";
                description "Enter the wlan-gw context";

                leaf-list apply-groups {
                    type leafref {
                        path "../../../../groups/group/name";
                    }
                    max-elements 8;
                    ordered-by user;
                    description "Apply a configuration group at this level";
                }

                container mobility-triggered-accounting {
                    description "Enter the mobility-triggered-accounting context";

                    leaf admin-state {
                        type types-sros:admin-state;
                        default "disable";
                        description "Administrative state of mobility-triggered-accounting";
                    }

                    leaf include-counters {
                        type boolean;
                        default "false";
                        description "Include counters in interim updates";
                    }

                    leaf hold-down {
                        type types-sros:time-duration {
                            range "60..86400";
                        }
                        units "seconds";
                        description "Hold additional mobility-triggered update until this timer expires";
                    }

                } // container mobility-triggered-accounting

                container distributed-subscriber-mgmt {
                    description "Enter the distributed-subscriber-mgmt context";

                    leaf ipv6-tcp-mss-adjust {
                        type uint32 {
                            range "160..10240";
                        }
                        description "Insert or decrease the TCP Maximum Segment Size option to this value for upstream IPv6 SYN messages";
                    }

                    leaf-list apply-groups {
                        type leafref {
                            path "../../../../../groups/group/name";
                        }
                        max-elements 8;
                        ordered-by user;
                        description "Apply a configuration group at this level";
                    }

                } // container distributed-subscriber-mgmt

                container xconnect {
                    description "Enter the xconnect context";

                    leaf admin-state {
                        type types-sros:admin-state;
                        default "disable";
                        description "Administrative state of the WLAN-GW cross-connect";
                    }

                    leaf tunnel-source-ip {
                        type types-sros:ipv6-prefix;
                        sros-ext:auto-restart-to-modify;
                        description "IPv6 prefix from which source addresses of cross-connect tunnels will be chosen";
                    }

                    leaf wlan-gw-group {
                        type leafref {
                            path "../../../../../isa/wlan-gw-group/id";
                        }
                        sros-ext:auto-restart-to-modify;
                        description "ISA WLAN-GW Group";
                    }

                    leaf-list apply-groups {
                        type leafref {
                            path "../../../../../groups/group/name";
                        }
                        max-elements 8;
                        ordered-by user;
                        description "Apply a configuration group at this level";
                    }

                } // container xconnect

            } // container wlan-gw

            container auto-bind-tunnel {
                description "Enter the auto-bind-tunnel context";

                leaf ecmp {
                    type types-router:mpls-ecmp;
                    default "1";
                    description "Maximum number of tunnels that can be used as ECMP next-hops for the VPRN";
                }

                leaf weighted-ecmp {
                    type boolean;
                    default "false";
                    description "Allow weighted load-balancing";
                }

                leaf resolution {
                    type types-services:resolve-status;
                    default "none";
                    description "Resolution method for tunnel selection";
                }

                leaf enforce-strict-tunnel-tagging {
                    type boolean;
                    default "false";
                    description "Consider only LSPs marked with an admin-tag for next-hop resolution";
                }

                leaf-list apply-groups {
                    type leafref {
                        path "../../../../groups/group/name";
                    }
                    max-elements 8;
                    ordered-by user;
                    description "Apply a configuration group at this level";
                }

                container resolution-filter {
                    description "Enter the resolution-filter context";

                    leaf bgp {
                        type boolean;
                        default "true";
                        description "Set BGP type for auto bind tunnel";
                    }

                    leaf gre {
                        type boolean;
                        default "false";
                        description "Enable/disable setting GRE type for auto-bind-tunnel";
                    }

                    leaf ldp {
                        type boolean;
                        default "false";
                        description "Enable/disable setting LDP type for auto-bind-tunnel";
                    }

                    leaf rsvp {
                        type boolean;
                        default "false";
                        description "Enable/disable setting RSVP-TE type for auto-bind-tunnel";
                    }

                    leaf sr-isis {
                        type boolean;
                        default "false";
                        description "Enable/disable setting SR-ISIS type for auto-bind-tunnel";
                    }

                    leaf sr-ospf {
                        type boolean;
                        default "false";
                        description "Enable/disable setting SR-OSPF type for auto-bind-tunnel";
                    }

                    leaf sr-te {
                        type boolean;
                        default "false";
                        description "Enable/disable setting SR-TE type for auto-bind-tunnel";
                    }

                    leaf udp {
                        type boolean;
                        default "false";
                        description "Set UDP type for auto-bind-tunnel";
                    }

                    leaf rib-api {
                        type boolean;
                        default "false";
                        description "Enable/disable setting RIB API type for auto-bind-tunnel";
                    }

                    leaf mpls-fwd-policy {
                        type boolean;
                        default "false";
                        description "Enable/disable setting MPLS Forwarding Policy type for auto-bind-tunnel";
                    }

                    leaf sr-policy {
                        type boolean;
                        default "false";
                        description "Enable/disable setting SR Policy type for auto-bind-tunnel";
                    }

                    leaf sr-ospf3 {
                        type boolean;
                        default "false";
                        description "Use segment routing ospf3 for next hop resolution.";
                    }

                } // container resolution-filter

            } // container auto-bind-tunnel

            container dns {
                presence "Allows to configure router specific DNS parameters.";
                description "Enter the dns context";

                leaf admin-state {
                    type types-sros:admin-state;
                    default "disable";
                    description "Administrative state of DNS";
                }

                leaf-list server {
                    type types-sros:ip-unicast-address;
                    max-elements 3;
                    ordered-by user;
                    description "List of DNS servers used for address resolution.";
                }

                leaf ipv4-source-address {
                    type union {
                        type enumeration {
                            enum "use-interface-ip"             { value 0; }
                        }
                        type types-sros:ipv4-unicast-address;
                    }
                    default "use-interface-ip";
                    description "Source address to contact an IPv4 DNS server";
                }

                leaf ipv6-source-address {
                    type union {
                        type enumeration {
                            enum "use-interface-ip"             { value 0; }
                        }
                        type types-sros:ipv6-unicast-address;
                    }
                    default "use-interface-ip";
                    description "Source address to contact an IPv6 DNS server";
                }

                leaf default-domain {
                    type types-sros:fully-qualified-domain-name {
                        pattern "[a-z0-9\\-\\.]+";
                    }
                    description "Default domain name to be searched when performing DNS address resolution";
                }

                leaf-list apply-groups {
                    type leafref {
                        path "../../../../groups/group/name";
                    }
                    max-elements 8;
                    ordered-by user;
                    description "Apply a configuration group at this level";
                }

            } // container dns

            container bgp {
                presence "Enable BGP for VPRN services";
                description "Enter the bgp context";

                leaf description {
                    type types-sros:description;
                    description "Text description";
                }

                leaf connect-retry {
                    type int32 {
                        range "1..65535";
                    }
                    default "120";
                    description "BGP connect retry timer value";
                }

                leaf admin-state {
                    type types-sros:admin-state;
                    default "enable";
                    description "Administrative state of the BGP instance";
                }

                leaf keepalive {
                    type int32 {
                        range "0..21845";
                    }
                    default "30";
                    description "Time after which the BGP KEEPALIVE message is sent";
                }

                leaf damping {
                    type boolean;
                    default "false";
                    description "Use BGP route damping to reduce route flap";
                }

                leaf local-preference {
                    type uint32;
                    default "100";
                    description "Default local preference if not in incoming routes";
                }

                leaf loop-detect {
                    type types-bgp:loop-detect;
                    default "ignore-loop";
                    description "Strategy for loop detection in the AS path";
                }

                leaf loop-detect-threshold {
                    type uint32 {
                        range "0..15";
                    }
                    default "0";
                    description "Threshold for the global ASN in a received AS path";
                }

                leaf min-route-advertisement {
                    type int16 {
                        range "1..255";
                    }
                    default "30";
                    description "Minimum time before a prefix can be advertised to peer";
                }

                leaf aggregator-id-zero {
                    type boolean;
                    default "false";
                    description "Set router ID in the BGP AGGREGATOR attribute to 0";
                }

                leaf preference {
                    type uint32 {
                        range "1..255";
                    }
                    default "170";
                    description "Route preference for routes learned from all peers";
                }

                leaf multihop {
                    type int32 {
                        range "1..255";
                    }
                    description "TTL in IP packet headers for EBGP peers multi-hops away";
                }

                leaf med-out {
                    type union {
                        type uint32;
                        type enumeration {
                            enum "igp-cost"                     { value -1; }
                        }
                    }
                    description "Default MED attribute value to advertise to peers";
                }

                leaf authentication-key {
                    type types-sros:encrypted-leaf {
                        length "1..370";
                    }
                    description "BGP authentication key for all peers";
                }

                leaf client-reflect {
                    type boolean;
                    default "true";
                    description "Allow client reflection of routes by route reflector";
                }

                leaf asn-4-byte {
                    type boolean;
                    default "true";
                    description "Advertise the use of 4-byte ASNs";
                }

                leaf eibgp-loadbalance {
                    type boolean;
                    default "false";
                    description "Use ECMP over BGP VPN and BGP routes";
                }

                leaf path-mtu-discovery {
                    type boolean;
                    default "false";
                    description "Enable Path MTU Discovery";
                }

                leaf enforce-first-as {
                    type boolean;
                    default "false";
                    description "Enforce the configured peer AS value in received routes";
                }

                leaf initial-send-delay-zero {
                    type boolean;
                    default "false";
                    description "Send BGP updates as soon as session comes up";
                }

                leaf router-id {
                    type types-sros:ipv4-address;
                    description "Router ID for the BGP instance in the AS";
                }

                leaf ibgp-multipath {
                    type boolean;
                    default "false";
                    description "Enable IBGP multipath load balancing";
                }

                leaf bfd-liveness {
                    type boolean;
                    default "false";
                    description "Enable BFD";
                }

                leaf fast-external-failover {
                    type boolean;
                    default "true";
                    description "Drop external BGP session immediately when link fails";
                }

                leaf advertise-inactive {
                    type boolean;
                    default "false";
                    description "Advertise an inactive BGP route to peers";
                }

                leaf authentication-keychain {
                    type leafref {
                        path "../../../../system/security/keychains/keychain/keychain-name";
                    }
                    description "TCP authentication keychain for the session";
                }

                leaf rapid-withdrawal {
                    type boolean;
                    default "false";
                    description "Send BGP withdrawal UPDATE messages immediately";
                }

                leaf peer-ip-tracking {
                    type boolean;
                    default "false";
                    description "Enable BGP peer tracking";
                }

                leaf split-horizon {
                    type boolean;
                    default "false";
                    description "Prevent routes being reflected back to best-route peer";
                }

                leaf third-party-nexthop {
                    type boolean;
                    default "false";
                    description "Apply third-party next-hop processing to EBGP peers";
                }

                leaf dynamic-neighbor-limit {
                    type uint32 {
                        range "1..8192";
                    }
                    description "Maximum dynamic BGP sessions to accept from remote peer";
                }

                leaf label-preference {
                    type uint32 {
                        range "1..255";
                    }
                    default "170";
                    description "Route preference for routes from labeled-unicast peers";
                }

                leaf peer-tracking-policy {
                    type types-sros:named-item-64;
                    description "Policy for BGP peer tracking on router instance";
                }

                leaf-list apply-groups {
                    type leafref {
                        path "../../../../groups/group/name";
                    }
                    max-elements 8;
                    ordered-by user;
                    description "Apply a configuration group at this level";
                }

                container hold-time {
                    description "Enter the hold-time context";

                    leaf seconds {
                        type int32 {
                            range "0|3..65535";
                        }
                        default "90";
                        description "Maximum time BGP waits between successive messages";
                    }

                    leaf minimum-hold-time {
                        type int32 {
                            range "0|3..65535";
                        }
                        default "0";
                        description "Minimum hold time between successive messages";
                    }

                } // container hold-time

                container family {
                    description "Enter the family context";

                    leaf ipv4 {
                        type boolean;
                        default "true";
                        description "Add support for the IPv4 address family";
                    }

                    leaf ipv6 {
                        type boolean;
                        default "false";
                        description "Add support for the IPv6 address family";
                    }

                    leaf mcast-ipv4 {
                        type boolean;
                        default "false";
                        description "Add support for the MCAST-IPv4 address family";
                    }

                    leaf flow-ipv4 {
                        type boolean;
                        default "false";
                        description "Add support for the flowspec-IPv4 address family";
                    }

                    leaf flow-ipv6 {
                        type boolean;
                        default "false";
                        description "Add support for the flowspec-IPv6 address family";
                    }

                    leaf mcast-ipv6 {
                        type boolean;
                        default "false";
                        description "Add support for the MCAST-IPv6 address family";
                    }

                    leaf label-ipv4 {
                        type boolean;
                        default "false";
                        description "Add support for the label-IPv4 address family";
                    }

                } // container family

                container send-default {
                    description "Enter the send-default context";

                    leaf ipv4 {
                        type boolean;
                        default "false";
                        description "Enable IPv4 family type";
                    }

                    leaf ipv6 {
                        type boolean;
                        default "false";
                        description "Enable IPv6 family type";
                    }

                    leaf export-policy {
                        type types-sros:named-item-64;
                        description "Export policy name";
                    }

                } // container send-default

                container default-preference {
                    description "Enter the default-preference context";

                    leaf ebgp {
                        type uint32 {
                            range "0..255";
                        }
                        default "0";
                        description "Default preference for EBGP";
                    }

                    leaf ibgp {
                        type uint32 {
                            range "0..255";
                        }
                        default "0";
                        description "Default preference for IBGP";
                    }

                } // container default-preference

                container default-label-preference {
                    description "Enter the default-label-preference context";

                    leaf ebgp {
                        type uint32 {
                            range "0..255";
                        }
                        default "0";
                        description "Default preference for EBGP";
                    }

                    leaf ibgp {
                        type uint32 {
                            range "0..255";
                        }
                        default "0";
                        description "Default preference for IBGP";
                    }

                } // container default-label-preference

                container remove-private {
                    presence "Remove private AS numbers from the AS Path before advertising to a peer.";
                    description "Enter the remove-private context";

                    leaf limited {
                        type boolean;
                        default "false";
                        description "Remove private ASNs up to first public ASN encountered";
                    }

                    leaf skip-peer-as {
                        type boolean;
                        default "false";
                        description "Keep private ASN if AS-PATH contains eBGP peer's ASN";
                    }

                    leaf replace {
                        type boolean;
                        default "false";
                        description "Replace private ASN with global ASN before advertising";
                    }

                } // container remove-private

                container cluster {
                    description "Enter the cluster context";

                    leaf cluster-id {
                        type types-sros:ipv4-address;
                        description "Route reflector cluster ID";
                    }

                } // container cluster

                container ebgp-default-reject-policy {
                    description "Enter the ebgp-default-reject-policy context";

                    leaf import {
                        type boolean;
                        default "true";
                        description "Enable default reject import policy for external peers";
                    }

                    leaf export {
                        type boolean;
                        default "true";
                        description "Enable default reject export policy for external peers";
                    }

                } // container ebgp-default-reject-policy

                container local-as {
                    description "Enter the local-as context";

                    leaf as-number {
                        type uint32 {
                            range "1..4294967295";
                        }
                        description "Local (or virtual) BGP AS number";
                    }

                    leaf private {
                        type boolean;
                        default "false";
                        description "Hide the local ASN in sent paths learned from peering";
                    }

                    leaf prepend-global-as {
                        type boolean;
                        default "true";
                        description "Prepend global AS when advertising routes to BGP peer";
                    }

                } // container local-as

                container best-path-selection {
                    description "Enter the best-path-selection context";

                    leaf compare-origin-validation-state {
                        type boolean;
                        default "false";
                        description "Specifies whether the origin validation state is used in the BGP decision process.";
                    }

                    leaf deterministic-med {
                        type boolean;
                        default "false";
                        description "Group paths based on AS before MED attribute comparison";
                    }

                    leaf origin-invalid-unusable {
                        type boolean;
                        default "false";
                        description "Specifies whether to use or ignore the routes that have an origin validation state of 'Invalid'.";
                    }

                    leaf ignore-nh-metric {
                        type boolean;
                        default "false";
                        description "Ignore next-hop distance in best path selection";
                    }

                    container always-compare-med {
                        description "Enter the always-compare-med context";

                        leaf med-value {
                            type types-bgp:med-value;
                            default "off";
                            description "Action for a missing MED attribute";
                        }

                        leaf strict-as {
                            type boolean;
                            default "true";
                            description "Compare MED attribute from same-neighbor AS routes only";
                        }

                    } // container always-compare-med

                    container as-path-ignore {
                        description "Enter the as-path-ignore context";

                        leaf ipv4 {
                            type boolean;
                            default "false";
                            description "Ignore AS path length for unlabeled unicast IPv4 routes";
                        }

                        leaf ipv6 {
                            type boolean;
                            default "false";
                            description "Ignore AS path length for unlabeled unicast IPv6 routes";
                        }

                        leaf label-ipv4 {
                            type boolean;
                            default "false";
                            description "Ignore AS path length for labeled-unicast IPv4 routes";
                        }

                    } // container as-path-ignore

                    container ignore-router-id {
                        presence
                            "Specifies whether to ignore the BGP identifier (router-ID)
                             comparison when comparing two paths learned from different
                             EBGP neighbors as long as both paths are not from a
                             configured-BGP peer.";
                        description "Enter the ignore-router-id context";

                    } // container ignore-router-id

                    container ebgp-ibgp-equal {
                        description "Enter the ebgp-ibgp-equal context";

                        leaf ipv4 {
                            type boolean;
                            default "false";
                            description "Consider EBGP and IBGP IPv4 routes equal";
                        }

                        leaf ipv6 {
                            type boolean;
                            default "false";
                            description "Consider EBGP and IBGP IPv6 routes equal";
                        }

                        leaf label-ipv4 {
                            type boolean;
                            default "false";
                            description "Consider EBGP and IBGP label-IPv4 routes equal";
                        }

                    } // container ebgp-ibgp-equal

                } // container best-path-selection

                container send-communities {
                    description "Enter the send-communities context";

                    leaf standard {
                        type boolean;
                        default "true";
                        description "Advertise the Communities attribute to peers";
                    }

                    leaf extended {
                        type boolean;
                        default "true";
                        description "Advertise the Extended Communities attribute to peers";
                    }

                    leaf large {
                        type boolean;
                        default "true";
                        description "Advertise the Large Communities attribute to peers";
                    }

                } // container send-communities

                container error-handling {
                    description "Enter the error-handling context";

                    leaf update-fault-tolerance {
                        type boolean;
                        default "false";
                        description "Tolerate non-critical errors in UPDATE messages";
                    }

                } // container error-handling

                container damp-peer-oscillations {
                    presence "Timers settings for damp-peer-oscillation";
                    description "Enter the damp-peer-oscillations context";

                    leaf error-interval {
                        type uint32 {
                            range "0..2048";
                        }
                        default "30";
                        description "Time after a reset that the session must be error-free";
                    }

                    container idle-hold-time {
                        description "Enter the idle-hold-time context";

                        leaf initial-wait {
                            type uint32 {
                                range "0..2048";
                            }
                            default "0";
                            description "Time session remains in idle state after stabilization";
                        }

                        leaf second-wait {
                            type uint32 {
                                range "1..2048";
                            }
                            default "5";
                            description "Time that doubles after each session failure";
                        }

                        leaf max-wait {
                            type uint32 {
                                range "1..2048";
                            }
                            default "60";
                            description "Maximum session idle time after repeated instability";
                        }

                    } // container idle-hold-time

                } // container damp-peer-oscillations

                container backup-path {
                    description "Enter the backup-path context";

                    leaf ipv4 {
                        type boolean;
                        default "false";
                        description "Enable support for unlabeled unicast IPv4 routes";
                    }

                    leaf ipv6 {
                        type boolean;
                        default "false";
                        description "Enable support for unlabeled unicast IPv6 routes";
                    }

                    leaf label-ipv4 {
                        type boolean;
                        default "false";
                        description "Enable support for labeled-unicast IPv4 routes";
                    }

                } // container backup-path

                container flowspec {
                    description "Enter the flowspec context";

                    leaf validate-dest-prefix {
                        type boolean;
                        default "false";
                        description "Validate destination prefix in FlowSpec-IPv4/IPv6 route";
                    }

                    leaf validate-redirect-ip {
                        type boolean;
                        default "false";
                        description "Validate the redirect-to-IPv4 action in FlowSpec route";
                    }

                } // container flowspec

                container convergence {
                    description "Enter the convergence context";

                    leaf min-wait-to-advertise {
                        type uint32 {
                            range "0..3600";
                        }
                        default "0";
                        description "Minimum wait time before advertising routes";
                    }

                    list family {
                        key "family-type";
                        description "Enter the family list instance";

                        leaf family-type {
                            type enumeration {
                                enum "ipv4"                         { value 1; }
                                enum "ipv6"                         { value 3; }
                            }
                            description "Address family for which convergence selection applies";
                        }

                        leaf max-wait-to-advertise {
                            type uint32 {
                                range "0..3600";
                            }
                            default "0";
                            description "Maximum wait time before advertising routes";
                        }

                        leaf-list apply-groups {
                            type leafref {
                                path "../../../../../../groups/group/name";
                            }
                            max-elements 8;
                            ordered-by user;
                            description "Apply a configuration group at this level";
                        }

                    } // list family

                } // container convergence

                container import {
                    presence "Enables bgp import polices at the instance level";
                    description "Enter the import context";

                    leaf-list policy {
                        type string {
                            length "1..255";
                            pattern "(.{1,64})|(.*[\\[].*)" {
                                error-message "Policy name too long or expression not valid";
                            }
                        }
                        min-elements 1;
                        max-elements 15;
                        ordered-by user;
                        description "Import policy name";
                    }

                    leaf-list apply-groups {
                        type leafref {
                            path "../../../../../groups/group/name";
                        }
                        max-elements 8;
                        ordered-by user;
                        description "Apply a configuration group at this level";
                    }

                } // container import

                container export {
                    presence "Enables bgp export polices at the instance level";
                    description "Enter the export context";

                    leaf-list policy {
                        type string {
                            length "1..255";
                            pattern "(.{1,64})|(.*[\\[].*)" {
                                error-message "Policy name too long or expression not valid";
                            }
                        }
                        min-elements 1;
                        max-elements 15;
                        ordered-by user;
                        description "Export policy name";
                    }

                    leaf-list apply-groups {
                        type leafref {
                            path "../../../../../groups/group/name";
                        }
                        max-elements 8;
                        ordered-by user;
                        description "Apply a configuration group at this level";
                    }

                } // container export

                container extended-nh-encoding {
                    description "Enter the extended-nh-encoding context";

                    leaf ipv4 {
                        type boolean;
                        default "false";
                        description "Enable/disable family type ipv4.";
                    }

                } // container extended-nh-encoding

                container advertise-ipv6-next-hops {
                    description "Enter the advertise-ipv6-next-hops context";

                    leaf ipv4 {
                        type boolean;
                        default "false";
                        description "Enable/disable family type ipv4.";
                    }

                } // container advertise-ipv6-next-hops

                container graceful-restart {
                    presence "Enable/disable graceful-restart for BGP process.";
                    description "Enter the graceful-restart context";

                    leaf restart-time {
                        type uint32 {
                            range "0..4095";
                        }
                        default "120";
                        description "Restart time advertised by GR capability";
                    }

                    leaf stale-routes-time {
                        type uint32 {
                            range "1..3600";
                        }
                        default "360";
                        description "Maximum time to maintain routes after graceful restart";
                    }

                    leaf gr-notification {
                        type boolean;
                        default "false";
                        description "Perform Graceful Restart procedures";
                    }

                    container long-lived {
                        presence "Long Lived Graceful restart attributes for BGP process.";
                        description "Enter the long-lived context";

                        leaf advertised-stale-time {
                            type uint32 {
                                range "0..16777215";
                            }
                            default "86400";
                            description "LLGR stale routes time";
                        }

                        leaf helper-override-stale-time {
                            type uint32 {
                                range "0..16777215";
                            }
                            description "Locally-configured stale routes override time";
                        }

                        leaf helper-override-restart-time {
                            type uint32 {
                                range "0..4095";
                            }
                            description "Locally-configured override for restart time";
                        }

                        leaf forwarding-bits-set {
                            type enumeration {
                                enum "none"                         { value 0; }
                                enum "all"                          { value 1; }
                                enum "non-fwd"                      { value 2; }
                            }
                            default "none";
                            description "BGP LLGR forwarding-bit behavior for address family";
                        }

                        leaf advertise-stale-to-all-neighbors {
                            type boolean;
                            default "false";
                            description "Advertise stale routes to all BGP peers";
                        }

                        leaf without-no-export {
                            type boolean;
                            default "false";
                            description "Advertise LLGR stale routes to non-LLGR peers";
                        }

                        list family {
                            key "family-type";
                            description "Enter the family list instance";

                            leaf family-type {
                                type types-bgp:vprn-bgp-llgr-family-identifiers;
                                description "Address family type for LLGR";
                            }

                            leaf advertised-stale-time {
                                type uint32 {
                                    range "0..16777215";
                                }
                                default "86400";
                                description "LLGR stale routes time for family override";
                            }

                            leaf helper-override-stale-time {
                                type uint32 {
                                    range "0..16777215";
                                }
                                description "Locally-configured stale routes override time";
                            }

                            leaf-list apply-groups {
                                type leafref {
                                    path "../../../../../../../groups/group/name";
                                }
                                max-elements 8;
                                ordered-by user;
                                description "Apply a configuration group at this level";
                            }

                        } // list family

                    } // container long-lived

                } // container graceful-restart

                container next-hop-resolution {
                    description "Enter the next-hop-resolution context";

                    leaf use-bgp-routes {
                        type boolean;
                        default "false";
                        description "Enable/Disable using BGP routes to resolve BGP nexthop.";
                    }

                    leaf policy {
                        type types-sros:named-item-64;
                        description "Policy that filters routes for BGP next-hop resolution";
                    }

                } // container next-hop-resolution

                container multipath {
                    description "Enter the multipath context";

                    leaf max-paths {
                        type types-router:ip-ecmp;
                        default "1";
                        description "Maximum multipaths per prefix";
                    }

                    leaf ebgp {
                        type types-router:ip-ecmp;
                        description "Maximum multipaths per prefix for EBGP learned routes";
                    }

                    leaf ibgp {
                        type types-router:ip-ecmp;
                        description "Maximum multipaths per prefix for IBGP learned routes";
                    }

                    leaf restrict {
                        type types-bgp:restrict;
                        default "same-as-path-length";
                        description "AS path restriction for the non-best path";
                    }

                    leaf unequal-cost {
                        type boolean;
                        default "false";
                        description "Ignore differences in the next-hop cost for multipath";
                    }

                    list family {
                        key "family-type";
                        description "Enter the family list instance";

                        leaf family-type {
                            type enumeration {
                                enum "ipv4"                         { value 1; }
                                enum "ipv6"                         { value 3; }
                                enum "label-ipv4"                   { value 17; }
                            }
                            description "Address family for which multipath selection applies";
                        }

                        leaf max-paths {
                            type types-router:ip-ecmp;
                            description "Maximum multipaths per prefix or NLRI";
                        }

                        leaf ebgp {
                            type types-router:ip-ecmp;
                            description "Attribute ebgp-max-paths for multipath.";
                        }

                        leaf ibgp {
                            type types-router:ip-ecmp;
                            description "Attribute ibgp-max-paths for multipath.";
                        }

                        leaf restrict {
                            type types-bgp:restrict;
                            default "same-as-path-length";
                            description "AS path restriction for the non-best path";
                        }

                        leaf unequal-cost {
                            type boolean;
                            default "false";
                            description "Ignore differences in the next-hop cost for multipath";
                        }

                        leaf-list apply-groups {
                            type leafref {
                                path "../../../../../../groups/group/name";
                            }
                            max-elements 8;
                            ordered-by user;
                            description "Apply a configuration group at this level";
                        }

                    } // list family

                } // container multipath

                container monitor {
                    presence "Contains all the BMP related configuration for a bgp-instance.";
                    description "Enter the monitor context";

                    leaf all-stations {
                        type boolean;
                        default "false";
                        description "Send BMP messages to all configured stations";
                    }

                    leaf admin-state {
                        type types-sros:admin-state;
                        default "disable";
                        description "Administrative state of BMP monitoring";
                    }

                    leaf-list apply-groups {
                        type leafref {
                            path "../../../../../groups/group/name";
                        }
                        max-elements 8;
                        ordered-by user;
                        description "Apply a configuration group at this level";
                    }

                    container route-monitoring {
                        description "Enter the route-monitoring context";

                        leaf pre-policy {
                            type boolean;
                            default "false";
                            description "Allow pre-policy route-monitoring messages to be sent";
                        }

                        leaf post-policy {
                            type boolean;
                            default "false";
                            description "Allow post-policy route-monitoring messages to be sent";
                        }

                    } // container route-monitoring

                    list station {
                        key "station-name";
                        max-elements 8;
                        description "Add a list entry for station";

                        leaf station-name {
                            type leafref {
                                path "../../../../../../bmp/station/name";
                            }
                            description "BMP monitoring station";
                        }

                    } // list station

                } // container monitor

                container rib-management {
                    description "Enter the rib-management context";

                    container ipv4 {
                        description "Enter the ipv4 context";

                        container route-table-import {
                            description "Enter the route-table-import context";

                            leaf policy-name {
                                type types-sros:named-item-64;
                                description "Name of policy that controls route importation into RIB";
                            }

                            leaf-list apply-groups {
                                type leafref {
                                    path "../../../../../../../groups/group/name";
                                }
                                max-elements 8;
                                ordered-by user;
                                description "Apply a configuration group at this level";
                            }

                        } // container route-table-import

                        container leak-import {
                            description "Enter the leak-import context";

                            leaf-list policy {
                                type string {
                                    length "1..255";
                                    pattern "(.{1,64})|(.*[\\[].*)" {
                                        error-message "Policy name too long or expression not valid";
                                    }
                                }
                                max-elements 15;
                                ordered-by user;
                                description "Leak import policy name";
                            }

                            leaf-list apply-groups {
                                type leafref {
                                    path "../../../../../../../groups/group/name";
                                }
                                max-elements 8;
                                ordered-by user;
                                description "Apply a configuration group at this level";
                            }

                        } // container leak-import

                    } // container ipv4

                    container ipv6 {
                        description "Enter the ipv6 context";

                        container route-table-import {
                            description "Enter the route-table-import context";

                            leaf policy-name {
                                type types-sros:named-item-64;
                                description "Name of policy that controls route importation into RIB";
                            }

                            leaf-list apply-groups {
                                type leafref {
                                    path "../../../../../../../groups/group/name";
                                }
                                max-elements 8;
                                ordered-by user;
                                description "Apply a configuration group at this level";
                            }

                        } // container route-table-import

                        container leak-import {
                            description "Enter the leak-import context";

                            leaf-list policy {
                                type string {
                                    length "1..255";
                                    pattern "(.{1,64})|(.*[\\[].*)" {
                                        error-message "Policy name too long or expression not valid";
                                    }
                                }
                                max-elements 15;
                                ordered-by user;
                                description "Leak import policy name";
                            }

                            leaf-list apply-groups {
                                type leafref {
                                    path "../../../../../../../groups/group/name";
                                }
                                max-elements 8;
                                ordered-by user;
                                description "Apply a configuration group at this level";
                            }

                        } // container leak-import

                    } // container ipv6

                    container label-ipv4 {
                        description "Enter the label-ipv4 context";

                        container route-table-import {
                            description "Enter the route-table-import context";

                            leaf policy-name {
                                type types-sros:named-item-64;
                                description "Name of policy that controls route importation into RIB";
                            }

                            leaf-list apply-groups {
                                type leafref {
                                    path "../../../../../../../groups/group/name";
                                }
                                max-elements 8;
                                ordered-by user;
                                description "Apply a configuration group at this level";
                            }

                        } // container route-table-import

                        container leak-import {
                            description "Enter the leak-import context";

                            leaf-list policy {
                                type string {
                                    length "1..255";
                                    pattern "(.{1,64})|(.*[\\[].*)" {
                                        error-message "Policy name too long or expression not valid";
                                    }
                                }
                                max-elements 15;
                                ordered-by user;
                                description "Leak import policy name";
                            }

                            leaf-list apply-groups {
                                type leafref {
                                    path "../../../../../../../groups/group/name";
                                }
                                max-elements 8;
                                ordered-by user;
                                description "Apply a configuration group at this level";
                            }

                        } // container leak-import

                    } // container label-ipv4

                } // container rib-management

                list group {
                    key "group-name";
                    description "Enter the group list instance";

                    leaf group-name {
                        type types-sros:named-item-64;
                        description "BGP peer group";
                    }

                    leaf description {
                        type types-sros:description;
                        description "Text description";
                    }

                    leaf connect-retry {
                        type int32 {
                            range "1..65535";
                        }
                        description "BGP connect retry timer value";
                    }

                    leaf admin-state {
                        type types-sros:admin-state;
                        default "enable";
                        description "Administrative state of the BGP group";
                    }

                    leaf static-group {
                        type boolean;
                        default "true";
                        description "Use group for static peers";
                    }

                    leaf keepalive {
                        type int32 {
                            range "0..21845";
                        }
                        description "Time after which the BGP KEEPALIVE message is sent";
                    }

                    leaf damping {
                        type boolean;
                        description "Use BGP route damping to reduce route flap";
                    }

                    leaf local-preference {
                        type int64 {
                            range "0..4294967295";
                        }
                        description "Default local preference if not in incoming routes";
                    }

                    leaf loop-detect {
                        type types-bgp:loop-detect;
                        description "Strategy for loop detection in the AS path";
                    }

                    leaf loop-detect-threshold {
                        type uint32 {
                            range "0..15";
                        }
                        description "Threshold for the global ASN in a received AS path";
                    }

                    leaf min-route-advertisement {
                        type int16 {
                            range "1..255";
                        }
                        description "Minimum time before a prefix can be advertised to peer";
                    }

                    leaf aggregator-id-zero {
                        type boolean;
                        description "Set router ID in the BGP AGGREGATOR attribute to zero";
                    }

                    leaf preference {
                        type uint32 {
                            range "1..255";
                        }
                        description "Route preference for routes learned from all peers";
                    }

                    leaf multihop {
                        type int32 {
                            range "1..255";
                        }
                        description "TTL in IP packet headers for EBGP peers multi-hops away";
                    }

                    leaf med-out {
                        type union {
                            type uint32;
                            type enumeration {
                                enum "igp-cost"                     { value -1; }
                            }
                        }
                        description "Default MED attribute value to advertise to peers";
                    }

                    leaf authentication-key {
                        type types-sros:encrypted-leaf {
                            length "1..370";
                        }
                        description "BGP authentication key for all peers";
                    }

                    leaf client-reflect {
                        type boolean;
                        description "Allow cluster RR to advertise routes to its clients";
                    }

                    leaf as-override {
                        type boolean;
                        default "false";
                        description "Replace the peer's ASN with the local ASN in AS Path";
                    }

                    leaf asn-4-byte {
                        type boolean;
                        description "Advertise the use of 4-byte ASNs";
                    }

                    leaf path-mtu-discovery {
                        type boolean;
                        description "Enable Path MTU Discovery";
                    }

                    leaf next-hop-self {
                        type boolean;
                        default "false";
                        description "Advertise routes with local address as next-hop address";
                    }

                    leaf passive {
                        type boolean;
                        default "false";
                        description "Enable passive mode for BGP communication";
                    }

                    leaf type {
                        type types-bgp:peer-type;
                        default "no-type";
                        description "BGP peer type";
                    }

                    leaf peer-as {
                        type uint32 {
                            range "1..4294967295";
                        }
                        description "Peer AS number";
                    }

                    leaf capability-negotiation {
                        type boolean;
                        default "true";
                        description "Enable capability negotiation";
                    }

                    leaf enforce-first-as {
                        type boolean;
                        description "Enforce the configured peer AS value in received routes";
                    }

                    leaf initial-send-delay-zero {
                        type boolean;
                        description "Send BGP updates as soon as the session comes up";
                    }

                    leaf local-address {
                        type types-bgp:local-address;
                        description "Local IP address used when communicating with BGP peers";
                    }

                    leaf ttl-security {
                        type uint32 {
                            range "1..255";
                        }
                        description "Minimum TTL value for an incoming BGP packet";
                    }

                    leaf advertise-inactive {
                        type boolean;
                        description "Advertise an inactive BGP route to peers";
                    }

                    leaf authentication-keychain {
                        type leafref {
                            path "../../../../../system/security/keychains/keychain/keychain-name";
                        }
                        description "TCP authentication keychain for the session";
                    }

                    leaf bfd-liveness {
                        type boolean;
                        description "Enable BFD";
                    }

                    leaf fast-external-failover {
                        type boolean;
                        description "Drop external BGP session immediately when link fails";
                    }

                    leaf peer-ip-tracking {
                        type boolean;
                        description "Enable BGP peer tracking";
                    }

                    leaf dynamic-neighbor-limit {
                        type uint32 {
                            range "1..8192";
                        }
                        description "Maximum dynamic BGP sessions to accept from remote peer";
                    }

                    leaf split-horizon {
                        type boolean;
                        description "Prevent routes being reflected back to best-route peer";
                    }

                    leaf third-party-nexthop {
                        type boolean;
                        description "Apply third-party next-hop processing to EBGP peers";
                    }

                    leaf label-preference {
                        type uint32 {
                            range "1..255";
                        }
                        description "Route preference for routes from labeled-unicast peers";
                    }

                    leaf multipath-eligible {
                        type boolean;
                        default "false";
                        description "Allow routes from group peers in multipath eligibility";
                    }

                    leaf-list apply-groups {
                        type leafref {
                            path "../../../../../groups/group/name";
                        }
                        max-elements 8;
                        ordered-by user;
                        description "Apply a configuration group at this level";
                    }

                    container hold-time {
                        description "Enter the hold-time context";

                        leaf seconds {
                            type int32 {
                                range "0|3..65535";
                            }
                            description "Maximum time BGP waits between successive messages";
                        }

                        leaf minimum-hold-time {
                            type int32 {
                                range "0|3..65536";
                            }
                            default "0";
                            description "Minimum hold time between successive messages";
                        }

                    } // container hold-time

                    container family {
                        presence "Configure family for BGP";
                        description "Enter the family context";

                        leaf ipv4 {
                            type boolean;
                            default "false";
                            description "Add support for the IPv4 address family";
                        }

                        leaf ipv6 {
                            type boolean;
                            default "false";
                            description "Add support for the IPv6 address family";
                        }

                        leaf mcast-ipv4 {
                            type boolean;
                            default "false";
                            description "Add support for the MCAST-IPv4 address family";
                        }

                        leaf flow-ipv4 {
                            type boolean;
                            default "false";
                            description "Add support for the flowspec-IPv4 address family";
                        }

                        leaf flow-ipv6 {
                            type boolean;
                            default "false";
                            description "Add support for the flowspec-IPv6 address family";
                        }

                        leaf mcast-ipv6 {
                            type boolean;
                            default "false";
                            description "Add support for the MCAST-IPv6 address family";
                        }

                        leaf label-ipv4 {
                            type boolean;
                            default "false";
                            description "Add support for the label-IPv4 address family";
                        }

                    } // container family

                    container send-default {
                        presence "Configure send-default and export policy.";
                        description "Enter the send-default context";

                        leaf ipv4 {
                            type boolean;
                            default "false";
                            description "Enable/disable family type ipv4.";
                        }

                        leaf ipv6 {
                            type boolean;
                            default "false";
                            description "Enable IPv6 family type";
                        }

                        leaf export-policy {
                            type types-sros:named-item-64;
                            description "Export policy name";
                        }

                    } // container send-default

                    container default-preference {
                        description "Enter the default-preference context";

                        leaf ebgp {
                            type uint32 {
                                range "0..255";
                            }
                            description "Default preference for EBGP";
                        }

                        leaf ibgp {
                            type uint32 {
                                range "0..255";
                            }
                            description "Default preference for IBGP";
                        }

                    } // container default-preference

                    container default-label-preference {
                        description "Enter the default-label-preference context";

                        leaf ebgp {
                            type uint32 {
                                range "0..255";
                            }
                            description "Default preference for EBGP";
                        }

                        leaf ibgp {
                            type uint32 {
                                range "0..255";
                            }
                            description "Default preference for IBGP";
                        }

                    } // container default-label-preference

                    container remove-private {
                        presence "Remove private AS numbers from the AS Path before advertising to a peer";
                        description "Enter the remove-private context";

                        leaf limited {
                            type boolean;
                            default "false";
                            description "Remove private ASNs up to first public ASN encountered";
                        }

                        leaf skip-peer-as {
                            type boolean;
                            default "false";
                            description "Keep private ASN if it is the same as the BGP peer ASN";
                        }

                        leaf replace {
                            type boolean;
                            default "false";
                            description "Replace private ASN with global ASN before advertising";
                        }

                    } // container remove-private

                    container cluster {
                        description "Enter the cluster context";

                        leaf cluster-id {
                            type types-sros:ipv4-address;
                            description "Route reflector cluster ID";
                        }

                    } // container cluster

                    container ebgp-default-reject-policy {
                        presence "Configure default reject behavior for BGP";
                        description "Enter the ebgp-default-reject-policy context";

                        leaf import {
                            type boolean;
                            default "true";
                            description "Enable default reject import policy for external peers";
                        }

                        leaf export {
                            type boolean;
                            default "true";
                            description "Enable default reject export policy for external peers";
                        }

                    } // container ebgp-default-reject-policy

                    container local-as {
                        description "Enter the local-as context";

                        leaf as-number {
                            type uint32 {
                                range "1..4294967295";
                            }
                            description "Local (or virtual) BGP AS number";
                        }

                        leaf private {
                            type boolean;
                            default "false";
                            description "Hide the local ASN in sent paths learned from peering";
                        }

                        leaf prepend-global-as {
                            type boolean;
                            default "true";
                            description "Prepend global ASN when advertising routes to BGP peer";
                        }

                    } // container local-as

                    container origin-validation {
                        description "Enter the origin-validation context";

                        leaf ipv4 {
                            type boolean;
                            default "false";
                            description "Enable/disable family type ipv4.";
                        }

                        leaf ipv6 {
                            type boolean;
                            default "false";
                            description "Enable support for unlabeled unicast IPv6 routes";
                        }

                        leaf label-ipv4 {
                            type boolean;
                            default "false";
                            description "Enable support for labeled-unicast IPv4 routes";
                        }

                    } // container origin-validation

                    container link-bandwidth {
                        description "Enter the link-bandwidth context";

                        container accept-from-ebgp {
                            description "Enter the accept-from-ebgp context";

                            leaf ipv4 {
                                type boolean;
                                default "false";
                                description "Support Link Bandwidth EC in IPv4 routes";
                            }

                            leaf ipv6 {
                                type boolean;
                                default "false";
                                description "Support Link Bandwidth EC in IPv6 routes";
                            }

                            leaf label-ipv4 {
                                type boolean;
                                default "false";
                                description "Support Link Bandwidth EC in label-IPv4 routes";
                            }

                        } // container accept-from-ebgp

                        container add-to-received-ebgp {
                            description "Enter the add-to-received-ebgp context";

                            leaf ipv4 {
                                type boolean;
                                default "false";
                                description "Support Link Bandwidth EC in IPv4 routes";
                            }

                            leaf ipv6 {
                                type boolean;
                                default "false";
                                description "Support Link Bandwidth EC in IPv6 routes";
                            }

                            leaf label-ipv4 {
                                type boolean;
                                default "false";
                                description "Support Link Bandwidth EC in label-IPv4 routes";
                            }

                        } // container add-to-received-ebgp

                        container aggregate-used-paths {
                            description "Enter the aggregate-used-paths context";

                            leaf ipv4 {
                                type boolean;
                                default "false";
                                description "Support Link Bandwidth EC in IPv4 routes";
                            }

                            leaf ipv6 {
                                type boolean;
                                default "false";
                                description "Support Link Bandwidth EC in IPv6 routes";
                            }

                            leaf label-ipv4 {
                                type boolean;
                                default "false";
                                description "Support Link Bandwidth EC in label-IPv4 routes";
                            }

                        } // container aggregate-used-paths

                        container send-to-ebgp {
                            description "Enter the send-to-ebgp context";

                            leaf ipv4 {
                                type boolean;
                                default "false";
                                description "Support Link Bandwidth EC in IPv4 routes";
                            }

                            leaf ipv6 {
                                type boolean;
                                default "false";
                                description "Support Link Bandwidth EC in IPv6 routes";
                            }

                            leaf label-ipv4 {
                                type boolean;
                                default "false";
                                description "Support Link Bandwidth EC in label-IPv4 routes";
                            }

                        } // container send-to-ebgp

                    } // container link-bandwidth

                    container send-communities {
                        description "Enter the send-communities context";

                        leaf standard {
                            type boolean;
                            description "Advertise the Communities attribute to peers";
                        }

                        leaf extended {
                            type boolean;
                            description "Advertise the Extended Communities attribute to peers";
                        }

                        leaf large {
                            type boolean;
                            description "Advertise the Large Communities attribute to peers";
                        }

                    } // container send-communities

                    container error-handling {
                        description "Enter the error-handling context";

                        leaf update-fault-tolerance {
                            type boolean;
                            description "Tolerate non-critical errors in UPDATE messages";
                        }

                    } // container error-handling

                    container damp-peer-oscillations {
                        presence "Timers settings for damp-peer-oscillation";
                        description "Enter the damp-peer-oscillations context";

                        leaf error-interval {
                            type uint32 {
                                range "0..2048";
                            }
                            default "30";
                            description "Time after a reset that the session must be error-free";
                        }

                        container idle-hold-time {
                            description "Enter the idle-hold-time context";

                            leaf initial-wait {
                                type uint32 {
                                    range "0..2048";
                                }
                                default "0";
                                description "Time session remains in idle state after stabilization";
                            }

                            leaf second-wait {
                                type uint32 {
                                    range "1..2048";
                                }
                                default "5";
                                description "Time that doubles after each repeated session failure";
                            }

                            leaf max-wait {
                                type uint32 {
                                    range "1..2048";
                                }
                                default "60";
                                description "Maximum session idle time after repeated instability";
                            }

                        } // container idle-hold-time

                    } // container damp-peer-oscillations

                    container import {
                        presence "Enables bgp import polices at the group level";
                        description "Enter the import context";

                        leaf-list policy {
                            type string {
                                length "1..255";
                                pattern "(.{1,64})|(.*[\\[].*)" {
                                    error-message "Policy name too long or expression not valid";
                                }
                            }
                            min-elements 1;
                            max-elements 15;
                            ordered-by user;
                            description "Specifies the name of the import policy. The name of the policy is limited to 64 characters except for the first policy.";
                        }

                        leaf-list apply-groups {
                            type leafref {
                                path "../../../../../../groups/group/name";
                            }
                            max-elements 8;
                            ordered-by user;
                            description "Apply a configuration group at this level";
                        }

                    } // container import

                    container export {
                        presence "Enables bgp export polices at the group level";
                        description "Enter the export context";

                        leaf-list policy {
                            type string {
                                length "1..255";
                                pattern "(.{1,64})|(.*[\\[].*)" {
                                    error-message "Policy name too long or expression not valid";
                                }
                            }
                            min-elements 1;
                            max-elements 15;
                            ordered-by user;
                            description "Export policy name";
                        }

                        leaf-list apply-groups {
                            type leafref {
                                path "../../../../../../groups/group/name";
                            }
                            max-elements 8;
                            ordered-by user;
                            description "Apply a configuration group at this level";
                        }

                    } // container export

                    container extended-nh-encoding {
                        presence
                            "families the Bgp instance is configured
                             to support extended next-hop encoding.";
                        description "Enter the extended-nh-encoding context";

                        leaf ipv4 {
                            type boolean;
                            default "false";
                            description "Enable/disable family type ipv4.";
                        }

                    } // container extended-nh-encoding

                    container advertise-ipv6-next-hops {
                        presence "families extended next-hop encoding is supported for.";
                        description "Enter the advertise-ipv6-next-hops context";

                        leaf ipv4 {
                            type boolean;
                            default "false";
                            description "Enable/disable family type ipv4.";
                        }

                    } // container advertise-ipv6-next-hops

                    container graceful-restart {
                        presence "Enable/disable graceful-restart for all BGP group.";
                        description "Enter the graceful-restart context";

                        leaf restart-time {
                            type uint32 {
                                range "0..4095";
                            }
                            default "300";
                            description "Restart time advertised by GR capability";
                        }

                        leaf stale-routes-time {
                            type uint32 {
                                range "1..3600";
                            }
                            default "360";
                            description "Maximum time to maintain routes after graceful restart";
                        }

                        leaf gr-notification {
                            type boolean;
                            default "false";
                            description "Perform graceful restart procedures after NOTIFICATION";
                        }

                        container long-lived {
                            presence "Long Lived Graceful restart attributes for all BGP group.";
                            description "Enter the long-lived context";

                            leaf advertised-stale-time {
                                type uint32 {
                                    range "0..16777215";
                                }
                                default "86400";
                                description "Advertised long-lived stale time for LLGR routes";
                            }

                            leaf helper-override-stale-time {
                                type uint32 {
                                    range "0..16777215";
                                }
                                description "Locally-configured stale routes override time";
                            }

                            leaf helper-override-restart-time {
                                type uint32 {
                                    range "0..4095";
                                }
                                description "Locally-configured override for restart time";
                            }

                            leaf forwarding-bits-set {
                                type enumeration {
                                    enum "none"                         { value 0; }
                                    enum "all"                          { value 1; }
                                    enum "non-fwd"                      { value 2; }
                                }
                                default "none";
                                description "BGP LLGR forwarding-bit behavior for address family";
                            }

                            leaf advertise-stale-to-all-neighbors {
                                type boolean;
                                default "false";
                                description "Advertise stale routes to all BGP peers";
                            }

                            leaf without-no-export {
                                type boolean;
                                default "false";
                                description "Advertise LLGR stale routes to non-LLGR peers";
                            }

                            list family {
                                key "family-type";
                                description "Enter the family list instance";

                                leaf family-type {
                                    type types-bgp:vprn-bgp-llgr-family-identifiers;
                                    description "Address family type for LLGR";
                                }

                                leaf advertised-stale-time {
                                    type uint32 {
                                        range "0..16777215";
                                    }
                                    default "86400";
                                    description "LLGR stale routes time for family override";
                                }

                                leaf helper-override-stale-time {
                                    type uint32 {
                                        range "0..16777216";
                                    }
                                    default "16777216";
                                    description "Locally-configured stale routes override time";
                                }

                                leaf-list apply-groups {
                                    type leafref {
                                        path "../../../../../../../../groups/group/name";
                                    }
                                    max-elements 8;
                                    ordered-by user;
                                    description "Apply a configuration group at this level";
                                }

                            } // list family

                        } // container long-lived

                    } // container graceful-restart

                    list prefix-limit {
                        key "family";
                        description "Enter the prefix-limit list instance";

                        leaf family {
                            type enumeration {
                                enum "ipv4"                         { value 1; }
                                enum "ipv6"                         { value 3; }
                                enum "mcast-ipv4"                   { value 4; }
                                enum "flow-ipv4"                    { value 10; }
                                enum "flow-ipv6"                    { value 14; }
                                enum "mcast-ipv6"                   { value 16; }
                                enum "label-ipv4"                   { value 17; }
                            }
                            description "Address family to which the limit applies";
                        }

                        leaf maximum {
                            type uint32 {
                                range "1..4294967295";
                            }
                            mandatory true;
                            description "Maximum number of routes to be learned from a peer";
                        }

                        leaf log-only {
                            type boolean;
                            default "false";
                            description "Send warning message at threshold instead of take-down";
                        }

                        leaf threshold {
                            type uint32 {
                                range "1..100";
                            }
                            default "90";
                            description "Percentage threshold that triggers a warning message";
                        }

                        leaf idle-timeout {
                            type int32 {
                                range "1..1024";
                            }
                            description "Time which BGP peering remains idle before reconnecting";
                        }

                        leaf post-import {
                            type boolean;
                            default "false";
                            description "Apply limit only to routes accepted by import policies";
                        }

                        leaf-list apply-groups {
                            type leafref {
                                path "../../../../../../groups/group/name";
                            }
                            max-elements 8;
                            ordered-by user;
                            description "Apply a configuration group at this level";
                        }

                    } // list prefix-limit

                    container dynamic-neighbor {
                        description "Enter the dynamic-neighbor context";

                        container match {
                            description "Enter the match context";

                            list prefix {
                                key "ip-prefix";
                                description "Enter the prefix list instance";

                                leaf ip-prefix {
                                    type types-sros:ip-prefix;
                                    description "Dynamic peer prefix for the group";
                                }

                                leaf-list allowed-peer-as {
                                    type string {
                                        pattern "(([1-9]|[1-9][0-9]{1,8}|[1-3][0-9]{9}|4[0-1][0-9]{8}|42[0-8][0-9]{7}|429[0-3][0-9]{6}|4294[0-8][0-9]{5}|42949[0-5][0-9]{4}|429496[0-6][0-9]{3}|4294967[0-1][0-9]{2}|42949672[0-8][0-9]|429496729[0-5]))|(([1-9]|[1-9][0-9]{1,8}|[1-3][0-9]{9}|4[0-1][0-9]{8}|42[0-8][0-9]{7}|429[0-3][0-9]{6}|4294[0-8][0-9]{5}|42949[0-5][0-9]{4}|429496[0-6][0-9]{3}|4294967[0-1][0-9]{2}|42949672[0-8][0-9]|429496729[0-5])\\.\\.([1-9]|[1-9][0-9]{1,8}|[1-3][0-9]{9}|4[0-1][0-9]{8}|42[0-8][0-9]{7}|429[0-3][0-9]{6}|4294[0-8][0-9]{5}|42949[0-5][0-9]{4}|429496[0-6][0-9]{3}|4294967[0-1][0-9]{2}|42949672[0-8][0-9]|429496729[0-5]))";
                                    }
                                    max-elements 32;
                                    ordered-by user;
                                    description "Allowed peer AS range";
                                }

                                leaf-list apply-groups {
                                    type leafref {
                                        path "../../../../../../../../groups/group/name";
                                    }
                                    max-elements 8;
                                    ordered-by user;
                                    description "Apply a configuration group at this level";
                                }

                            } // list prefix

                        } // container match

                    } // container dynamic-neighbor

                    container monitor {
                        presence "Contains all the BMP related configuration for a bgp-group.";
                        description "Enter the monitor context";

                        leaf all-stations {
                            type boolean;
                            default "false";
                            description "Send BMP messages to all configured stations";
                        }

                        leaf admin-state {
                            type types-sros:admin-state;
                            default "disable";
                            description "Administrative state of BMP monitoring";
                        }

                        leaf-list apply-groups {
                            type leafref {
                                path "../../../../../../groups/group/name";
                            }
                            max-elements 8;
                            ordered-by user;
                            description "Apply a configuration group at this level";
                        }

                        container route-monitoring {
                            description "Enter the route-monitoring context";

                            leaf pre-policy {
                                type boolean;
                                default "false";
                                description "Allow pre-policy route-monitoring messages to be sent";
                            }

                            leaf post-policy {
                                type boolean;
                                default "false";
                                description "Allow post-policy route-monitoring messages to be sent";
                            }

                        } // container route-monitoring

                        list station {
                            key "station-name";
                            max-elements 8;
                            description "Add a list entry for station";

                            leaf station-name {
                                type leafref {
                                    path "../../../../../../../bmp/station/name";
                                }
                                description "BMP monitoring station";
                            }

                        } // list station

                    } // container monitor

                } // list group

                list neighbor {
                    key "ip-address";
                    description "Enter the neighbor list instance";

                    leaf ip-address {
                        type types-sros:ip-address-with-zone;
                        description "IP address that the neighbor uses to communicate with BGP peers";
                    }

                    leaf ttl-security {
                        type uint32 {
                            range "1..255";
                        }
                        description "Minimum TTL value for an incoming BGP packet";
                    }

                    leaf advertise-inactive {
                        type boolean;
                        description "Advertise an inactive BGP route to peers";
                    }

                    leaf authentication-keychain {
                        type leafref {
                            path "../../../../../system/security/keychains/keychain/keychain-name";
                        }
                        description "TCP authentication keychain for the session";
                    }

                    leaf bfd-liveness {
                        type boolean;
                        description "Enable BFD";
                    }

                    leaf fast-external-failover {
                        type boolean;
                        description "Drop external BGP session immediately when link fails";
                    }

                    leaf peer-ip-tracking {
                        type boolean;
                        description "Enable BGP peer tracking";
                    }

                    leaf split-horizon {
                        type boolean;
                        description "Prevent routes being reflected back to best-route peer";
                    }

                    leaf third-party-nexthop {
                        type boolean;
                        description "Apply third-party next-hop processing to EBGP peers";
                    }

                    leaf label-preference {
                        type uint32 {
                            range "1..255";
                        }
                        description "Route preference for routes from labeled-unicast peers";
                    }

                    leaf multipath-eligible {
                        type boolean;
                        description "Allow routes from this peer in multipath eligibility";
                    }

                    leaf group {
                        type leafref {
                            path "../../group/group-name";
                        }
                        sros-ext:immutable;
                        mandatory true;
                        description "Neighbor to group";
                    }

                    leaf peer-creation-type {
                        type types-bgp:peer-creation-type;
                        default "static";
                        description "Peer creation type";
                    }

                    leaf connect-retry {
                        type int32 {
                            range "1..65535";
                        }
                        description "BGP connect retry timer value";
                    }

                    leaf description {
                        type types-sros:description;
                        description "Text description";
                    }

                    leaf admin-state {
                        type types-sros:admin-state;
                        default "enable";
                        description "Administrative state of the BGP neighbor";
                    }

                    leaf keepalive {
                        type int32 {
                            range "0..21845";
                        }
                        description "Time after which the BGP KEEPALIVE message is sent";
                    }

                    leaf damping {
                        type boolean;
                        description "Use BGP route damping to reduce route flap";
                    }

                    leaf local-preference {
                        type int64 {
                            range "0..4294967295";
                        }
                        description "Default local preference if not in incoming routes";
                    }

                    leaf loop-detect {
                        type types-bgp:loop-detect;
                        description "Strategy for loop detection in the AS path";
                    }

                    leaf loop-detect-threshold {
                        type uint32 {
                            range "0..15";
                        }
                        description "Threshold for the global ASN in a received AS path";
                    }

                    leaf min-route-advertisement {
                        type int16 {
                            range "1..255";
                        }
                        description "Minimum interval between successive prefix updates";
                    }

                    leaf aggregator-id-zero {
                        type boolean;
                        description "Set router ID in the BGP AGGREGATOR attribute to zero";
                    }

                    leaf preference {
                        type uint32 {
                            range "1..255";
                        }
                        description "Route preference for routes learned from all peers";
                    }

                    leaf multihop {
                        type int32 {
                            range "1..255";
                        }
                        description "TTL in IP packet headers for EBGP peers multi-hops away";
                    }

                    leaf med-out {
                        type union {
                            type uint32;
                            type enumeration {
                                enum "igp-cost"                     { value -1; }
                            }
                        }
                        description "Default MED attribute value to advertise to peers";
                    }

                    leaf authentication-key {
                        type types-sros:encrypted-leaf {
                            length "1..370";
                        }
                        description "BGP authentication key for all peers";
                    }

                    leaf client-reflect {
                        type boolean;
                        description "Allow cluster RR to advertise routes to its clients";
                    }

                    leaf as-override {
                        type boolean;
                        description "Replace the peer's ASN with the local ASN in AS Path";
                    }

                    leaf asn-4-byte {
                        type boolean;
                        description "Advertise the use of 4-byte ASNs";
                    }

                    leaf path-mtu-discovery {
                        type boolean;
                        description "Enable path MTU discovery";
                    }

                    leaf local-address {
                        type types-bgp:local-address;
                        description "Local IP address used when communicating with BGP peers";
                    }

                    leaf next-hop-self {
                        type boolean;
                        description "Advertise routes with local address as next-hop address";
                    }

                    leaf passive {
                        type boolean;
                        description "Use passive mode for BGP communication";
                    }

                    leaf type {
                        type types-bgp:peer-type;
                        description "BGP peer type";
                    }

                    leaf peer-as {
                        type uint32 {
                            range "1..4294967295";
                        }
                        description "Peer AS number";
                    }

                    leaf capability-negotiation {
                        type boolean;
                        description "Enable capability negotiation";
                    }

                    leaf enforce-first-as {
                        type boolean;
                        description "Enforce the configured peer AS value in received routes";
                    }

                    leaf initial-send-delay-zero {
                        type boolean;
                        description "Send BGP updates as soon as the session comes up";
                    }

                    leaf-list apply-groups {
                        type leafref {
                            path "../../../../../groups/group/name";
                        }
                        max-elements 8;
                        ordered-by user;
                        description "Apply a configuration group at this level";
                    }

                    container origin-validation {
                        presence "Configure origin-validation.";
                        description "Enter the origin-validation context";

                        leaf ipv4 {
                            type boolean;
                            default "false";
                            description "Enable/disable family type ipv4.";
                        }

                        leaf ipv6 {
                            type boolean;
                            default "false";
                            description "Enable support for unlabeled unicast IPv6 routes";
                        }

                        leaf label-ipv4 {
                            type boolean;
                            default "false";
                            description "Enable support for labeled-unicast IPv4 routes";
                        }

                    } // container origin-validation

                    container link-bandwidth {
                        description "Enter the link-bandwidth context";

                        container accept-from-ebgp {
                            presence
                                "Families for whom the Link Bandwidth extended community
                                 are allowed when a route is leared by a IBGP peer from a
                                 EBGP peer.";
                            description "Enter the accept-from-ebgp context";

                            leaf ipv4 {
                                type boolean;
                                default "false";
                                description "Support Link Bandwidth EC in IPv4 routes";
                            }

                            leaf ipv6 {
                                type boolean;
                                default "false";
                                description "Support Link Bandwidth EC in IPv6 routes";
                            }

                            leaf label-ipv4 {
                                type boolean;
                                default "false";
                                description "Support Link Bandwidth EC in label-IPv4 routes";
                            }

                        } // container accept-from-ebgp

                        container add-to-received-ebgp {
                            presence
                                "Adds link-bandwidth Extended Community to all the
                                 received EBGP multi-paths that is based on actual link speed.";
                            description "Enter the add-to-received-ebgp context";

                            leaf ipv4 {
                                type boolean;
                                default "false";
                                description "Support Link Bandwidth EC in IPv4 routes";
                            }

                            leaf ipv6 {
                                type boolean;
                                default "false";
                                description "Support Link Bandwidth EC in IPv6 routes";
                            }

                            leaf label-ipv4 {
                                type boolean;
                                default "false";
                                description "Support Link Bandwidth EC in label-IPv4 routes";
                            }

                        } // container add-to-received-ebgp

                        container aggregate-used-paths {
                            presence
                                "Families for whom the link-bandwidth sum accross all multipaths
                                 are advertised along with extended community.";
                            description "Enter the aggregate-used-paths context";

                            leaf ipv4 {
                                type boolean;
                                default "false";
                                description "Support Link Bandwidth EC in IPv4 routes";
                            }

                            leaf ipv6 {
                                type boolean;
                                default "false";
                                description "Support Link Bandwidth EC in IPv6 routes";
                            }

                            leaf label-ipv4 {
                                type boolean;
                                default "false";
                                description "Support Link Bandwidth EC in label-IPv4 routes";
                            }

                        } // container aggregate-used-paths

                        container send-to-ebgp {
                            presence
                                "Families for whom the Link Bandwidth extended community
                                 are allowed when a route is advertised by a IBGP peer to a
                                 EBGP peer.";
                            description "Enter the send-to-ebgp context";

                            leaf ipv4 {
                                type boolean;
                                default "false";
                                description "Support Link Bandwidth EC in IPv4 routes";
                            }

                            leaf ipv6 {
                                type boolean;
                                default "false";
                                description "Support Link Bandwidth EC in IPv6 routes";
                            }

                            leaf label-ipv4 {
                                type boolean;
                                default "false";
                                description "Support Link Bandwidth EC in label-IPv4 routes";
                            }

                        } // container send-to-ebgp

                    } // container link-bandwidth

                    container send-communities {
                        description "Enter the send-communities context";

                        leaf standard {
                            type boolean;
                            description "Advertise the Communities attribute to peers";
                        }

                        leaf extended {
                            type boolean;
                            description "Advertise the Extended Communities attribute to peers";
                        }

                        leaf large {
                            type boolean;
                            description "Advertise the Large Communities attribute to peers";
                        }

                    } // container send-communities

                    container error-handling {
                        description "Enter the error-handling context";

                        leaf update-fault-tolerance {
                            type boolean;
                            description "Tolerate non-critical errors in UPDATE messages";
                        }

                    } // container error-handling

                    container damp-peer-oscillations {
                        presence "Timers settings for damp-peer-oscillation";
                        description "Enter the damp-peer-oscillations context";

                        leaf error-interval {
                            type uint32 {
                                range "0..2048";
                            }
                            default "30";
                            description "Time after a reset that the session must be error-free";
                        }

                        container idle-hold-time {
                            description "Enter the idle-hold-time context";

                            leaf initial-wait {
                                type uint32 {
                                    range "0..2048";
                                }
                                default "0";
                                description "Time session remains in idle state after stabilization";
                            }

                            leaf second-wait {
                                type uint32 {
                                    range "1..2048";
                                }
                                default "5";
                                description "Time that doubles after each repeated session failure";
                            }

                            leaf max-wait {
                                type uint32 {
                                    range "1..2048";
                                }
                                default "60";
                                description "Maximum session idle time after repeated instability";
                            }

                        } // container idle-hold-time

                    } // container damp-peer-oscillations

                    container hold-time {
                        description "Enter the hold-time context";

                        leaf seconds {
                            type int32 {
                                range "0|3..65535";
                            }
                            description "BGP hold time";
                        }

                        leaf minimum-hold-time {
                            type int32 {
                                range "0|3..65536";
                            }
                            default "0";
                            description "Minimum hold time between successive messages";
                        }

                    } // container hold-time

                    container family {
                        presence "Configure family for BGP.";
                        description "Enter the family context";

                        leaf ipv4 {
                            type boolean;
                            default "false";
                            description "Add support for the IPv4 address family";
                        }

                        leaf ipv6 {
                            type boolean;
                            default "false";
                            description "Add support for the IPv6 address family";
                        }

                        leaf mcast-ipv4 {
                            type boolean;
                            default "false";
                            description "Add support for the MCAST-IPv4 address family";
                        }

                        leaf flow-ipv4 {
                            type boolean;
                            default "false";
                            description "Add support for the flowspec-IPv4 address family";
                        }

                        leaf flow-ipv6 {
                            type boolean;
                            default "false";
                            description "Add support for the flowspec-IPv6 address family";
                        }

                        leaf mcast-ipv6 {
                            type boolean;
                            default "false";
                            description "Add support for the MCAST-IPv6 address family";
                        }

                        leaf label-ipv4 {
                            type boolean;
                            default "false";
                            description "Add support for the label-IPv4 address family";
                        }

                    } // container family

                    container send-default {
                        presence "Configure send-default and export policy.";
                        description "Enter the send-default context";

                        leaf ipv4 {
                            type boolean;
                            default "false";
                            description "Enable IPv4 family type";
                        }

                        leaf ipv6 {
                            type boolean;
                            default "false";
                            description "Enable IPv6 family type";
                        }

                        leaf export-policy {
                            type types-sros:named-item-64;
                            description "Export policy name";
                        }

                    } // container send-default

                    container default-preference {
                        description "Enter the default-preference context";

                        leaf ebgp {
                            type uint32 {
                                range "0..255";
                            }
                            description "Default preference for EBGP";
                        }

                        leaf ibgp {
                            type uint32 {
                                range "0..255";
                            }
                            description "Default preference for IBGP";
                        }

                    } // container default-preference

                    container default-label-preference {
                        description "Enter the default-label-preference context";

                        leaf ebgp {
                            type uint32 {
                                range "0..255";
                            }
                            description "Default preference for EBGP";
                        }

                        leaf ibgp {
                            type uint32 {
                                range "0..255";
                            }
                            description "Default preference for IBGP";
                        }

                    } // container default-label-preference

                    container remove-private {
                        presence "Remove private AS numbers from the AS Path before advertising to a peer.";
                        description "Enter the remove-private context";

                        leaf limited {
                            type boolean;
                            default "false";
                            description "Remove private ASNs up to first public ASN encountered";
                        }

                        leaf skip-peer-as {
                            type boolean;
                            default "false";
                            description "Keep private ASN if it is the same as the BGP peer ASN";
                        }

                        leaf replace {
                            type boolean;
                            default "false";
                            description "Replace private ASN with global ASN before advertising";
                        }

                    } // container remove-private

                    container cluster {
                        description "Enter the cluster context";

                        leaf cluster-id {
                            type types-sros:ipv4-address;
                            description "Route reflector cluster ID";
                        }

                    } // container cluster

                    container ebgp-default-reject-policy {
                        presence "Configure default reject behavior for BGP";
                        description "Enter the ebgp-default-reject-policy context";

                        leaf import {
                            type boolean;
                            default "true";
                            description "Enable default reject import policy for external peers";
                        }

                        leaf export {
                            type boolean;
                            default "true";
                            description "Enable default reject export policy for external peers";
                        }

                    } // container ebgp-default-reject-policy

                    container local-as {
                        description "Enter the local-as context";

                        leaf as-number {
                            type uint32 {
                                range "1..4294967295";
                            }
                            description "Local (or virtual) BGP AS number";
                        }

                        leaf private {
                            type boolean;
                            default "false";
                            description "Hide the local ASN in sent paths learned from peering";
                        }

                        leaf prepend-global-as {
                            type boolean;
                            default "true";
                            description "Prepend global ASN when advertising routes to BGP peer";
                        }

                    } // container local-as

                    container import {
                        presence "Enables bgp import polices at the neighbor level";
                        description "Enter the import context";

                        leaf-list policy {
                            type string {
                                length "1..255";
                                pattern "(.{1,64})|(.*[\\[].*)" {
                                    error-message "Policy name too long or expression not valid";
                                }
                            }
                            min-elements 1;
                            max-elements 15;
                            ordered-by user;
                            description "Specifies the name of the import policy. The name of the policy is limited to 64 characters except for the first policy.";
                        }

                        leaf-list apply-groups {
                            type leafref {
                                path "../../../../../../groups/group/name";
                            }
                            max-elements 8;
                            ordered-by user;
                            description "Apply a configuration group at this level";
                        }

                    } // container import

                    container export {
                        presence "Enables bgp export polices at the peer level";
                        description "Enter the export context";

                        leaf-list policy {
                            type string {
                                length "1..255";
                                pattern "(.{1,64})|(.*[\\[].*)" {
                                    error-message "Policy name too long or expression not valid";
                                }
                            }
                            min-elements 1;
                            max-elements 15;
                            ordered-by user;
                            description "Export policy name";
                        }

                        leaf-list apply-groups {
                            type leafref {
                                path "../../../../../../groups/group/name";
                            }
                            max-elements 8;
                            ordered-by user;
                            description "Apply a configuration group at this level";
                        }

                    } // container export

                    container extended-nh-encoding {
                        presence
                            "families the Bgp instance is configured
                             to support extended next-hop encoding.";
                        description "Enter the extended-nh-encoding context";

                        leaf ipv4 {
                            type boolean;
                            default "false";
                            description "Enable/disable family type ipv4.";
                        }

                    } // container extended-nh-encoding

                    container advertise-ipv6-next-hops {
                        presence "families extended next-hop encoding is supported for.";
                        description "Enter the advertise-ipv6-next-hops context";

                        leaf ipv4 {
                            type boolean;
                            default "false";
                            description "Enable/disable family type ipv4.";
                        }

                    } // container advertise-ipv6-next-hops

                    container graceful-restart {
                        presence "Enable/disable graceful-restart for BGP neighbor.";
                        description "Enter the graceful-restart context";

                        leaf restart-time {
                            type uint32 {
                                range "0..4095";
                            }
                            default "300";
                            description "Restart time advertised by GR capability";
                        }

                        leaf stale-routes-time {
                            type uint32 {
                                range "1..3600";
                            }
                            default "360";
                            description "Maximum time to maintain routes after graceful restart";
                        }

                        leaf gr-notification {
                            type boolean;
                            default "false";
                            description "Perform graceful restart procedures after NOTIFICATION";
                        }

                        container long-lived {
                            presence "Long Lived Graceful restart attributes for all BGP group.";
                            description "Enter the long-lived context";

                            leaf advertised-stale-time {
                                type uint32 {
                                    range "0..16777215";
                                }
                                default "86400";
                                description "Advertised long-lived stale time for LLGR routes";
                            }

                            leaf helper-override-stale-time {
                                type uint32 {
                                    range "0..16777215";
                                }
                                description "Locally-configured stale routes override time";
                            }

                            leaf helper-override-restart-time {
                                type uint32 {
                                    range "0..4095";
                                }
                                description "Locally-configured override for restart time";
                            }

                            leaf forwarding-bits-set {
                                type enumeration {
                                    enum "none"                         { value 0; }
                                    enum "all"                          { value 1; }
                                    enum "non-fwd"                      { value 2; }
                                }
                                default "none";
                                description "BGP LLGR forwarding-bit behavior for address family";
                            }

                            leaf advertise-stale-to-all-neighbors {
                                type boolean;
                                default "false";
                                description "Advertise stale routes to all BGP peers";
                            }

                            leaf without-no-export {
                                type boolean;
                                default "false";
                                description "Advertise LLGR stale routes to non-LLGR peers";
                            }

                            list family {
                                key "family-type";
                                description "Enter the family list instance";

                                leaf family-type {
                                    type types-bgp:vprn-bgp-llgr-family-identifiers;
                                    description "Address family type for LLGR";
                                }

                                leaf advertised-stale-time {
                                    type uint32 {
                                        range "0..16777215";
                                    }
                                    default "86400";
                                    description "LLGR stale routes time for family override";
                                }

                                leaf helper-override-stale-time {
                                    type uint32 {
                                        range "0..16777216";
                                    }
                                    default "16777216";
                                    description "Locally-configured stale routes override time";
                                }

                                leaf-list apply-groups {
                                    type leafref {
                                        path "../../../../../../../../groups/group/name";
                                    }
                                    max-elements 8;
                                    ordered-by user;
                                    description "Apply a configuration group at this level";
                                }

                            } // list family

                        } // container long-lived

                    } // container graceful-restart

                    list prefix-limit {
                        key "family";
                        description "Enter the prefix-limit list instance";

                        leaf family {
                            type enumeration {
                                enum "ipv4"                         { value 1; }
                                enum "ipv6"                         { value 3; }
                                enum "mcast-ipv4"                   { value 4; }
                                enum "flow-ipv4"                    { value 10; }
                                enum "flow-ipv6"                    { value 14; }
                                enum "mcast-ipv6"                   { value 16; }
                                enum "label-ipv4"                   { value 17; }
                            }
                            description "Address family to which the limit applies";
                        }

                        leaf maximum {
                            type uint32 {
                                range "1..4294967295";
                            }
                            mandatory true;
                            description "Maximum number of routes to be learned from a peer";
                        }

                        leaf log-only {
                            type boolean;
                            default "false";
                            description "Send warning message at threshold instead of take-down";
                        }

                        leaf threshold {
                            type uint32 {
                                range "1..100";
                            }
                            default "90";
                            description "Percentage threshold that triggers a warning message";
                        }

                        leaf idle-timeout {
                            type int32 {
                                range "1..1024";
                            }
                            description "Time which BGP peering remains idle before reconnecting";
                        }

                        leaf post-import {
                            type boolean;
                            default "false";
                            description "Apply limit only to routes accepted by import policies";
                        }

                        leaf-list apply-groups {
                            type leafref {
                                path "../../../../../../groups/group/name";
                            }
                            max-elements 8;
                            ordered-by user;
                            description "Apply a configuration group at this level";
                        }

                    } // list prefix-limit

                    container monitor {
                        presence "Contains all the BMP related configuration for a bgp-neighbor.";
                        description "Enter the monitor context";

                        leaf all-stations {
                            type boolean;
                            default "false";
                            description "Send BMP messages to all configured stations";
                        }

                        leaf admin-state {
                            type types-sros:admin-state;
                            default "disable";
                            description "Administrative state of BMP monitoring";
                        }

                        leaf-list apply-groups {
                            type leafref {
                                path "../../../../../../groups/group/name";
                            }
                            max-elements 8;
                            ordered-by user;
                            description "Apply a configuration group at this level";
                        }

                        container route-monitoring {
                            description "Enter the route-monitoring context";

                            leaf pre-policy {
                                type boolean;
                                default "false";
                                description "Allow pre-policy route-monitoring messages to be sent";
                            }

                            leaf post-policy {
                                type boolean;
                                default "false";
                                description "Allow post-policy route-monitoring messages to be sent";
                            }

                        } // container route-monitoring

                        list station {
                            key "station-name";
                            max-elements 8;
                            description "Add a list entry for station";

                            leaf station-name {
                                type leafref {
                                    path "../../../../../../../bmp/station/name";
                                }
                                description "BMP monitoring station";
                            }

                        } // list station

                    } // container monitor

                } // list neighbor

            } // container bgp

            container confederation {
                description "Enter the confederation context";

                leaf confed-as-num {
                    type inet:as-number {
                        range "1..4294967295";
                    }
                    description "Confederation number within an autonomous system";
                }

                list members {
                    key "as-number";
                    max-elements 256;
                    description "Add a list entry for members";

                    leaf as-number {
                        type inet:as-number {
                            range "1..4294967295";
                        }
                        description "Tertiary index for tBgpConfederation4ByteTable. Each confederation member entry is differentiated by an autonomous system number.";
                    }

                } // list members

            } // container confederation

            container eth-cfm {
                description "Enter the eth-cfm context";

                leaf-list apply-groups {
                    type leafref {
                        path "../../../../groups/group/name";
                    }
                    max-elements 8;
                    ordered-by user;
                    description "Apply a configuration group at this level";
                }

            } // container eth-cfm

            container maximum-ipv4-routes {
                description "Enter the maximum-ipv4-routes context";

                leaf value {
                    type int32 {
                        range "1..2147483647";
                    }
                    sros-ext:auto-restart-to-modify;
                    description "Maximum number of routes that are configured on this virtual router";
                }

                leaf log-only {
                    type boolean;
                    default "false";
                    description "Action when the maximum number of routes, held within a VRF context, is reached";
                }

                leaf threshold {
                    type uint32 {
                        range "1..100";
                    }
                    units "percent";
                    description "Mid-level water marker for the number of routes which this VRF holds";
                }

            } // container maximum-ipv4-routes

            container maximum-ipv6-routes {
                description "Enter the maximum-ipv6-routes context";

                leaf value {
                    type int32 {
                        range "1..2147483647";
                    }
                    sros-ext:auto-restart-to-modify;
                    description "Maximum number of routes that are configured on this virtual router";
                }

                leaf log-only {
                    type boolean;
                    default "false";
                    description "Action when the maximum number of routes, held within a VRF context, is reached";
                }

                leaf threshold {
                    type uint32 {
                        range "1..100";
                    }
                    units "percent";
                    description "Mid-level water marker for the number of routes which this VRF holds";
                }

            } // container maximum-ipv6-routes

            container mc-maximum-routes {
                description "Enter the mc-maximum-routes context";

                leaf value {
                    type int32 {
                        range "1..2147483647";
                    }
                    description "Maximum number of multicast routes to be configured on this virtual router";
                }

                leaf log-only {
                    type boolean;
                    default "false";
                    description "Action when the maximum number of multicast routes, held within a VRF context, is reached";
                }

                leaf threshold {
                    type uint32 {
                        range "1..100";
                    }
                    units "percent";
                    description "Mid-level water marker for the number of multicast routes which this VRF holds";
                }

            } // container mc-maximum-routes

            container mss-adjust {
                presence "Enables TCP Maximum Segment Size adjustment using an ISA-BB card.";
                description "Enter the mss-adjust context";

                leaf nat-group {
                    type uint32;
                    sros-ext:immutable;
                    mandatory true;
                    description "NAT group (including WLAN Gateway group) that executes the adjustment";
                }

                leaf segment-size {
                    type uint32 {
                        range "160..10240";
                    }
                    mandatory true;
                    description "Intended value for the Maximum Segment Size (MSS) option in transmitted TCP SYN requests";
                }

                leaf-list apply-groups {
                    type leafref {
                        path "../../../../groups/group/name";
                    }
                    max-elements 8;
                    ordered-by user;
                    description "Apply a configuration group at this level";
                }

            } // container mss-adjust

            container reassembly {
                presence "Reassembly of IP datagram fragments using an ISA-BB card.";
                description "Enter the reassembly context";

                leaf nat-group {
                    type uint32;
                    sros-ext:immutable;
                    mandatory true;
                    description "NAT group (including WLAN Gateway group) that executes the reassembly";
                }

                leaf to-base-network {
                    type boolean;
                    default "false";
                    description "Enable/disable sending reassembled traffic to network interface on base router";
                }

                leaf-list apply-groups {
                    type leafref {
                        path "../../../../groups/group/name";
                    }
                    max-elements 8;
                    ordered-by user;
                    description "Apply a configuration group at this level";
                }

            } // container reassembly

            container sfm-overload {
                presence "Enables reporting of SFM overload on this router.";
                description "Enter the sfm-overload context";

                leaf holdoff-time {
                    type uint32 {
                        range "1..600";
                    }
                    units "seconds";
                    description "The delay between the detection of the SFM condition and the IGP entering the overload state.";
                }

            } // container sfm-overload

            container mtrace2 {
                description "Enter the mtrace2 context";

                leaf admin-state {
                    type types-sros:admin-state;
                    default "disable";
                    description "Administrative state of multicast path tracing";
                }

                leaf udp-port {
                    type uint32 {
                        range "1024..49151";
                    }
                    default "5000";
                    description "Destination UDP port for mstat2|mtrace2 test, or unsolicited mstat2|mtrace2 packets";
                }

            } // container mtrace2

            list interface {
                key "interface-name";
                description "Enter the interface list instance";

                leaf interface-name {
                    type types-sros:interface-name;
                    description "Name of the interface";
                }

                leaf description {
                    type types-sros:very-long-description;
                    description "Text description";
                }

                leaf admin-state {
                    type types-sros:admin-state;
                    default "enable";
                    description "Administrative state of the interface";
                }

                leaf radius-auth-policy {
                    type leafref {
                        path "../../../../subscriber-mgmt/radius-authentication-policy/name";
                    }
                    description "Authentication policy";
                }

                leaf tunnel {
                    type boolean;
                    sros-ext:immutable;
                    default "false";
                    description "Enable/disable tunnel interface";
                }

                leaf static-tunnel-redundant-nexthop {
                    type types-sros:ipv4-unicast-address;
                    description "IPv4 address of the redundant next-hop for static ISA tunnels on this interface";
                }

                leaf dynamic-tunnel-redundant-nexthop {
                    type types-sros:ipv4-unicast-address;
                    description "IPv4 address of the redundant next-hop for dynamic ISA tunnels on this interface";
                }

                leaf loopback {
                    type boolean;
                    default "false";
                    description "Use interface as a loopback interface";
                }

                leaf monitor-oper-group {
                    type leafref {
                        path "../../../oper-group/name";
                    }
                    description "Operational group to monitor";
                }

                leaf shcv-policy-ipv4 {
                    when "not(../tunnel = 'true')";
                    type leafref {
                        path "../../../../subscriber-mgmt/shcv-policy/name";
                    }
                    description "Host connectivity IPv4 policy";
                }

                leaf cpu-protection {
                    type leafref {
                        path "../../../../system/security/cpu-protection/policy/policy-id";
                    }
                    description "CPU protection policy";
                }

                leaf ip-mtu {
                    type types-router:ip-mtu-ext;
                    units "bytes";
                    description "Interface IP MTU";
                }

                leaf mac {
                    type types-sros:mac-unicast-address;
                    description "MAC address for the interface";
                }

                leaf tos-marking-state {
                    type types-router:tos-marking-state;
                    default "trusted";
                    description "TOS marking state";
                }

                leaf ingress-stats {
                    type boolean;
                    default "false";
                    description "Collect ingress statistics";
                }

                leaf mac-accounting {
                    type boolean;
                    default "false";
                    description "Enable MAC accounting functionality";
                }

                leaf vas-if-type {
                    when "../tunnel = 'false'";
                    type types-router:vas-if-type;
                    description "VAS interface type";
                }

                leaf-list apply-groups {
                    type leafref {
                        path "../../../../groups/group/name";
                    }
                    max-elements 8;
                    ordered-by user;
                    description "Apply a configuration group at this level";
                }

                container ingress {
                    description "Enter the ingress context";

                    leaf policy-accounting {
                        type leafref {
                            path "../../../../../routing-options/policy-accounting/policy-acct-template/name";
                        }
                        description "Configure ingress policy accounting.";
                    }

                } // container ingress

                container load-balancing {
                    description "Enter the load-balancing context";

                    leaf ip-load-balancing {
                        type types-router:ip-load-balancing;
                        default "both";
                        description "Configure IP load balancing algorithm.";
                    }

                    leaf spi-load-balancing {
                        type boolean;
                        default "false";
                        description "Allow use of SPI (Security Parameter Index) in hashing for ESP/AH encrypted IPv4/IPv6 traffic";
                    }

                    leaf teid-load-balancing {
                        type boolean;
                        default "false";
                        description "Include TEID in hashing algorithm for GTP-U/C encapsulated traffic";
                    }

                } // container load-balancing

                container hold-time {
                    when "../tunnel = 'false' or ../loopback = 'true'";
                    description "Enter the hold-time context";

                    container ipv4 {
                        description "Enter the ipv4 context";

                        container up {
                            description "Enter the up context";

                            leaf seconds {
                                type types-router:hold-time-seconds;
                                units "seconds";
                                description "Up hold time for the IP interface";
                            }

                        } // container up

                        container down {
                            description "Enter the down context";

                            leaf seconds {
                                type types-router:hold-time-seconds;
                                units "seconds";
                                description "Down hold time for the IP interface";
                            }

                            leaf init-only {
                                type boolean;
                                default "false";
                                description "Apply delay only at interface configuration or reboot";
                            }

                        } // container down

                    } // container ipv4

                    container ipv6 {
                        description "Enter the ipv6 context";

                        container up {
                            description "Enter the up context";

                            leaf seconds {
                                type types-router:hold-time-seconds;
                                units "seconds";
                                description "Up hold time for the IP interface";
                            }

                        } // container up

                        container down {
                            description "Enter the down context";

                            leaf seconds {
                                type types-router:hold-time-seconds;
                                units "seconds";
                                description "Down hold time for the IP interface";
                            }

                            leaf init-only {
                                type boolean;
                                default "false";
                                description "Apply delay only at interface configuration or reboot";
                            }

                        } // container down

                    } // container ipv6

                } // container hold-time

                container cflowd-parameters {
                    description "Enter the cflowd-parameters context";

                    list sampling {
                        key "sampling-type";
                        description "Enter the sampling list instance";

                        leaf sampling-type {
                            type types-router:cflowd-sampling;
                            description "Unicast or multicast traffic";
                        }

                        leaf type {
                            when "not(../sampling-type = 'both')";
                            type enumeration {
                                enum "acl"                          { value 1; }
                                enum "interface"                    { value 2; }
                            }
                            mandatory true;
                            description "Type of cflowd analysis";
                        }

                        leaf direction {
                            type enumeration {
                                enum "ingress-only"                 { value 1; }
                                enum "egress-only"                  { value 2; }
                                enum "both"                         { value 3; }
                            }
                            default "ingress-only";
                            description "Direction of traffic for cflowd sampling";
                        }

                        leaf sample-profile {
                            type union {
                                type enumeration {
                                    enum "1"                            { value 1; }
                                }
                                type uint32;
                            }
                            description "Sample profile ID";
                        }

                        leaf-list apply-groups {
                            type leafref {
                                path "../../../../../../groups/group/name";
                            }
                            max-elements 8;
                            ordered-by user;
                            description "Apply a configuration group at this level";
                        }

                    } // list sampling

                } // container cflowd-parameters

                container ipv4 {
                    description "Enter the ipv4 context";

                    leaf tcp-mss {
                        type types-router:ipv4-tcp-mss-ext;
                        description "TCP maximum segment size for the interface";
                    }

                    leaf allow-directed-broadcasts {
                        type boolean;
                        default "false";
                        description "Forward directed broadcasts";
                    }

                    leaf local-dhcp-server {
                        when "../../tunnel = 'false'";
                        type leafref {
                            path "../../../dhcp-server/dhcpv4/name";
                        }
                        description "DHCP server for the interface";
                    }

                    leaf qos-route-lookup {
                        type types-router:qos-route-lookup;
                        description "QoS Route lookup";
                    }

                    leaf ip-helper-address {
                        type types-sros:ipv4-unicast-address;
                        description "Gateway address";
                    }

                    container icmp {
                        description "Enter the icmp context";

                        leaf mask-reply {
                            type boolean;
                            default "true";
                            description "Allow responses to ICMP mask requests";
                        }

                        container redirects {
                            description "Enter the redirects context";

                            leaf admin-state {
                                type types-sros:admin-state;
                                default "enable";
                                description "Administrative state of sending ICMP redirects";
                            }

                            leaf number {
                                type uint16 {
                                    range "10..1000";
                                }
                                default "100";
                                description "Maximum number of ICMP redirect messages to send";
                            }

                            leaf seconds {
                                type uint16 {
                                    range "1..60";
                                }
                                units "seconds";
                                default "10";
                                description "Time used to limit the number of ICMP redirect messages";
                            }

                        } // container redirects

                        container ttl-expired {
                            description "Enter the ttl-expired context";

                            leaf admin-state {
                                type types-sros:admin-state;
                                default "enable";
                                description "Administrative state of sending TTL expired messages";
                            }

                            leaf number {
                                type uint16 {
                                    range "10..2000";
                                }
                                default "100";
                                description "Maximum number of TTL-expired messages to send";
                            }

                            leaf seconds {
                                type uint16 {
                                    range "1..60";
                                }
                                units "seconds";
                                default "10";
                                description "Time used to limit the number of TTL-expired messages";
                            }

                        } // container ttl-expired

                        container unreachables {
                            description "Enter the unreachables context";

                            leaf admin-state {
                                type types-sros:admin-state;
                                default "enable";
                                description "Administrative state of sending unreachable messages";
                            }

                            leaf number {
                                type uint16 {
                                    range "10..2000";
                                }
                                default "100";
                                description "Maximum number of unreachable messages to send";
                            }

                            leaf seconds {
                                type uint16 {
                                    range "1..60";
                                }
                                units "seconds";
                                default "10";
                                description "Time to limit the number of ICMP unreachable messages";
                            }

                        } // container unreachables

                        container param-problem {
                            description "Enter the param-problem context";

                            leaf admin-state {
                                type types-sros:admin-state;
                                default "enable";
                                description "Administrative state of sent Parameter Problem messages";
                            }

                            leaf number {
                                type uint32 {
                                    range "10..1000";
                                }
                                default "100";
                                description "Maximum number of parameter problem messages to send";
                            }

                            leaf seconds {
                                type uint32 {
                                    range "1..60";
                                }
                                units "seconds";
                                default "10";
                                description "Time used to limit number of parameter problem messages";
                            }

                        } // container param-problem

                    } // container icmp

                    container unnumbered {
                        description "Enter the unnumbered context";

                        choice source {
                            case ip-address {

                                leaf ip-address {
                                    type types-sros:ipv4-unicast-address;
                                    description "IP address of the interface";
                                }

                            }
                            case ip-int-name {

                                leaf ip-int-name {
                                    type types-sros:interface-name;
                                    description "Name of the interface";
                                }

                            }
                        }
                    } // container unnumbered

                    container urpf-check {
                        presence "Enables unicast RPF check on this interface.";
                        description "Enter the urpf-check context";

                        leaf ignore-default {
                            type boolean;
                            default "false";
                            description "Ignore default route when performing a uRPF check";
                        }

                        leaf mode {
                            type types-router:urpf-check-mode;
                            default "strict";
                            description "Unicast RPF check mode";
                        }

                    } // container urpf-check

                    container bfd {
                        description "Enter the bfd context";

                        leaf admin-state {
                            type types-sros:admin-state;
                            default "disable";
                            description "Administrative state of BFD sessions";
                        }

                        leaf transmit-interval {
                            type uint32 {
                                range "10..100000";
                            }
                            units "milliseconds";
                            default "100";
                            description "BFD transmit interval over this interface";
                        }

                        leaf receive {
                            type uint32 {
                                range "10..100000";
                            }
                            units "milliseconds";
                            default "100";
                            description "BFD receive interval over this interface";
                        }

                        leaf multiplier {
                            type uint32 {
                                range "1..20";
                            }
                            default "3";
                            description "Number of consecutive BFD messages missed from the peer";
                        }

                        leaf echo-receive {
                            type uint32 {
                                range "100..100000";
                            }
                            units "milliseconds";
                            description "Minimum echo interval over this interface";
                        }

                        leaf type {
                            type enumeration {
                                enum "cpm-np"                       { value 1; }
                                enum "auto"                         { value 2; }
                                enum "fp"                           { value 3; }
                            }
                            default "auto";
                            description "Local termination point for BFD session";
                        }

                    } // container bfd

                    container primary {
                        presence "Enables primary IPv4 address for this ies interface.";
                        description "Enter the primary context";

                        leaf address {
                            type types-sros:ipv4-unicast-address;
                            mandatory true;
                            description "Primary IPv4 address assigned to the interface";
                        }

                        leaf prefix-length {
                            type uint32 {
                                range "0..32";
                            }
                            mandatory true;
                            description "IPv4 address prefix length";
                        }

                        leaf broadcast {
                            type types-services:broadcast-address-format;
                            default "host-ones";
                            description "Broadcast address format";
                        }

                        leaf track-srrp {
                            type uint32 {
                                range "1..4294967295";
                            }
                            description "SRRP instance whose state is tracked on this IP address";
                        }

                        leaf-list apply-groups {
                            type leafref {
                                path "../../../../../../groups/group/name";
                            }
                            max-elements 8;
                            ordered-by user;
                            description "Apply a configuration group at this level";
                        }

                    } // container primary

                    list secondary {
                        key "address";
                        description "Enter the secondary list instance";

                        leaf address {
                            type types-sros:ipv4-unicast-address;
                            description "Secondary IPv4 address assigned to the interface";
                        }

                        leaf prefix-length {
                            type uint32 {
                                range "0..32";
                            }
                            mandatory true;
                            description "IPv4 address prefix length";
                        }

                        leaf igp-inhibit {
                            type boolean;
                            default "false";
                            description "Secondary IP address that is not recognized as local interface by the running IGP";
                        }

                        leaf broadcast {
                            type types-services:broadcast-address-format;
                            default "host-ones";
                            description "Broadcast address format";
                        }

                        leaf track-srrp {
                            type uint32 {
                                range "1..4294967295";
                            }
                            description "SRRP instance whose state is tracked on this IP address";
                        }

                        leaf-list apply-groups {
                            type leafref {
                                path "../../../../../../groups/group/name";
                            }
                            max-elements 8;
                            ordered-by user;
                            description "Apply a configuration group at this level";
                        }

                    } // list secondary

                    container addresses {
                        description "Enter the addresses context";

                        list address {
                            key "ipv4-address";
                            description "Enter the address list instance";

                            leaf ipv4-address {
                                type types-sros:ipv4-unicast-address;
                                description "IPv4 address for the interface";
                            }

                            leaf prefix-length {
                                type uint32 {
                                    range "0..32";
                                }
                                mandatory true;
                                description "IPv4 address prefix length";
                            }

                            leaf-list apply-groups {
                                type leafref {
                                    path "../../../../../../../groups/group/name";
                                }
                                max-elements 8;
                                ordered-by user;
                                description "Apply a configuration group at this level";
                            }

                        } // list address

                    } // container addresses

                    container neighbor-discovery {
                        when "../../tunnel = 'false'";
                        description "Enter the neighbor-discovery context";

                        leaf timeout {
                            type uint32 {
                                range "0..65535";
                            }
                            units "seconds";
                            default "14400";
                            description "Timeout for an ARP entry learned on the interface";
                        }

                        leaf retry-timer {
                            type uint32 {
                                range "1..300";
                            }
                            units "deciseconds";
                            default "50";
                            description "ARP retry interval";
                        }

                        leaf learn-unsolicited {
                            type boolean;
                            default "false";
                            description "Learn new entries from any received NA message";
                        }

                        leaf proactive-refresh {
                            type boolean;
                            default "false";
                            description "Send a single refresh message with no retries 30 seconds prior to entry timeout";
                        }

                        leaf populate {
                            type boolean;
                            default "false";
                            description "Allow static and dynamic hosts to be populated in system ARP cache";
                        }

                        leaf local-proxy-arp {
                            type boolean;
                            default "false";
                            description "Enable local proxy ARP on interface";
                        }

                        leaf remote-proxy-arp {
                            type boolean;
                            default "false";
                            description "Enable remote proxy ARP on interface";
                        }

                        leaf-list proxy-arp-policy {
                            type leafref {
                                path "../../../../../../policy-options/policy-statement/name";
                            }
                            max-elements 5;
                            ordered-by user;
                            description "Proxy ARP policy name";
                        }

                        leaf populate-host {
                            status obsolete;
                            type boolean;
                            default "false";
                            description "Allow addition or deletion of host routes in route table derived from ARP entries in ARP cache";
                        }

                        leaf route-tag {
                            status obsolete;
                            type types-router:route-tag;
                            description "ARP route tag";
                        }

                        container host-route {
                            description "Enter the host-route context";

                            list populate {
                                key "route-type";
                                description "Enter the populate list instance";

                                leaf route-type {
                                    type enumeration {
                                        enum "static"                       { value 1; }
                                        enum "dynamic"                      { value 2; }
                                        enum "evpn"                         { value 3; }
                                    }
                                    description "Controls what type of IPv4/IPv6 entries generate a host route.";
                                }

                                leaf route-tag {
                                    type uint32 {
                                        range "1..255";
                                    }
                                    sros-ext:immutable;
                                    description "Configure tag of the route.";
                                }

                                leaf-list apply-groups {
                                    type leafref {
                                        path "../../../../../../../../groups/group/name";
                                    }
                                    max-elements 8;
                                    ordered-by user;
                                    description "Apply a configuration group at this level";
                                }

                            } // list populate

                        } // container host-route

                        container limit {
                            description "Enter the limit context";

                            leaf max-entries {
                                type types-router:ipv4-neighbor-limit;
                                description "Maximum number of entries that can be learned";
                            }

                            leaf log-only {
                                type boolean;
                                default "false";
                                description "Apply the limit to log entries only";
                            }

                            leaf threshold {
                                type uint32 {
                                    range "1..100";
                                }
                                units "percent";
                                default "90";
                                description "Threshold value that triggers a warning message";
                            }

                        } // container limit

                        container static-neighbor-unnumbered {
                            presence "Enables IP-to-MAC address mapping on the unnumbered interface.";
                            description "Enter the static-neighbor-unnumbered context";

                            leaf mac-address {
                                type yang:mac-address;
                                mandatory true;
                                description "Media-dependent physical address";
                            }

                        } // container static-neighbor-unnumbered

                        list static-neighbor {
                            key "ipv4-address";
                            description "Enter the static-neighbor list instance";

                            leaf ipv4-address {
                                type types-sros:ipv4-address;
                                description "IPv4 address corresponding to the media-dependent physical address";
                            }

                            leaf mac-address {
                                type yang:mac-address;
                                mandatory true;
                                description "Media-dependent physical address";
                            }

                            leaf-list apply-groups {
                                type leafref {
                                    path "../../../../../../../groups/group/name";
                                }
                                max-elements 8;
                                ordered-by user;
                                description "Apply a configuration group at this level";
                            }

                        } // list static-neighbor

                    } // container neighbor-discovery

                    container dhcp {
                        description "Enter the dhcp context";

                        leaf admin-state {
                            type types-sros:admin-state;
                            default "disable";
                            description "Administrative state of DHCP";
                        }

                        leaf description {
                            type types-sros:description;
                            description "Text description";
                        }

                        leaf python-policy {
                            when "../../../tunnel = 'false'";
                            type leafref {
                                path "../../../../../../python/python-policy/name";
                            }
                            description "Python policy";
                        }

                        leaf-list server {
                            type types-sros:ipv4-unicast-address;
                            max-elements 8;
                            ordered-by user;
                            description "IP addresses for DHCP server requests";
                        }

                        leaf trusted {
                            type boolean;
                            default "false";
                            description "Relay untrusted packets";
                        }

                        leaf gi-address {
                            type types-sros:ipv4-unicast-address;
                            description "Gateway interface address for the DHCP relay";
                        }

                        leaf src-ip-addr {
                            type enumeration {
                                enum "auto"                         { value 0; }
                                enum "gi-address"                   { value 1; }
                            }
                            default "auto";
                            description "Type of source address to use for DHCP relay";
                        }

                        leaf relay-plain-bootp {
                            when "../../../tunnel = 'false'";
                            type boolean;
                            default "false";
                            description "Enable/disable relaying of plain BOOTP packets.";
                        }

                        leaf use-arp {
                            when "../../../tunnel = 'false'";
                            type boolean;
                            default "false";
                            description "Enable/disable the use of ARP to determine the destination Hw address.";
                        }

                        leaf-list apply-groups {
                            type leafref {
                                path "../../../../../../groups/group/name";
                            }
                            max-elements 8;
                            ordered-by user;
                            description "Apply a configuration group at this level";
                        }

                        container proxy-server {
                            description "Enter the proxy-server context";

                            leaf admin-state {
                                type types-sros:admin-state;
                                default "disable";
                                description "Administrative state of the DHCP proxy server";
                            }

                            leaf emulated-server {
                                type types-sros:ipv4-unicast-address;
                                description "The address used as source and siaddr when emulating a DHCP server.";
                            }

                            container lease-time {
                                description "Enter the lease-time context";

                                leaf value {
                                    type types-sros:time-duration {
                                        range "300..315446399";
                                    }
                                    units "seconds";
                                    description "DHCP lease time";
                                }

                                leaf radius-override {
                                    type boolean;
                                    default "false";
                                    description "Use lease time information provided by RADIUS server";
                                }

                            } // container lease-time

                        } // container proxy-server

                        container option-82 {
                            description "Enter the option-82 context";

                            leaf action {
                                type enumeration {
                                    enum "replace"                      { value 1; }
                                    enum "drop"                         { value 2; }
                                    enum "keep"                         { value 3; }
                                }
                                default "keep";
                                description "Action to take with received DHCP Option 82";
                            }

                            container circuit-id {
                                description "Enter the circuit-id context";

                                choice circuit-id {
                                    default "ascii-tuple";
                                    case none {

                                        leaf none {
                                            type empty;
                                            description "Do not include the circuit-id.";
                                        }

                                    }
                                    case ifindex {

                                        leaf ifindex {
                                            type empty;
                                            description "Use the interface index for the Circuit ID";
                                        }

                                    }
                                    case ascii-tuple {

                                        leaf ascii-tuple {
                                            type empty;
                                            description "Use the ASCII-encoded tuple for the Circuit ID";
                                        }

                                    }
                                    case sap-id {

                                        leaf sap-id {
                                            type empty;
                                            description "Use SAP ID in the option.";
                                        }

                                    }
                                    case vlan-ascii-tuple {

                                        leaf vlan-ascii-tuple {
                                            type empty;
                                            description "Include the VLAN ID and dot1p bits in the ASCII tuple";
                                        }

                                    }
                                }
                            } // container circuit-id

                            container remote-id {
                                description "Enter the remote-id context";

                                choice remote-id {
                                    default "none";
                                    case none {

                                        leaf none {
                                            type empty;
                                            description "Do not include the Remote ID";
                                        }

                                    }
                                    case mac {

                                        leaf mac {
                                            type empty;
                                            description "Use the MAC address for the Remote ID";
                                        }

                                    }
                                    case ascii-string {

                                        leaf ascii-string {
                                            type types-sros:string-not-all-spaces {
                                                length "1..32";
                                            }
                                            description "User-defined ASCII string for the Remote ID";
                                        }

                                    }
                                }
                            } // container remote-id

                            container vendor-specific-option {
                                description "Enter the vendor-specific-option context";

                                leaf system-id {
                                    type boolean;
                                    default "false";
                                    description "Send the system ID in the Vendor Specific Option";
                                }

                                leaf client-mac-address {
                                    type boolean;
                                    default "false";
                                    description "Send the MAC address in the Vendor Specific Option";
                                }

                                leaf pool-name {
                                    type boolean;
                                    default "false";
                                    description "Send the pool name in the Vendor Specific Option";
                                }

                                leaf service-id {
                                    type boolean;
                                    default "false";
                                    description "Send the service ID in the Vendor Specific Option";
                                }

                                leaf sap-id {
                                    type boolean;
                                    default "false";
                                    description "Send the SAP ID in the Nokia vendor specific suboption.";
                                }

                                leaf string {
                                    type types-sros:string-not-all-spaces {
                                        length "1..32";
                                    }
                                    description "User-defined ASCII string for Vendor Specific Option";
                                }

                            } // container vendor-specific-option

                        } // container option-82

                        container lease-populate {
                            description "Enter the lease-populate context";

                            leaf max-leases {
                                type uint32 {
                                    range "0..511999";
                                }
                                default "0";
                                description "The maximum number of DHCPv4 leases.";
                            }

                        } // container lease-populate

                        container relay-proxy {
                            presence
                                "Enable/disable relaying of unicast DHCP client messages and optional DHCP
                                 server ip address hiding.";
                            description "Enter the relay-proxy context";

                            leaf release-update-src-ip {
                                type boolean;
                                default "false";
                                description "Specify whether or not to relay release messages.";
                            }

                            leaf siaddr-override {
                                type types-sros:ipv4-unicast-address;
                                description "Specify the IP address to use.";
                            }

                        } // container relay-proxy

                    } // container dhcp

                    list vrrp {
                        key "virtual-router-id";
                        description "Enter the vrrp list instance";

                        leaf virtual-router-id {
                            type int32 {
                                range "1..255";
                            }
                            description "Virtual Router Identifier (VRID) for the VRRP virtual router instance";
                        }

                        leaf authentication-key {
                            type types-sros:encrypted-leaf {
                                length "1..38";
                            }
                            description "Password for simple text authentication";
                        }

                        leaf-list backup {
                            type types-sros:ipv4-unicast-address;
                            max-elements 16;
                            description "Virtual router IP addresses for the interface";
                        }

                        leaf message-interval {
                            type uint32 {
                                range "1..2559";
                            }
                            units "deciseconds";
                            default "10";
                            description "Interval for sending VRRP Advertisement messages";
                        }

                        leaf passive {
                            type boolean;
                            sros-ext:immutable;
                            default "false";
                            description "Suppress the transmission and reception of VRRP advertisement messages";
                        }

                        leaf init-delay {
                            type uint32 {
                                range "1..65535";
                            }
                            units "seconds";
                            description "VRRP initialization delay timer";
                        }

                        leaf mac {
                            type types-sros:mac-unicast-address;
                            description "MAC address used by virtual router instance overriding the VRRP default derived from the VRID";
                        }

                        leaf priority {
                            type uint32 {
                                range "1..255";
                            }
                            description "Base priority for the VRRP";
                        }

                        leaf oper-group {
                            type leafref {
                                path "../../../../../oper-group/name";
                            }
                            description "Operational group name associated with VRRP";
                        }

                        leaf-list apply-groups {
                            type leafref {
                                path "../../../../../../groups/group/name";
                            }
                            max-elements 8;
                            ordered-by user;
                            description "Apply a configuration group at this level";
                        }

                        choice owner-type {
                            default "non-owner";
                            case non-owner {

                                leaf admin-state {
                                    type types-sros:admin-state;
                                    default "enable";
                                    description "Administrative state of VRRP";
                                }

                                leaf master-int-inherit {
                                    type boolean;
                                    default "false";
                                    description "Allow the master instance to dictate the master down timer";
                                }

                                leaf ping-reply {
                                    type boolean;
                                    default "false";
                                    description "Allow non-owner master to reply to ICMP echo requests";
                                }

                                leaf policy {
                                    type leafref {
                                        path "../../../../../../vrrp/policy/policy-id";
                                    }
                                    description "VRRP priority control policy associated with the virtual router instance";
                                }

                                leaf preempt {
                                    type boolean;
                                    default "true";
                                    description "Allow the VRRP to override an existing non-owner master";
                                }

                                leaf telnet-reply {
                                    type boolean;
                                    default "false";
                                    description "Allow non-owner master to reply to Telnet requests";
                                }

                                leaf traceroute-reply {
                                    type boolean;
                                    default "false";
                                    description "Allow non-owner master to reply to traceroute requests";
                                }

                                leaf standby-forwarding {
                                    type boolean;
                                    default "false";
                                    description "Allow the forwarding of packets by a standby router";
                                }

                                leaf ssh-reply {
                                    type boolean;
                                    default "false";
                                    description "Allow non-owner master to reply to SSH requests";
                                }

                                leaf ntp-reply {
                                    type boolean;
                                    default "false";
                                    description "Allow/disallow non-owner master to reply to NTP requests.";
                                }

                            }
                            case owner {

                                leaf owner {
                                    type empty;
                                    sros-ext:immutable;
                                    description "Designate virtual router instance as owning the virtual router IP addresses";
                                }

                            }
                        }
                        container bfd-liveness {
                            presence "Enable bfd on this vrrp.";
                            description "Enter the bfd-liveness context";

                            leaf dest-ip {
                                type types-sros:ipv4-address;
                                sros-ext:immutable;
                                mandatory true;
                                description "Destination IP address to be used for BFD session";
                            }

                            leaf service-name {
                                type types-services:service-name;
                                sros-ext:immutable;
                                description "Service name of interface running BFD";
                            }

                            leaf interface-name {
                                type types-sros:interface-name;
                                sros-ext:immutable;
                                mandatory true;
                                description "Name of interface running BFD";
                            }

                            leaf-list apply-groups {
                                type leafref {
                                    path "../../../../../../../groups/group/name";
                                }
                                max-elements 8;
                                ordered-by user;
                                description "Apply a configuration group at this level";
                            }

                        } // container bfd-liveness

                    } // list vrrp

                } // container ipv4

                list spoke-sdp {
                    key "sdp-bind-id";
                    max-elements 1;
                    description "Enter the spoke-sdp list instance";

                    leaf sdp-bind-id {
                        type types-services:sdp-bind-id;
                        description "SDP Binding identifier as <sdp-id>:<vc-id>. sdp-id - [1..32767] vc-id - [1..4294967295].";
                    }

                    leaf description {
                        type types-sros:description;
                        description "Text description";
                    }

                    leaf admin-state {
                        type types-sros:admin-state;
                        default "enable";
                        description "Administrative state of the SDP binding to the service";
                    }

                    leaf collect-stats {
                        type boolean;
                        default "false";
                        description "Allow agent to collect accounting statistics";
                    }

                    leaf accounting-policy {
                        type leafref {
                            path "../../../../../log/accounting-policy/policy-id";
                        }
                        description "Policy to collect accounting statistics";
                    }

                    leaf control-word {
                        type boolean;
                        default "false";
                        description "Use the control word as preferred";
                    }

                    leaf bfd-template {
                        type leafref {
                            path "../../../../../bfd/bfd-template/name";
                        }
                        description "BFD template associated with SDP binding";
                    }

                    leaf vc-type {
                        type types-services:ies-sdp-bind-vc-type;
                        sros-ext:immutable;
                        default "ether";
                        description "Type of virtual circuit (VC) associated with the SDP binding";
                    }

                    leaf-list apply-groups {
                        type leafref {
                            path "../../../../../groups/group/name";
                        }
                        max-elements 8;
                        ordered-by user;
                        description "Apply a configuration group at this level";
                    }

                    choice label {
                        case entropy {

                            leaf entropy-label {
                                type empty;
                                description "Whether the use of entropy-label is enabled or not.";
                            }

                        }
                        case hash {

                            container hash-label {
                                presence "Enable use of hash-label.";
                                description "Enter the hash-label context";

                                leaf signal-capability {
                                    type empty;
                                    description "To signal the hash label capability to the remote PE.";
                                }

                            } // container hash-label

                        }
                    }
                    container ingress {
                        description "Enter the ingress context";

                        leaf vc-label {
                            type types-services:ingress-vc-label;
                            sros-ext:auto-restart-to-modify;
                            description "Static MPLS VC label used by the far end device to send packets through this SDP";
                        }

                        container filter {
                            description "Enter the filter context";

                            leaf ip {
                                type leafref {
                                    path "../../../../../../../filter/ip-filter/filter-name";
                                }
                                description "IP filter ID";
                            }

                            leaf ipv6 {
                                type leafref {
                                    path "../../../../../../../filter/ipv6-filter/filter-name";
                                }
                                description "IPv6 filter identifier";
                            }

                        } // container filter

                        container qos {
                            description "Enter the qos context";

                            container network {
                                description "Enter the network context";

                                leaf policy-name {
                                    type leafref {
                                        path "../../../../../../../../qos/network/network-policy-name";
                                    }
                                    description "Ingress network policy name applied to this SDP binding";
                                }

                                container fp-redirect-group {
                                    description "Enter the fp-redirect-group context";

                                    leaf group-name {
                                        type leafref {
                                            path "../../../../../../../../../qos/queue-group-templates/ingress/queue-group/ingress-queue-group-name";
                                        }
                                        description "Forwarding-plane queue group policy for this SDP binding";
                                    }

                                    leaf instance {
                                        type types-services:qos-qgrp-instance-id;
                                        description "Instance of the forwarding-plane ingress Queue Group for this SDP binding";
                                    }

                                } // container fp-redirect-group

                            } // container network

                        } // container qos

                    } // container ingress

                    container egress {
                        description "Enter the egress context";

                        leaf vc-label {
                            type types-services:egress-vc-label;
                            sros-ext:auto-restart-to-modify;
                            description "Static MPLS VC label that is used to send packets to the far end device through this SDP";
                        }

                        container filter {
                            description "Enter the filter context";

                            leaf ip {
                                type leafref {
                                    path "../../../../../../../filter/ip-filter/filter-name";
                                }
                                description "IP filter ID";
                            }

                            leaf ipv6 {
                                type leafref {
                                    path "../../../../../../../filter/ipv6-filter/filter-name";
                                }
                                description "IPv6 filter identifier";
                            }

                        } // container filter

                        container qos {
                            description "Enter the qos context";

                            container network {
                                description "Enter the network context";

                                leaf policy-name {
                                    type leafref {
                                        path "../../../../../../../../qos/network/network-policy-name";
                                    }
                                    description "Egress network policy name applied to this SDP binding";
                                }

                                container port-redirect-group {
                                    description "Enter the port-redirect-group context";

                                    leaf group-name {
                                        type leafref {
                                            path "../../../../../../../../../qos/queue-group-templates/egress/queue-group/egress-queue-group-name";
                                        }
                                        description "Policy for port queue group for this SDP binding";
                                    }

                                    leaf instance {
                                        type types-services:qos-qgrp-instance-id;
                                        description "Instance of the port egress Queue Group for this SDP binding.";
                                    }

                                } // container port-redirect-group

                            } // container network

                        } // container qos

                    } // container egress

                    container cpu-protection {
                        description "Enter the cpu-protection context";

                        leaf policy-id {
                            type leafref {
                                path "../../../../../../system/security/cpu-protection/policy/policy-id";
                            }
                            description "CPM protection policy";
                        }

                        choice monitoring {
                            case mac {

                                leaf mac-monitoring {
                                    type empty;
                                    description "Monitor MAC for CPU protection";
                                }

                            }
                            case cfm {

                                container eth-cfm-monitoring {
                                    presence "Enable ETH CFM monitoring configuration.";
                                    description "Enter the eth-cfm-monitoring context";

                                    leaf aggregate {
                                        type empty;
                                        description "Apply rate limit to the sum of the per peer packet rates";
                                    }

                                    leaf car {
                                        type empty;
                                        description "Eth-CFM packets to be ignored when enforcing overall rate";
                                    }

                                } // container eth-cfm-monitoring

                            }
                            case ip {

                                leaf ip-src-monitoring {
                                    type empty;
                                    description "Enable IP source monitoring for CPU protection";
                                }

                            }
                        }
                    } // container cpu-protection

                    container bfd-liveness {
                        presence "Enable BFD liveness information.";
                        description "Enter the bfd-liveness context";

                        leaf encap {
                            type types-services:bfd-encap;
                            default "ipv4";
                            description "BFD encapsulation used on this SDP binding";
                        }

                    } // container bfd-liveness

                    container eth-cfm {
                        description "Enter the eth-cfm context";

                        leaf collect-lmm-stats {
                            type boolean;
                            default "false";
                            description "Collect statistics for loss measurement message tests";
                        }

                        leaf-list squelch-ingress-levels {
                            type uint32 {
                                range "0..7";
                            }
                            max-elements 8;
                            description "ETH-CFM PDUs to be silently discarded";
                        }

                        leaf-list apply-groups {
                            type leafref {
                                path "../../../../../../groups/group/name";
                            }
                            max-elements 8;
                            ordered-by user;
                            description "Apply a configuration group at this level";
                        }

                        container collect-lmm-fc-stats {
                            description "Enter the collect-lmm-fc-stats context";

                            leaf-list fc {
                                type types-eth-cfm:fc-type;
                                max-elements 8;
                                description "Forwarding class name for profile-unaware counter";
                            }

                            leaf-list fc-in-profile {
                                type types-eth-cfm:fc-type;
                                max-elements 8;
                                description "Forwarding class name for profile-aware counter";
                            }

                        } // container collect-lmm-fc-stats

                        list mep {
                            key "md-admin-name ma-admin-name mep-id";
                            description "Enter the mep list instance";

                            leaf md-admin-name {
                                type leafref {
                                    path "../../../../../../../eth-cfm/domain/md-admin-name";
                                }
                                description "Admin-assigned maintenance domain index value";
                            }

                            leaf ma-admin-name {
                                type leafref {
                                    path "../../../../../../../eth-cfm/domain[md-admin-name=current()/../md-admin-name]/association/ma-admin-name";
                                }
                                description "Admin-assigned maintenance association index value";
                            }

                            leaf mep-id {
                                type types-eth-cfm:mep-id-type;
                                description "MEP identifier";
                            }

                            leaf admin-state {
                                type types-sros:admin-state;
                                default "disable";
                                description "Administrative state of the MEP";
                            }

                            leaf description {
                                type types-sros:description;
                                description "Text description";
                            }

                            leaf install-mep {
                                type boolean;
                                default "false";
                                description "Install MEP in the forwarding plane";
                            }

                            leaf low-priority-defect {
                                type types-eth-cfm:lowest-alarm-priority;
                                default "mac-rem-err-xcon";
                                description "Lowest priority defect that is allowed to generate a fault alarm";
                            }

                            leaf fault-propagation {
                                type types-eth-cfm:fault-propagation-type;
                                description "Fault propagation for the MEP";
                            }

                            leaf ccm {
                                type boolean;
                                default "false";
                                description "Generate CCM messages";
                            }

                            leaf ccm-ltm-priority {
                                type types-eth-cfm:frame-priority;
                                default "7";
                                description "Priority of CCM and LTM messages transmitted by the MEP";
                            }

                            leaf ccm-padding-size {
                                type uint32 {
                                    range "3..1500";
                                }
                                description "Number of octets of padding to insert in CCM packets";
                            }

                            leaf one-way-delay-threshold {
                                type uint32 {
                                    range "0..600";
                                }
                                units "seconds";
                                default "3";
                                description "Threshold time limit for one-way delay test";
                            }

                            leaf ais {
                                type boolean;
                                default "false";
                                description "Generate AIS frames from the Maintenance Entity Group (MEG).";
                            }

                            leaf-list apply-groups {
                                type leafref {
                                    path "../../../../../../../groups/group/name";
                                }
                                max-elements 8;
                                ordered-by user;
                                description "Apply a configuration group at this level";
                            }

                            container alarm-notification {
                                description "Enter the alarm-notification context";

                                leaf fng-alarm-time {
                                    type int32 {
                                        range "250|500|1000";
                                    }
                                    units "centiseconds";
                                    description "Time that must expire before an FNG alarm is raised";
                                }

                                leaf fng-reset-time {
                                    type int32 {
                                        range "250|500|1000";
                                    }
                                    units "centiseconds";
                                    description "Time that must expire before an FNG alarm is reset";
                                }

                            } // container alarm-notification

                            container csf {
                                presence "The reception of Client Signal Fail (CSF) message parameters";
                                description "Enter the csf context";

                                leaf multiplier {
                                    type decimal64 {
                                        range "0.0|2.0..30.0";
                                        fraction-digits 1;
                                    }
                                    default "3.5";
                                    description "Receive period multiplier to time out CSF";
                                }

                            } // container csf

                            container eth-test {
                                presence "Enable/disable eth-test functionality on MEP.";
                                description "Enter the eth-test context";

                                leaf bit-error-threshold {
                                    type uint32 {
                                        range "0..11840";
                                    }
                                    units "bit errors";
                                    default "1";
                                    description "Lowest priority defect allowed to generate fault alarm";
                                }

                                container test-pattern {
                                    description "Enter the test-pattern context";

                                    leaf pattern {
                                        type enumeration {
                                            enum "all-zeros"                    { value 0; }
                                            enum "all-ones"                     { value 1; }
                                        }
                                        default "all-zeros";
                                        description "Test pattern for ETH-test frames";
                                    }

                                    leaf crc-tlv {
                                        type boolean;
                                        default "false";
                                        description "Generate a CRC checksum";
                                    }

                                } // container test-pattern

                            } // container eth-test

                            container grace {
                                description "Enter the grace context";

                                container eth-ed {
                                    description "Enter the eth-ed context";

                                    leaf max-rx-defect-window {
                                        type uint32 {
                                            range "1..86400";
                                        }
                                        units "seconds";
                                        description "Maximum received ETH-ED window duration";
                                    }

                                    leaf priority {
                                        type int32 {
                                            range "0..7";
                                        }
                                        description "Transmission priority for ETH-ED PDUs";
                                    }

                                    leaf rx-eth-ed {
                                        type boolean;
                                        default "true";
                                        description "Receive and process ETH-ED ITU-T Y.1731 PDUs on the MEP";
                                    }

                                    leaf tx-eth-ed {
                                        type boolean;
                                        default "false";
                                        description "Transmit ETH-ED PDUs from the MEP";
                                    }

                                } // container eth-ed

                                container eth-vsm-grace {
                                    description "Enter the eth-vsm-grace context";

                                    leaf rx-eth-vsm-grace {
                                        type boolean;
                                        default "true";
                                        description "Receive and process Nokia ETH-CFM Grace PDU on the MEP";
                                    }

                                    leaf tx-eth-vsm-grace {
                                        type boolean;
                                        default "true";
                                        description "Transmit ETH-ED PDUs from the MEP";
                                    }

                                } // container eth-vsm-grace

                            } // container grace

                        } // list mep

                    } // container eth-cfm

                } // list spoke-sdp

                list sap {
                    key "sap-id";
                    max-elements 1;
                    description "Enter the sap list instance";

                    leaf sap-id {
                        type types-sros:sap;
                        description "SAP identifier";
                    }

                    leaf description {
                        type types-sros:long-description;
                        description "Text description";
                    }

                    leaf admin-state {
                        type types-sros:admin-state;
                        default "enable";
                        description "Administrative state of the SAP";
                    }

                    leaf accounting-policy {
                        type leafref {
                            path "../../../../../log/accounting-policy/policy-id";
                        }
                        description "Accounting policy";
                    }

                    leaf anti-spoof {
                        type types-services:anti-spoof-option;
                        description "Anti-spoof filtering";
                    }

                    leaf bandwidth {
                        type types-services:sap-bandwidth;
                        units "kilobps";
                        description "SAP bandwidth";
                    }

                    leaf calling-station-id {
                        type types-sros:string-not-all-spaces {
                            length "1..64";
                        }
                        description "Calling station ID";
                    }

                    leaf collect-stats {
                        type boolean;
                        default "false";
                        description "Collect accounting statistics";
                    }

                    leaf dist-cpu-protection {
                        type leafref {
                            path "../../../../../system/security/dist-cpu-protection/policy/policy-name";
                        }
                        description "Distributed CPU protection policy for SAP";
                    }

                    leaf host-admin-state {
                        type types-sros:admin-state;
                        default "enable";
                        description "Enable/disable administrative state of hosts";
                    }

                    leaf host-lockout-policy {
                        type leafref {
                            path "../../../../../subscriber-mgmt/host-lockout-policy/name";
                        }
                        description "Host lockout policy";
                    }

                    leaf multi-service-site {
                        type types-sros:named-item;
                        description "Multi service site name";
                    }

                    leaf-list apply-groups {
                        type leafref {
                            path "../../../../../groups/group/name";
                        }
                        max-elements 8;
                        ordered-by user;
                        description "Apply a configuration group at this level";
                    }

                    container ingress {
                        description "Enter the ingress context";

                        leaf queue-group-redirect-list {
                            type leafref {
                                path "../../../../../../qos/queue-group-redirect-list/name";
                            }
                            description "Queue group redirect list";
                        }

                        container qos {
                            description "Enter the qos context";

                            leaf match-qinq-dot1p {
                                type enumeration {
                                    enum "top"                          { value 2; }
                                    enum "bottom"                       { value 3; }
                                }
                                description "Ingress match QinQ Dot1p";
                            }

                            container sap-ingress {
                                description "Enter the sap-ingress context";

                                leaf policy-name {
                                    type leafref {
                                        path "../../../../../../../../qos/sap-ingress/sap-ingress-policy-name";
                                    }
                                    description "Policy identifier";
                                }

                                leaf queuing-type {
                                    type types-services:services-sap-queuing-type;
                                    description "Ingress queuing type";
                                }

                                container fp-redirect-group {
                                    description "Enter the fp-redirect-group context";

                                    leaf group-name {
                                        type leafref {
                                            path "../../../../../../../../../qos/queue-group-templates/ingress/queue-group/ingress-queue-group-name";
                                        }
                                        description "Forwarding-plane queue group policy";
                                    }

                                    leaf instance {
                                        type types-services:qos-qgrp-instance-id;
                                        description "Queue group instance";
                                    }

                                } // container fp-redirect-group

                                container overrides {
                                    description "Enter the overrides context";

                                    list queue {
                                        key "queue-id";
                                        description "Enter the queue list instance";

                                        leaf queue-id {
                                            type leafref {
                                                path "../../../../../../../../../../qos/sap-ingress[sap-ingress-policy-name=current()/../../../policy-name]/queue/queue-id";
                                            }
                                            description "Policer unique ID";
                                        }

                                        leaf cbs {
                                            type union {
                                                type uint32 {
                                                    range "0..1048576";
                                                }
                                                type enumeration {
                                                    enum "auto"                         { value -1; }
                                                }
                                            }
                                            units "kilobytes";
                                            description "CBS";
                                        }

                                        leaf mbs {
                                            type union {
                                                type types-qos:bytes {
                                                    range "0..1073741824";
                                                }
                                                type enumeration {
                                                    enum "auto"                         { value -1; }
                                                }
                                            }
                                            units "bytes";
                                            description "MBS";
                                        }

                                        leaf monitor-depth {
                                            type boolean;
                                            default "false";
                                            description "Monitor queue depth";
                                        }

                                        leaf-list apply-groups {
                                            type leafref {
                                                path "../../../../../../../../../../groups/group/name";
                                            }
                                            max-elements 8;
                                            ordered-by user;
                                            description "Apply a configuration group at this level";
                                        }

                                        choice queue-override-rate {
                                            case rate {

                                                container rate {
                                                    description "Enter the rate context";

                                                    leaf pir {
                                                        type types-services:sap-pir-rate-ovr;
                                                        units "kilobps";
                                                        description "PIR rate";
                                                    }

                                                    leaf cir {
                                                        type types-services:sap-cir-rate-ovr;
                                                        units "kilobps";
                                                        description "CIR rate";
                                                    }

                                                } // container rate

                                            }
                                            case percent-rate {

                                                container percent-rate {
                                                    description "Enter the percent-rate context";

                                                    leaf pir {
                                                        type decimal64 {
                                                            range "0.01..100.00";
                                                            fraction-digits 2;
                                                        }
                                                        description "PIR percent rate";
                                                    }

                                                    leaf cir {
                                                        type decimal64 {
                                                            range "0.00..100.00";
                                                            fraction-digits 2;
                                                        }
                                                        description "CIR percent rate";
                                                    }

                                                } // container percent-rate

                                            }
                                        }
                                        container adaptation-rule {
                                            description "Enter the adaptation-rule context";

                                            leaf pir {
                                                type types-qos:adaptation-rule-override;
                                                description "Constraint used when deriving the operational PIR value";
                                            }

                                            leaf cir {
                                                type types-qos:adaptation-rule-override;
                                                description "Constraint used when deriving the operational CIR value";
                                            }

                                        } // container adaptation-rule

                                        container drop-tail {
                                            description "Enter the drop-tail context";

                                            container low {
                                                description "Enter the low context";

                                                leaf percent-reduction-from-mbs {
                                                    type types-qos:burst-percent-or-default-override;
                                                    description "Percentage reduction from the MBS for a queue drop tail";
                                                }

                                            } // container low

                                        } // container drop-tail

                                        container parent {
                                            description "Enter the parent context";

                                            leaf weight {
                                                type types-qos:weight-override;
                                                description "PIR parameter that overrides parent for queue group";
                                            }

                                            leaf cir-weight {
                                                type types-qos:weight-override;
                                                description "CIR parameter that overrides parent for queue group";
                                            }

                                        } // container parent

                                    } // list queue

                                    list policer {
                                        key "policer-id";
                                        description "Enter the policer list instance";

                                        leaf policer-id {
                                            type leafref {
                                                path "../../../../../../../../../../qos/sap-ingress[sap-ingress-policy-name=current()/../../../policy-name]/policer/policer-id";
                                            }
                                            description "Policer unique ID";
                                        }

                                        leaf cbs {
                                            type union {
                                                type types-qos:bytes {
                                                    range "0..16777216";
                                                }
                                                type enumeration {
                                                    enum "auto"                         { value -1; }
                                                }
                                            }
                                            units "bytes";
                                            description "CBS";
                                        }

                                        leaf mbs {
                                            type union {
                                                type types-qos:bytes {
                                                    range "0..1073741824";
                                                }
                                                type enumeration {
                                                    enum "auto"                         { value -1; }
                                                }
                                            }
                                            description "MBS";
                                        }

                                        leaf packet-byte-offset {
                                            type types-qos:ingress-per-packet-offset-override;
                                            description "Size of each packet, handled by the policer, to be modified";
                                        }

                                        leaf stat-mode {
                                            type types-qos:ingress-policer-stat-mode;
                                            description "Mode of statistics collected by the policer";
                                        }

                                        leaf-list apply-groups {
                                            type leafref {
                                                path "../../../../../../../../../../groups/group/name";
                                            }
                                            max-elements 8;
                                            ordered-by user;
                                            description "Apply a configuration group at this level";
                                        }

                                        choice policer-override-rate {
                                            case rate {

                                                container rate {
                                                    description "Enter the rate context";

                                                    leaf pir {
                                                        type union {
                                                            type int64 {
                                                                range "1..6400000000";
                                                            }
                                                            type enumeration {
                                                                enum "max"                          { value -1; }
                                                            }
                                                        }
                                                        units "kilobps";
                                                        description "PIR rate";
                                                    }

                                                    leaf cir {
                                                        type union {
                                                            type int64 {
                                                                range "0..6400000000";
                                                            }
                                                            type enumeration {
                                                                enum "max"                          { value -1; }
                                                            }
                                                        }
                                                        units "kilobps";
                                                        description "CIR rate";
                                                    }

                                                } // container rate

                                            }
                                            case percent-rate {

                                                container percent-rate {
                                                    description "Enter the percent-rate context";

                                                    leaf pir {
                                                        type decimal64 {
                                                            range "0.01..100.00";
                                                            fraction-digits 2;
                                                        }
                                                        description "PIR percent rate";
                                                    }

                                                    leaf cir {
                                                        type decimal64 {
                                                            range "0.00..100.00";
                                                            fraction-digits 2;
                                                        }
                                                        description "CIR percent rate";
                                                    }

                                                } // container percent-rate

                                            }
                                        }
                                    } // list policer

                                } // container overrides

                            } // container sap-ingress

                            container policer-control-policy {
                                description "Enter the policer-control-policy context";

                                leaf policy-name {
                                    type leafref {
                                        path "../../../../../../../../qos/policer-control-policy/policer-control-policy-name";
                                    }
                                    description "Policer control policy name";
                                }

                                container overrides {
                                    presence "Apply a policer control policy override.";
                                    description "Enter the overrides context";

                                    leaf-list apply-groups {
                                        type leafref {
                                            path "../../../../../../../../../groups/group/name";
                                        }
                                        max-elements 8;
                                        ordered-by user;
                                        description "Apply a configuration group at this level";
                                    }

                                    container root {
                                        description "Enter the root context";

                                        leaf max-rate {
                                            type types-services:sap-max-rate-ovr;
                                            description "Maximum frame-based bandwidth limit";
                                        }

                                        container priority-mbs-thresholds {
                                            description "Enter the priority-mbs-thresholds context";

                                            leaf min-thresh-separation {
                                                type union {
                                                    type types-qos:bytes {
                                                        range "0..16777216";
                                                    }
                                                    type enumeration {
                                                        enum "auto"                         { value -1; }
                                                    }
                                                }
                                                units "bytes";
                                                description "Minimum amount of separation buffer space";
                                            }

                                            list priority {
                                                key "priority-level";
                                                description "Enter the priority list instance";

                                                leaf priority-level {
                                                    type types-qos:hierarchy-level;
                                                    description "Priority level";
                                                }

                                                leaf mbs-contribution {
                                                    type union {
                                                        type types-qos:bytes {
                                                            range "0..16777216";
                                                        }
                                                        type enumeration {
                                                            enum "auto"                         { value -1; }
                                                        }
                                                    }
                                                    units "bytes";
                                                    description "Minimum amount of cumulative buffer space allowed";
                                                }

                                                leaf-list apply-groups {
                                                    type leafref {
                                                        path "../../../../../../../../../../../../groups/group/name";
                                                    }
                                                    max-elements 8;
                                                    ordered-by user;
                                                    description "Apply a configuration group at this level";
                                                }

                                            } // list priority

                                        } // container priority-mbs-thresholds

                                    } // container root

                                } // container overrides

                            } // container policer-control-policy

                            container scheduler-policy {
                                description "Enter the scheduler-policy context";

                                leaf policy-name {
                                    type leafref {
                                        path "../../../../../../../../qos/scheduler-policy/scheduler-policy-name";
                                    }
                                    description "Scheduler policy name";
                                }

                                container overrides {
                                    description "Enter the overrides context";

                                    list scheduler {
                                        key "scheduler-name";
                                        description "Enter the scheduler list instance";

                                        leaf scheduler-name {
                                            type types-sros:named-item;
                                            description "Scheduler override policy name";
                                        }

                                        leaf-list apply-groups {
                                            type leafref {
                                                path "../../../../../../../../../../groups/group/name";
                                            }
                                            max-elements 8;
                                            ordered-by user;
                                            description "Apply a configuration group at this level";
                                        }

                                        container parent {
                                            description "Enter the parent context";

                                            leaf weight {
                                                type types-qos:weight;
                                                description "Weight to be used by the scheduler for feeding this queue";
                                            }

                                            leaf cir-weight {
                                                type types-qos:weight;
                                                description "Weight that is used by the scheduler until the committed rate for feeding this queue";
                                            }

                                        } // container parent

                                        container rate {
                                            description "Enter the rate context";

                                            leaf pir {
                                                type union {
                                                    type int64 {
                                                        range "1..6400000000";
                                                    }
                                                    type enumeration {
                                                        enum "max"                          { value -1; }
                                                    }
                                                }
                                                description "Specifies the administrative PIR";
                                            }

                                            leaf cir {
                                                type union {
                                                    type int64 {
                                                        range "0..6400000000";
                                                    }
                                                    type enumeration {
                                                        enum "sum"                          { value -3; }
                                                        enum "max"                          { value -1; }
                                                    }
                                                }
                                                description "Specifies the administrative CIR";
                                            }

                                        } // container rate

                                    } // list scheduler

                                } // container overrides

                            } // container scheduler-policy

                        } // container qos

                        container filter {
                            description "Enter the filter context";

                            leaf ip {
                                type leafref {
                                    path "../../../../../../../filter/ip-filter/filter-name";
                                }
                                description "IP filter ID";
                            }

                            leaf ipv6 {
                                type leafref {
                                    path "../../../../../../../filter/ipv6-filter/filter-name";
                                }
                                description "IPv6 filter identifier";
                            }

                        } // container filter

                    } // container ingress

                    container egress {
                        description "Enter the egress context";

                        leaf queue-group-redirect-list {
                            type leafref {
                                path "../../../../../../qos/queue-group-redirect-list/name";
                            }
                            description "Queue group redirect list";
                        }

                        container qos {
                            description "Enter the qos context";

                            leaf qinq-mark-top-only {
                                type boolean;
                                default "false";
                                description "Mark top Q-tags";
                            }

                            container sap-egress {
                                description "Enter the sap-egress context";

                                leaf policy-name {
                                    type leafref {
                                        path "../../../../../../../../qos/sap-egress/sap-egress-policy-name";
                                    }
                                    description "Policy identifier";
                                }

                                container port-redirect-group {
                                    description "Enter the port-redirect-group context";

                                    leaf group-name {
                                        type leafref {
                                            path "../../../../../../../../../qos/queue-group-templates/egress/queue-group/egress-queue-group-name";
                                        }
                                        description "Policy for port redirect queue group";
                                    }

                                    leaf instance {
                                        type types-services:qos-qgrp-instance-id;
                                        description "Instance of port queue group";
                                    }

                                } // container port-redirect-group

                                container overrides {
                                    description "Enter the overrides context";

                                    leaf hs-secondary-shaper {
                                        type types-sros:named-item;
                                        description "HS Secondary Shaper";
                                    }

                                    container hsmda-queues {
                                        description "Enter the hsmda-queues context";

                                        leaf secondary-shaper {
                                            type types-sros:named-item;
                                            description "Secondary shaper for the HSMDA queue";
                                        }

                                        leaf packet-byte-offset {
                                            type types-services:egress-hsmda-queue-packet-byte-offset;
                                            description "Packet byte offset for HSMDA queue";
                                        }

                                        leaf wrr-policy {
                                            type leafref {
                                                path "../../../../../../../../../../qos/hsmda-wrr-policy/hsmda-wrr-policy-name";
                                            }
                                            description "WRR policy for the HSMDA queue";
                                        }

                                        list queue {
                                            key "queue-id";
                                            description "Enter the queue list instance";

                                            leaf queue-id {
                                                type leafref {
                                                    path "../../../../../../../../../../../qos/sap-egress[sap-egress-policy-name=current()/../../../../policy-name]/hsmda-queues/queue/queue-id";
                                                }
                                                description "Egress HSMDA queue ID";
                                            }

                                            leaf mbs {
                                                type types-qos:hsmda-queue-burst-size-override;
                                                units "bytes";
                                                description "Buffer space allowed for the queue";
                                            }

                                            leaf rate {
                                                type types-qos:hsmda-queue-pir-rate-override;
                                                description "Administrative PIR rate.";
                                            }

                                            leaf slope-policy {
                                                type leafref {
                                                    path "../../../../../../../../../../../qos/hsmda-slope-policy/hsmda-slope-policy-name";
                                                }
                                                description "Name of the slope-policy which is used to override the default slope-policy for the named buffer pool.";
                                            }

                                            leaf wrr-weight {
                                                type types-qos:hsmda-wrr-weight-override;
                                                description "Weight value for the HSMDA queue";
                                            }

                                            leaf-list apply-groups {
                                                type leafref {
                                                    path "../../../../../../../../../../../groups/group/name";
                                                }
                                                max-elements 8;
                                                ordered-by user;
                                                description "Apply a configuration group at this level";
                                            }

                                        } // list queue

                                    } // container hsmda-queues

                                    list queue {
                                        key "queue-id";
                                        description "Enter the queue list instance";

                                        leaf queue-id {
                                            type leafref {
                                                path "../../../../../../../../../../qos/sap-egress[sap-egress-policy-name=current()/../../../policy-name]/queue/queue-id";
                                            }
                                            description "Policer unique ID";
                                        }

                                        leaf avg-frame-overhead {
                                            type decimal64 {
                                                range "0.00..100.00";
                                                fraction-digits 2;
                                            }
                                            description "Encapsulation overhead, in centipercent, used to translate packet-based rate to frame-based rate and vice versa.";
                                        }

                                        leaf burst-limit {
                                            type union {
                                                type types-qos:bytes {
                                                    range "1..14000000";
                                                }
                                                type enumeration {
                                                    enum "auto"                         { value -1; }
                                                }
                                            }
                                            description "Explicit shaping burst size of a queue.";
                                        }

                                        leaf cbs {
                                            type union {
                                                type uint32 {
                                                    range "0..1048576";
                                                }
                                                type enumeration {
                                                    enum "auto"                         { value -1; }
                                                }
                                            }
                                            units "kilobytes";
                                            description "CBS";
                                        }

                                        leaf mbs {
                                            type union {
                                                type types-qos:bytes {
                                                    range "0..1073741824";
                                                }
                                                type enumeration {
                                                    enum "auto"                         { value -1; }
                                                }
                                            }
                                            units "bytes";
                                            description "MBS";
                                        }

                                        leaf monitor-depth {
                                            type boolean;
                                            default "false";
                                            description "Monitor queue depth";
                                        }

                                        leaf hs-wrr-weight {
                                            type types-qos:hs-wrr-weight-override;
                                            default "1";
                                            description "Weighted Round Robin (WRR) weight to parent with this queue into the scheduler";
                                        }

                                        leaf hs-class-weight {
                                            type types-qos:hs-class-weight-override;
                                            description "Scheduling class weight.";
                                        }

                                        leaf-list apply-groups {
                                            type leafref {
                                                path "../../../../../../../../../../groups/group/name";
                                            }
                                            max-elements 8;
                                            ordered-by user;
                                            description "Apply a configuration group at this level";
                                        }

                                        choice queue-override-rate {
                                            case rate {

                                                container rate {
                                                    description "Enter the rate context";

                                                    leaf pir {
                                                        type types-services:sap-pir-rate-ovr;
                                                        units "kilobps";
                                                        description "PIR rate";
                                                    }

                                                    leaf cir {
                                                        type types-services:sap-cir-rate-ovr;
                                                        units "kilobps";
                                                        description "CIR rate";
                                                    }

                                                } // container rate

                                            }
                                            case percent-rate {

                                                container percent-rate {
                                                    description "Enter the percent-rate context";

                                                    leaf pir {
                                                        type decimal64 {
                                                            range "0.01..100.00";
                                                            fraction-digits 2;
                                                        }
                                                        description "PIR percent rate";
                                                    }

                                                    leaf cir {
                                                        type decimal64 {
                                                            range "0.00..100.00";
                                                            fraction-digits 2;
                                                        }
                                                        description "CIR percent rate";
                                                    }

                                                } // container percent-rate

                                            }
                                        }
                                        container adaptation-rule {
                                            description "Enter the adaptation-rule context";

                                            leaf pir {
                                                type types-qos:adaptation-rule-override;
                                                description "Constraint used when deriving the operational PIR value";
                                            }

                                            leaf cir {
                                                type types-qos:adaptation-rule-override;
                                                description "Constraint used when deriving the operational CIR value";
                                            }

                                        } // container adaptation-rule

                                        container drop-tail {
                                            description "Enter the drop-tail context";

                                            container low {
                                                description "Enter the low context";

                                                leaf percent-reduction-from-mbs {
                                                    type types-qos:burst-percent-or-default-override;
                                                    description "Percentage reduction from the MBS for a queue drop tail";
                                                }

                                            } // container low

                                        } // container drop-tail

                                        container parent {
                                            description "Enter the parent context";

                                            leaf weight {
                                                type types-qos:weight-override;
                                                description "PIR parameter that overrides parent for queue group";
                                            }

                                            leaf cir-weight {
                                                type types-qos:weight-override;
                                                description "CIR parameter that overrides parent for queue group";
                                            }

                                        } // container parent

                                        container hs-wred-queue {
                                            description "Enter the hs-wred-queue context";

                                            leaf policy {
                                                type leafref {
                                                    path "../../../../../../../../../../../qos/slope-policy/slope-policy-name";
                                                }
                                                description "Name of slope-policy.";
                                            }

                                        } // container hs-wred-queue

                                    } // list queue

                                    list policer {
                                        key "policer-id";
                                        description "Enter the policer list instance";

                                        leaf policer-id {
                                            type leafref {
                                                path "../../../../../../../../../../qos/sap-egress[sap-egress-policy-name=current()/../../../policy-name]/policer/policer-id";
                                            }
                                            description "Policer unique ID";
                                        }

                                        leaf cbs {
                                            type union {
                                                type types-qos:bytes {
                                                    range "0..16777216";
                                                }
                                                type enumeration {
                                                    enum "auto"                         { value -1; }
                                                }
                                            }
                                            units "bytes";
                                            description "CBS";
                                        }

                                        leaf mbs {
                                            type union {
                                                type types-qos:bytes {
                                                    range "0..1073741824";
                                                }
                                                type enumeration {
                                                    enum "auto"                         { value -1; }
                                                }
                                            }
                                            description "MBS";
                                        }

                                        leaf packet-byte-offset {
                                            type types-qos:egress-per-packet-offset-override;
                                            description "Size of each packet, handled by the policer, to be modified";
                                        }

                                        leaf stat-mode {
                                            type types-qos:egress-policer-stat-mode;
                                            description "Mode of statistics collected by the policer";
                                        }

                                        leaf-list apply-groups {
                                            type leafref {
                                                path "../../../../../../../../../../groups/group/name";
                                            }
                                            max-elements 8;
                                            ordered-by user;
                                            description "Apply a configuration group at this level";
                                        }

                                        choice policer-override-rate {
                                            case rate {

                                                container rate {
                                                    description "Enter the rate context";

                                                    leaf pir {
                                                        type union {
                                                            type int64 {
                                                                range "1..6400000000";
                                                            }
                                                            type enumeration {
                                                                enum "max"                          { value -1; }
                                                            }
                                                        }
                                                        units "kilobps";
                                                        description "PIR rate";
                                                    }

                                                    leaf cir {
                                                        type union {
                                                            type int64 {
                                                                range "0..6400000000";
                                                            }
                                                            type enumeration {
                                                                enum "max"                          { value -1; }
                                                            }
                                                        }
                                                        units "kilobps";
                                                        description "CIR rate";
                                                    }

                                                } // container rate

                                            }
                                            case percent-rate {

                                                container percent-rate {
                                                    description "Enter the percent-rate context";

                                                    leaf pir {
                                                        type decimal64 {
                                                            range "0.01..100.00";
                                                            fraction-digits 2;
                                                        }
                                                        description "PIR percent rate";
                                                    }

                                                    leaf cir {
                                                        type decimal64 {
                                                            range "0.00..100.00";
                                                            fraction-digits 2;
                                                        }
                                                        description "CIR percent rate";
                                                    }

                                                } // container percent-rate

                                            }
                                        }
                                    } // list policer

                                    list hs-wrr-group {
                                        key "group-id";
                                        description "Enter the hs-wrr-group list instance";

                                        leaf group-id {
                                            type leafref {
                                                path "../../../../../../../../../../qos/sap-egress[sap-egress-policy-name=current()/../../../policy-name]/hs-wrr-group/group-id";
                                            }
                                            description "HS WRR group identifier";
                                        }

                                        leaf hs-class-weight {
                                            type types-qos:hs-class-weight-override;
                                            description "Weight of scheduling class.";
                                        }

                                        leaf-list apply-groups {
                                            type leafref {
                                                path "../../../../../../../../../../groups/group/name";
                                            }
                                            max-elements 8;
                                            ordered-by user;
                                            description "Apply a configuration group at this level";
                                        }

                                        choice rate-or-percent-rate {
                                            case rate {

                                                leaf rate {
                                                    type union {
                                                        type uint32 {
                                                            range "1..2000000000";
                                                        }
                                                        type enumeration {
                                                            enum "max"                          { value -1; }
                                                        }
                                                    }
                                                    units "kilobps";
                                                    description "Administrative PIR.";
                                                }

                                            }
                                            case percent-rate {

                                                leaf percent-rate {
                                                    type decimal64 {
                                                        range "0.01..100.00";
                                                        fraction-digits 2;
                                                    }
                                                    description "Administrative PIR percent.";
                                                }

                                            }
                                        }
                                    } // list hs-wrr-group

                                } // container overrides

                            } // container sap-egress

                            container policer-control-policy {
                                description "Enter the policer-control-policy context";

                                leaf policy-name {
                                    type leafref {
                                        path "../../../../../../../../qos/policer-control-policy/policer-control-policy-name";
                                    }
                                    description "Policer control policy name";
                                }

                                container overrides {
                                    presence "Apply a policer control policy override.";
                                    description "Enter the overrides context";

                                    leaf-list apply-groups {
                                        type leafref {
                                            path "../../../../../../../../../groups/group/name";
                                        }
                                        max-elements 8;
                                        ordered-by user;
                                        description "Apply a configuration group at this level";
                                    }

                                    container root {
                                        description "Enter the root context";

                                        leaf max-rate {
                                            type types-services:sap-max-rate-ovr;
                                            description "Maximum frame-based bandwidth limit";
                                        }

                                        container priority-mbs-thresholds {
                                            description "Enter the priority-mbs-thresholds context";

                                            leaf min-thresh-separation {
                                                type union {
                                                    type types-qos:bytes {
                                                        range "0..16777216";
                                                    }
                                                    type enumeration {
                                                        enum "auto"                         { value -1; }
                                                    }
                                                }
                                                units "bytes";
                                                description "Minimum amount of separation buffer space";
                                            }

                                            list priority {
                                                key "priority-level";
                                                description "Enter the priority list instance";

                                                leaf priority-level {
                                                    type types-qos:hierarchy-level;
                                                    description "Priority level";
                                                }

                                                leaf mbs-contribution {
                                                    type union {
                                                        type types-qos:bytes {
                                                            range "0..16777216";
                                                        }
                                                        type enumeration {
                                                            enum "auto"                         { value -1; }
                                                        }
                                                    }
                                                    units "bytes";
                                                    description "Minimum amount of cumulative buffer space allowed";
                                                }

                                                leaf-list apply-groups {
                                                    type leafref {
                                                        path "../../../../../../../../../../../../groups/group/name";
                                                    }
                                                    max-elements 8;
                                                    ordered-by user;
                                                    description "Apply a configuration group at this level";
                                                }

                                            } // list priority

                                        } // container priority-mbs-thresholds

                                    } // container root

                                } // container overrides

                            } // container policer-control-policy

                            container scheduler-policy {
                                description "Enter the scheduler-policy context";

                                leaf policy-name {
                                    type leafref {
                                        path "../../../../../../../../qos/scheduler-policy/scheduler-policy-name";
                                    }
                                    description "Scheduler policy name";
                                }

                                container overrides {
                                    description "Enter the overrides context";

                                    list scheduler {
                                        key "scheduler-name";
                                        description "Enter the scheduler list instance";

                                        leaf scheduler-name {
                                            type types-sros:named-item;
                                            description "Scheduler override policy name";
                                        }

                                        leaf-list apply-groups {
                                            type leafref {
                                                path "../../../../../../../../../../groups/group/name";
                                            }
                                            max-elements 8;
                                            ordered-by user;
                                            description "Apply a configuration group at this level";
                                        }

                                        container parent {
                                            description "Enter the parent context";

                                            leaf weight {
                                                type types-qos:weight;
                                                description "Weight to be used by the scheduler for feeding this queue";
                                            }

                                            leaf cir-weight {
                                                type types-qos:weight;
                                                description "Weight that is used by the scheduler until the committed rate for feeding this queue";
                                            }

                                        } // container parent

                                        container rate {
                                            description "Enter the rate context";

                                            leaf pir {
                                                type union {
                                                    type int64 {
                                                        range "1..6400000000";
                                                    }
                                                    type enumeration {
                                                        enum "max"                          { value -1; }
                                                    }
                                                }
                                                description "Specifies the administrative PIR";
                                            }

                                            leaf cir {
                                                type union {
                                                    type int64 {
                                                        range "0..6400000000";
                                                    }
                                                    type enumeration {
                                                        enum "sum"                          { value -3; }
                                                        enum "max"                          { value -1; }
                                                    }
                                                }
                                                description "Specifies the administrative CIR";
                                            }

                                        } // container rate

                                    } // list scheduler

                                } // container overrides

                            } // container scheduler-policy

                            container vlan-qos-policy {
                                description "Enter the vlan-qos-policy context";

                                leaf policy-name {
                                    type leafref {
                                        path "../../../../../../../../qos/vlan-qos-policy/vlan-qos-policy-name";
                                    }
                                    description "Egress vlan-qos-policy name";
                                }

                            } // container vlan-qos-policy

                            container egress-remark-policy {
                                description "Enter the egress-remark-policy context";

                                leaf policy-name {
                                    type leafref {
                                        path "../../../../../../../../qos/egress-remark-policy/egress-remark-policy-name";
                                    }
                                    description "Egress-remark-policy name";
                                }

                            } // container egress-remark-policy

                        } // container qos

                        container filter {
                            description "Enter the filter context";

                            leaf ip {
                                type leafref {
                                    path "../../../../../../../filter/ip-filter/filter-name";
                                }
                                description "MAC filter ID";
                            }

                            leaf ipv6 {
                                type leafref {
                                    path "../../../../../../../filter/ipv6-filter/filter-name";
                                }
                                description "IPv6 filter identifier";
                            }

                        } // container filter

                        container agg-rate {
                            description "Enter the agg-rate context";

                            leaf limit-unused-bandwidth {
                                type boolean;
                                default "false";
                                description "Enable aggregate rate overrun protection";
                            }

                            leaf rate {
                                type types-services:agg-rate-rate;
                                description "Maximum total rate of all egress queues in kbps.";
                            }

                            leaf queue-frame-based-accounting {
                                type boolean;
                                default "false";
                                description "Enable frame-based accounting on all policers and queues associated with context";
                            }

                            leaf cir {
                                type union {
                                    type int32 {
                                        range "0..100000000";
                                    }
                                    type enumeration {
                                        enum "max"                          { value -1; }
                                    }
                                }
                                units "kilobps";
                                default "0";
                                description "Specifies the administrative CIR.";
                            }

                        } // container agg-rate

                    } // container egress

                    container cpu-protection {
                        description "Enter the cpu-protection context";

                        leaf policy-id {
                            type leafref {
                                path "../../../../../../system/security/cpu-protection/policy/policy-id";
                            }
                            description "CPM protection policy";
                        }

                        choice monitoring {
                            case mac {

                                leaf mac-monitoring {
                                    type empty;
                                    description "Monitor MAC for CPU protection";
                                }

                            }
                            case cfm {

                                container eth-cfm-monitoring {
                                    presence "Enable ETH CFM monitoring configuration.";
                                    description "Enter the eth-cfm-monitoring context";

                                    leaf aggregate {
                                        type empty;
                                        description "Apply rate limit to the sum of the per peer packet rates";
                                    }

                                    leaf car {
                                        type empty;
                                        description "Eth-CFM packets to be ignored when enforcing overall rate";
                                    }

                                } // container eth-cfm-monitoring

                            }
                            case ip {

                                leaf ip-src-monitoring {
                                    type empty;
                                    description "Enable IP source monitoring for CPU protection";
                                }

                            }
                        }
                    } // container cpu-protection

                    container lag {
                        description "Enter the lag context";

                        leaf link-map-profile {
                            type types-services:link-map-profile-id;
                            description "LAG link map profile applied to a SAP or network interface";
                        }

                        container per-link-hash {
                            description "Enter the per-link-hash context";

                            leaf class {
                                type types-services:sap-lag-per-link-hash-class;
                                default "1";
                                description "Class used on LAG egress when using weighted per-link-hash";
                            }

                            leaf weight {
                                type types-services:sap-lag-per-link-hash-weight;
                                default "1";
                                description "Weight used on LAG egress when using weighted per-link-hash";
                            }

                        } // container per-link-hash

                    } // container lag

                    container fwd-wholesale {
                        description "Enter the fwd-wholesale context";

                        leaf pppoe-service {
                            type leafref {
                                path "../../../../../epipe/service-name";
                            }
                            description "PPPoE service name";
                        }

                    } // container fwd-wholesale

                    container eth-cfm {
                        description "Enter the eth-cfm context";

                        leaf collect-lmm-stats {
                            type boolean;
                            default "false";
                            description "Collect statistics for loss measurement message tests";
                        }

                        leaf-list squelch-ingress-levels {
                            type uint32 {
                                range "0..7";
                            }
                            max-elements 8;
                            description "ETH-CFM PDUs to be silently discarded";
                        }

                        leaf-list apply-groups {
                            type leafref {
                                path "../../../../../../groups/group/name";
                            }
                            max-elements 8;
                            ordered-by user;
                            description "Apply a configuration group at this level";
                        }

                        container collect-lmm-fc-stats {
                            description "Enter the collect-lmm-fc-stats context";

                            leaf-list fc {
                                type types-eth-cfm:fc-type;
                                max-elements 8;
                                description "Forwarding class name for profile-unaware counter";
                            }

                            leaf-list fc-in-profile {
                                type types-eth-cfm:fc-type;
                                max-elements 8;
                                description "Forwarding class name for profile-aware counter";
                            }

                        } // container collect-lmm-fc-stats

                        list mep {
                            key "md-admin-name ma-admin-name mep-id";
                            description "Enter the mep list instance";

                            leaf md-admin-name {
                                type leafref {
                                    path "../../../../../../../eth-cfm/domain/md-admin-name";
                                }
                                description "Admin-assigned maintenance domain index value";
                            }

                            leaf ma-admin-name {
                                type leafref {
                                    path "../../../../../../../eth-cfm/domain[md-admin-name=current()/../md-admin-name]/association/ma-admin-name";
                                }
                                description "Admin-assigned maintenance association index value";
                            }

                            leaf mep-id {
                                type types-eth-cfm:mep-id-type;
                                description "MEP identifier";
                            }

                            leaf admin-state {
                                type types-sros:admin-state;
                                default "disable";
                                description "Administrative state of the MEP";
                            }

                            leaf description {
                                type types-sros:description;
                                description "Text description";
                            }

                            leaf install-mep {
                                type boolean;
                                default "false";
                                description "Install MEP in the forwarding plane";
                            }

                            leaf low-priority-defect {
                                type types-eth-cfm:lowest-alarm-priority;
                                default "mac-rem-err-xcon";
                                description "Lowest priority defect that is allowed to generate a fault alarm";
                            }

                            leaf fault-propagation {
                                type types-eth-cfm:fault-propagation-type;
                                description "Fault propagation for the MEP";
                            }

                            leaf ccm {
                                type boolean;
                                default "false";
                                description "Generate CCM messages";
                            }

                            leaf ccm-ltm-priority {
                                type types-eth-cfm:frame-priority;
                                default "7";
                                description "Priority of CCM and LTM messages transmitted by the MEP";
                            }

                            leaf ccm-padding-size {
                                type uint32 {
                                    range "3..1500";
                                }
                                description "Number of octets of padding to insert in CCM packets";
                            }

                            leaf one-way-delay-threshold {
                                type uint32 {
                                    range "0..600";
                                }
                                units "seconds";
                                default "3";
                                description "Threshold time limit for one-way delay test";
                            }

                            leaf ais {
                                type boolean;
                                default "false";
                                description "Generate AIS frames from the Maintenance Entity Group (MEG).";
                            }

                            leaf-list apply-groups {
                                type leafref {
                                    path "../../../../../../../groups/group/name";
                                }
                                max-elements 8;
                                ordered-by user;
                                description "Apply a configuration group at this level";
                            }

                            container alarm-notification {
                                description "Enter the alarm-notification context";

                                leaf fng-alarm-time {
                                    type int32 {
                                        range "250|500|1000";
                                    }
                                    units "centiseconds";
                                    description "Time that must expire before an FNG alarm is raised";
                                }

                                leaf fng-reset-time {
                                    type int32 {
                                        range "250|500|1000";
                                    }
                                    units "centiseconds";
                                    description "Time that must expire before an FNG alarm is reset";
                                }

                            } // container alarm-notification

                            container csf {
                                presence "The reception of Client Signal Fail (CSF) message parameters";
                                description "Enter the csf context";

                                leaf multiplier {
                                    type decimal64 {
                                        range "0.0|2.0..30.0";
                                        fraction-digits 1;
                                    }
                                    default "3.5";
                                    description "Receive period multiplier to time out CSF";
                                }

                            } // container csf

                            container eth-test {
                                presence "Enable/disable eth-test functionality on MEP.";
                                description "Enter the eth-test context";

                                leaf bit-error-threshold {
                                    type uint32 {
                                        range "0..11840";
                                    }
                                    units "bit errors";
                                    default "1";
                                    description "Lowest priority defect allowed to generate fault alarm";
                                }

                                container test-pattern {
                                    description "Enter the test-pattern context";

                                    leaf pattern {
                                        type enumeration {
                                            enum "all-zeros"                    { value 0; }
                                            enum "all-ones"                     { value 1; }
                                        }
                                        default "all-zeros";
                                        description "Test pattern for ETH-test frames";
                                    }

                                    leaf crc-tlv {
                                        type boolean;
                                        default "false";
                                        description "Generate a CRC checksum";
                                    }

                                } // container test-pattern

                            } // container eth-test

                            container grace {
                                description "Enter the grace context";

                                container eth-ed {
                                    description "Enter the eth-ed context";

                                    leaf max-rx-defect-window {
                                        type uint32 {
                                            range "1..86400";
                                        }
                                        units "seconds";
                                        description "Maximum received ETH-ED window duration";
                                    }

                                    leaf priority {
                                        type int32 {
                                            range "0..7";
                                        }
                                        description "Transmission priority for ETH-ED PDUs";
                                    }

                                    leaf rx-eth-ed {
                                        type boolean;
                                        default "true";
                                        description "Receive and process ETH-ED ITU-T Y.1731 PDUs on the MEP";
                                    }

                                    leaf tx-eth-ed {
                                        type boolean;
                                        default "false";
                                        description "Transmit ETH-ED PDUs from the MEP";
                                    }

                                } // container eth-ed

                                container eth-vsm-grace {
                                    description "Enter the eth-vsm-grace context";

                                    leaf rx-eth-vsm-grace {
                                        type boolean;
                                        default "true";
                                        description "Receive and process Nokia ETH-CFM Grace PDU on the MEP";
                                    }

                                    leaf tx-eth-vsm-grace {
                                        type boolean;
                                        default "true";
                                        description "Transmit ETH-ED PDUs from the MEP";
                                    }

                                } // container eth-vsm-grace

                            } // container grace

                        } // list mep

                    } // container eth-cfm

                    list ip-tunnel {
                        key "tunnel-name";
                        max-elements 1;
                        description "Enter the ip-tunnel list instance";

                        leaf tunnel-name {
                            type types-sros:interface-name;
                            description "IP tunnel name";
                        }

                        leaf admin-state {
                            type types-sros:admin-state;
                            default "disable";
                            description "Administrative state of the tunnel";
                        }

                        leaf description {
                            type types-sros:description;
                            sros-ext:auto-restart-to-modify;
                            description "Text description";
                        }

                        leaf clear-df-bit {
                            type boolean;
                            sros-ext:auto-restart-to-modify;
                            default "false";
                            description "Clear the Do-not-Fragment bit";
                        }

                        leaf delivery-service {
                            type types-services:service-name;
                            sros-ext:auto-restart-to-modify;
                            description "Delivery service name";
                        }

                        leaf dscp {
                            type types-qos:dscp-name;
                            sros-ext:auto-restart-to-modify;
                            description "Differentiated Services Code Point (DSCP) name";
                        }

                        leaf encapsulated-ip-mtu {
                            type uint32 {
                                range "512..9000";
                            }
                            units "bytes";
                            sros-ext:auto-restart-to-modify;
                            description "Encapsulated IP MTU of this tunnel";
                        }

                        leaf ip-mtu {
                            type uint32 {
                                range "512..9000";
                            }
                            units "bytes";
                            sros-ext:auto-restart-to-modify;
                            description "IP MTU of this tunnel";
                        }

                        leaf public-tcp-mss-adjust {
                            type union {
                                type uint32 {
                                    range "512..9000";
                                }
                                type enumeration {
                                    enum "auto"                         { value 0; }
                                }
                            }
                            units "bytes";
                            sros-ext:auto-restart-to-modify;
                            description "TCP maximum segment size (MSS) on private network";
                        }

                        leaf private-tcp-mss-adjust {
                            type int32 {
                                range "512..9000";
                            }
                            units "bytes";
                            sros-ext:auto-restart-to-modify;
                            description "TCP maximum segment size (MSS) on private network";
                        }

                        leaf reassembly {
                            type union {
                                type int32 {
                                    range "1..5000";
                                }
                                type enumeration {
                                    enum "use-tunnel-group-setting"     { value -1; }
                                    enum "none"                         { value 0; }
                                }
                            }
                            units "milliseconds";
                            sros-ext:auto-restart-to-modify;
                            description "Reassembly wait time";
                        }

                        leaf remote-ip-address {
                            type types-sros:ip-address;
                            sros-ext:auto-restart-to-modify;
                            description "Remote IP address of this tunnel";
                        }

                        leaf backup-remote-ip-address {
                            type types-sros:ip-address;
                            sros-ext:auto-restart-to-modify;
                            description "Backup remote IP address that is applied to this tunnel";
                        }

                        leaf local-ip-address {
                            type types-sros:ip-address;
                            sros-ext:auto-restart-to-modify;
                            description "Local IP address of this tunnel";
                        }

                        leaf-list apply-groups {
                            type leafref {
                                path "../../../../../../groups/group/name";
                            }
                            max-elements 8;
                            ordered-by user;
                            sros-ext:auto-restart-to-modify;
                            description "Apply a configuration group at this level";
                        }

                        container icmp6-generation {
                            sros-ext:auto-restart-to-modify;
                            description "Enter the icmp6-generation context";

                            container packet-too-big {
                                sros-ext:auto-restart-to-modify;
                                description "Enter the packet-too-big context";

                                leaf admin-state {
                                    type types-sros:admin-state;
                                    sros-ext:auto-restart-to-modify;
                                    description "Administrative state of sending Packet Too Big messages";
                                }

                                leaf number {
                                    type uint32 {
                                        range "10..1000";
                                    }
                                    sros-ext:auto-restart-to-modify;
                                    default "100";
                                    description "Number of packet-too-big ICMPv6 messages issued in a specified time frame";
                                }

                                leaf seconds {
                                    type uint32 {
                                        range "1..60";
                                    }
                                    units "seconds";
                                    sros-ext:auto-restart-to-modify;
                                    default "10";
                                    description "Time frame to limit the number of packet-too-big ICMPv6 messages";
                                }

                            } // container packet-too-big

                        } // container icmp6-generation

                        container gre-header {
                            sros-ext:auto-restart-to-modify;
                            description "Enter the gre-header context";

                            leaf admin-state {
                                type types-sros:admin-state;
                                sros-ext:auto-restart-to-modify;
                                description "Administrative state of the GRE header in the tunnel";
                            }

                            container key {
                                sros-ext:auto-restart-to-modify;
                                description "Enter the key context";

                                leaf admin-state {
                                    type types-sros:admin-state;
                                    sros-ext:auto-restart-to-modify;
                                    default "disable";
                                    description "Administrative state of the keys in the GRE header";
                                }

                                leaf send {
                                    type uint32;
                                    sros-ext:auto-restart-to-modify;
                                    default "0";
                                    description "Send key of a GRE header";
                                }

                                leaf receive {
                                    type uint32;
                                    sros-ext:auto-restart-to-modify;
                                    default "0";
                                    description "Receive key of a GRE header";
                                }

                            } // container key

                        } // container gre-header

                        list dest-ip {
                            key "dest-ip-address";
                            sros-ext:auto-restart-to-modify;
                            description "Add a list entry for dest-ip";

                            leaf dest-ip-address {
                                type types-sros:ip-address;
                                description "Destination IP address of the tunnel";
                            }

                        } // list dest-ip

                    } // list ip-tunnel

                    list ipsec-gateway {
                        key "name";
                        max-elements 1;
                        description "Enter the ipsec-gateway list instance";

                        leaf name {
                            type types-sros:named-item;
                            description "IPsec gateway name.";
                        }

                        leaf admin-state {
                            type types-sros:admin-state;
                            default "disable";
                            description "Administrative state of the IPsec gateway.";
                        }

                        leaf default-tunnel-template {
                            type leafref {
                                path "../../../../../../ipsec/tunnel-template/id";
                            }
                            description "The IPsec tunnel template ID.";
                        }

                        leaf ike-policy {
                            type leafref {
                                path "../../../../../../ipsec/ike-policy/id";
                            }
                            description "IKE policy ID.";
                        }

                        leaf pre-shared-key {
                            type types-sros:encrypted-leaf {
                                length "1..115";
                            }
                            description "The pre-shared key used for authentication by two peers forming the tunnel for the IPSec gateway.";
                        }

                        leaf ts-list {
                            type leafref {
                                path "../../../../../../ipsec/ts-list/name";
                            }
                            description "The name of Traffic Selector (TS) list, used for IKEv2 TS negotiation.";
                        }

                        leaf-list apply-groups {
                            type leafref {
                                path "../../../../../../groups/group/name";
                            }
                            max-elements 8;
                            ordered-by user;
                            description "Apply a configuration group at this level";
                        }

                        container dhcp-address-assignment {
                            description "Enter the dhcp-address-assignment context";

                            container dhcpv4 {
                                presence "DHCPv4 server information.";
                                description "Enter the dhcpv4 context";

                                leaf admin-state {
                                    type types-sros:admin-state;
                                    default "disable";
                                    description "Administrative state of the IPsec DHCPv4 server.";
                                }

                                leaf gi-address {
                                    type types-sros:ipv4-unicast-address;
                                    description "The giaddr of relayed DHCPv4 header.";
                                }

                                leaf send-release {
                                    type boolean;
                                    default "true";
                                    description "Send DHCPv4 release messages.";
                                }

                                leaf-list apply-groups {
                                    type leafref {
                                        path "../../../../../../../../groups/group/name";
                                    }
                                    max-elements 8;
                                    ordered-by user;
                                    description "Apply a configuration group at this level";
                                }

                                container server {
                                    description "Enter the server context";

                                    leaf-list address {
                                        type types-sros:ipv4-unicast-address;
                                        max-elements 8;
                                        description "The DHCPv4 server addresses.";
                                    }

                                    leaf router-instance {
                                        type types-sros:router-instance-base-vprn-loose;
                                        description "Router instance to reach the DHCPv4 server.";
                                    }

                                } // container server

                            } // container dhcpv4

                            container dhcpv6 {
                                presence "DHCPv6 server information.";
                                description "Enter the dhcpv6 context";

                                leaf admin-state {
                                    type types-sros:admin-state;
                                    default "disable";
                                    description "Administrative state of the IPsec DHCPv6 server.";
                                }

                                leaf link-address {
                                    type types-sros:ipv6-unicast-address;
                                    description "The link-address in DHCPv6 relay packet.";
                                }

                                leaf send-release {
                                    type boolean;
                                    default "true";
                                    description "Send DHCPv6 release messages when a tunnel is down.";
                                }

                                leaf-list apply-groups {
                                    type leafref {
                                        path "../../../../../../../../groups/group/name";
                                    }
                                    max-elements 8;
                                    ordered-by user;
                                    description "Apply a configuration group at this level";
                                }

                                container server {
                                    description "Enter the server context";

                                    leaf-list address {
                                        type types-sros:ipv6-unicast-address;
                                        max-elements 8;
                                        description "The DHCPv6 server addresses.";
                                    }

                                    leaf router-instance {
                                        type types-sros:router-instance-base-vprn-loose;
                                        description "Router instance to reach the DHCPv6 server.";
                                    }

                                } // container server

                            } // container dhcpv6

                        } // container dhcp-address-assignment

                        container cert {
                            description "Enter the cert context";

                            leaf cert-profile {
                                type leafref {
                                    path "../../../../../../../ipsec/cert-profile/name";
                                }
                                description "Certificate profile name.";
                            }

                            leaf trust-anchor-profile {
                                type leafref {
                                    path "../../../../../../../ipsec/trust-anchor-profile/name";
                                }
                                description "Trust anchor profile.";
                            }

                            container status-verify {
                                description "Enter the status-verify context";

                                leaf default-result {
                                    type enumeration {
                                        enum "revoked"                      { value 0; }
                                        enum "good"                         { value 1; }
                                    }
                                    default "revoked";
                                    description "The default result of Certificate Status Verification (CSV).";
                                }

                                leaf primary {
                                    type types-ipsec:cert-revocation-status;
                                    default "crl";
                                    description "The primary method used to verify the peer certificate's revocation status.";
                                }

                                leaf secondary {
                                    type types-ipsec:cert-revocation-status-with-none;
                                    default "none";
                                    description "The secondary method used to verify the peer certificate's revocation status.";
                                }

                            } // container status-verify

                        } // container cert

                        container client-db {
                            presence "IPsec client database.";
                            description "Enter the client-db context";

                            leaf name {
                                type leafref {
                                    path "../../../../../../../ipsec/client-db/name";
                                }
                                mandatory true;
                                description "IPsec client database name.";
                            }

                            leaf fallback {
                                type boolean;
                                default "true";
                                description "Fall back to the tunnel authentication and creation attribute as if client-db is not configured when IPsec database client matching has failed.";
                            }

                        } // container client-db

                        container default-secure-service {
                            presence "The default security service used by this IPsec gateway.";
                            description "Enter the default-secure-service context";

                            leaf service-name {
                                type types-services:service-name;
                                sros-ext:auto-restart-to-modify;
                                description "Name of the default security service used by this IPsec gateway";
                            }

                            leaf interface {
                                type types-sros:interface-name;
                                sros-ext:auto-restart-to-modify;
                                description "The name of the default interface used by this IPsec gateway.";
                            }

                        } // container default-secure-service

                        container local {
                            description "Enter the local context";

                            leaf gateway-address {
                                type types-sros:ip-address;
                                sros-ext:auto-restart-to-modify;
                                description "The IPsec gateway address.";
                            }

                            container address-assignment {
                                presence "Local address assignment information.";
                                description "Enter the address-assignment context";

                                leaf admin-state {
                                    type types-sros:admin-state;
                                    default "disable";
                                    description "Administrative state of local address assignments";
                                }

                                leaf-list apply-groups {
                                    type leafref {
                                        path "../../../../../../../../groups/group/name";
                                    }
                                    max-elements 8;
                                    ordered-by user;
                                    description "Apply a configuration group at this level";
                                }

                                container ipv4 {
                                    presence "Local DHCPv4 server and pool information.";
                                    description "Enter the ipv4 context";

                                    leaf router-instance {
                                        type types-sros:router-instance-base-vprn-loose;
                                        mandatory true;
                                        description "Router instance hosting the DHCPv4 connection.";
                                    }

                                    leaf dhcp-server {
                                        type types-sros:named-item;
                                        mandatory true;
                                        description "Local DHCPv4 server name";
                                    }

                                    leaf pool {
                                        type types-sros:named-item;
                                        mandatory true;
                                        description "Name of the pool defined in the specified DHCPv4 server";
                                    }

                                    leaf secondary-pool {
                                        type types-sros:named-item;
                                        description "Name of the secondary pool defined in the DHCPv4 server";
                                    }

                                } // container ipv4

                                container ipv6 {
                                    presence "DHCPv6 server and pool information.";
                                    description "Enter the ipv6 context";

                                    leaf router-instance {
                                        type types-sros:router-instance-base-vprn-loose;
                                        mandatory true;
                                        description "Router instance hosting the DHCPv6 connection.";
                                    }

                                    leaf dhcp-server {
                                        type types-sros:named-item;
                                        mandatory true;
                                        description "Local DHCPv6 server name";
                                    }

                                    leaf pool {
                                        type types-sros:named-item;
                                        mandatory true;
                                        description "Name of the secondary pool defined in the DHCPv6 server";
                                    }

                                } // container ipv6

                            } // container address-assignment

                            container id {
                                description "Enter the id context";

                                choice id {
                                    default "auto";
                                    case auto {

                                        leaf auto {
                                            type empty;
                                            sros-ext:auto-restart-to-modify;
                                            description "System picks a local ID automatically based on auth-method configured in ike-policy.";
                                        }

                                    }
                                    case ipv4 {

                                        leaf ipv4 {
                                            type types-sros:ipv4-unicast-address;
                                            sros-ext:auto-restart-to-modify;
                                            description "The IPv4 Local ID.";
                                        }

                                    }
                                    case ipv6 {

                                        leaf ipv6 {
                                            type types-sros:ip-address;
                                            sros-ext:auto-restart-to-modify;
                                            description "The IPv6 Local ID.";
                                        }

                                    }
                                    case fqdn {

                                        leaf fqdn {
                                            type types-sros:fully-qualified-domain-name;
                                            sros-ext:auto-restart-to-modify;
                                            description "The Fully Qualified Domain Name (FQDN) Local ID.";
                                        }

                                    }
                                }
                            } // container id

                        } // container local

                        container radius {
                            description "Enter the radius context";

                            leaf accounting-policy {
                                type leafref {
                                    path "../../../../../../../ipsec/radius/accounting-policy/name";
                                }
                                description "RADIUS accounting policy.";
                            }

                            leaf authentication-policy {
                                type leafref {
                                    path "../../../../../../../ipsec/radius/authentication-policy/name";
                                }
                                description "RADIUS authentication policy.";
                            }

                        } // container radius

                        container max-history-key-records {
                            description "Enter the max-history-key-records context";

                            leaf ike {
                                type uint32 {
                                    range "1..3";
                                }
                                description "The maximum number of historical IKE keys which can be recorded by the system.";
                            }

                            leaf esp {
                                type uint32 {
                                    range "1..48";
                                }
                                description "The maximum number of historical ESP keys which can be recorded by the system.";
                            }

                        } // container max-history-key-records

                    } // list ipsec-gateway

                    list ipsec-tunnel {
                        key "name";
                        description "Enter the ipsec-tunnel list instance";

                        leaf name {
                            type types-sros:named-item {
                                pattern "[a-zA-Z]+.*" {
                                    error-message "IPSec tunnel name cannot start with a number";
                                }
                            }
                            description "IPsec ipsec name.";
                        }

                        leaf admin-state {
                            type types-sros:admin-state;
                            sros-ext:auto-restart-to-modify;
                            default "disable";
                            description "Administrative state of the IPsec tunnel.";
                        }

                        leaf description {
                            type types-sros:description;
                            description "Text description";
                        }

                        leaf clear-df-bit {
                            type boolean;
                            sros-ext:auto-restart-to-modify;
                            default "false";
                            description "Clear Do-not-Fragment bit.";
                        }

                        leaf encapsulated-ip-mtu {
                            type uint32 {
                                range "512..9000";
                            }
                            units "bytes";
                            sros-ext:auto-restart-to-modify;
                            description "Encapsulated IP MTU of this tunnel.";
                        }

                        leaf ip-mtu {
                            type uint32 {
                                range "512..9000";
                            }
                            units "bytes";
                            sros-ext:auto-restart-to-modify;
                            description "IP MTU of this tunnel.";
                        }

                        leaf replay-window {
                            type uint32 {
                                range "32|64|128|256|512";
                            }
                            units "packets";
                            sros-ext:auto-restart-to-modify;
                            description "Anti replay window size.";
                        }

                        leaf public-tcp-mss-adjust {
                            type union {
                                type uint32 {
                                    range "512..9000";
                                }
                                type enumeration {
                                    enum "auto"                         { value 0; }
                                }
                            }
                            units "bytes";
                            sros-ext:auto-restart-to-modify;
                            description "TCP maximum segment size (MSS) on public network.";
                        }

                        leaf private-tcp-mss-adjust {
                            type int32 {
                                range "512..9000";
                            }
                            units "bytes";
                            sros-ext:auto-restart-to-modify;
                            description "TCP maximum segment size (MSS) on private network.";
                        }

                        leaf-list apply-groups {
                            type leafref {
                                path "../../../../../../groups/group/name";
                            }
                            max-elements 8;
                            ordered-by user;
                            sros-ext:auto-restart-to-modify;
                            description "Apply a configuration group at this level";
                        }

                        container bfd {
                            sros-ext:auto-restart-to-modify;
                            description "Enter the bfd context";

                            leaf bfd-designate {
                                type boolean;
                                sros-ext:auto-restart-to-modify;
                                default "false";
                                description "Enable BFD designated tunnel.";
                            }

                            container bfd-liveness {
                                presence "BFD liveness information.";
                                sros-ext:auto-restart-to-modify;
                                description "Enter the bfd-liveness context";

                                leaf dest-ip {
                                    type types-sros:ipv4-unicast-address;
                                    sros-ext:auto-restart-to-modify;
                                    mandatory true;
                                    description "Destination address for this BFD session.";
                                }

                                leaf interface {
                                    type types-sros:interface-name;
                                    sros-ext:auto-restart-to-modify;
                                    mandatory true;
                                    description "The name of the interface used by this BFD session.";
                                }

                                leaf service-name {
                                    type types-services:service-name;
                                    sros-ext:auto-restart-to-modify;
                                    mandatory true;
                                    description "Service name of the interface running BFD.";
                                }

                            } // container bfd-liveness

                        } // container bfd

                        container icmp6-generation {
                            sros-ext:auto-restart-to-modify;
                            description "Enter the icmp6-generation context";

                            container packet-too-big {
                                sros-ext:auto-restart-to-modify;
                                description "Enter the packet-too-big context";

                                leaf admin-state {
                                    type types-sros:admin-state;
                                    sros-ext:auto-restart-to-modify;
                                    default "enable";
                                    description "Send packet-too-big messages";
                                }

                                leaf message-count {
                                    type uint32 {
                                        range "10..1000";
                                    }
                                    sros-ext:auto-restart-to-modify;
                                    default "100";
                                    description "The maximum number of ICMPv6 messages that can be sent during the period specified by 'interval'.";
                                }

                                leaf interval {
                                    type uint32 {
                                        range "1..60";
                                    }
                                    units "seconds";
                                    sros-ext:auto-restart-to-modify;
                                    default "10";
                                    description "The maximum interval that the ICMPv6 messages can be sent.";
                                }

                            } // container packet-too-big

                        } // container icmp6-generation

                        container key-exchange {
                            sros-ext:auto-restart-to-modify;
                            description "Enter the key-exchange context";

                            choice type {
                                case dynamic {

                                    container dynamic {
                                        presence "Dynamic key information.";
                                        sros-ext:auto-restart-to-modify;
                                        description "Enter the dynamic context";

                                        leaf auto-establish {
                                            type boolean;
                                            sros-ext:auto-restart-to-modify;
                                            default "false";
                                            description "Whether to attempt to establish a IKE SA automatically.";
                                        }

                                        leaf ike-policy {
                                            type leafref {
                                                path "../../../../../../../../ipsec/ike-policy/id";
                                            }
                                            sros-ext:auto-restart-to-modify;
                                            description "IKE policy ID.";
                                        }

                                        leaf-list ipsec-transform {
                                            type leafref {
                                                path "../../../../../../../../ipsec/ipsec-transform/id";
                                            }
                                            max-elements 4;
                                            sros-ext:auto-restart-to-modify;
                                            description "IPsec transform used by the dynamic key.";
                                        }

                                        leaf pre-shared-key {
                                            type types-sros:encrypted-leaf {
                                                length "1..115";
                                            }
                                            sros-ext:auto-restart-to-modify;
                                            description "The shared secret between the two peers forming the tunnel.";
                                        }

                                        container cert {
                                            sros-ext:auto-restart-to-modify;
                                            description "Enter the cert context";

                                            leaf cert-profile {
                                                type leafref {
                                                    path "../../../../../../../../../ipsec/cert-profile/name";
                                                }
                                                description "Certificate profile name.";
                                            }

                                            leaf trust-anchor-profile {
                                                type leafref {
                                                    path "../../../../../../../../../ipsec/trust-anchor-profile/name";
                                                }
                                                description "Trust anchor profile.";
                                            }

                                            container status-verify {
                                                sros-ext:auto-restart-to-modify;
                                                description "Enter the status-verify context";

                                                leaf default-result {
                                                    type enumeration {
                                                        enum "revoked"                      { value 0; }
                                                        enum "good"                         { value 1; }
                                                    }
                                                    default "revoked";
                                                    description "The default result of Certificate Status Verification (CSV).";
                                                }

                                                leaf primary {
                                                    type types-ipsec:cert-revocation-status;
                                                    default "crl";
                                                    description "The primary method used to verify the peer certificate's revocation status.";
                                                }

                                                leaf secondary {
                                                    type types-ipsec:cert-revocation-status-with-none;
                                                    default "none";
                                                    description "The secondary method used to verify the peer certificate's revocation status.";
                                                }

                                            } // container status-verify

                                        } // container cert

                                        container id {
                                            sros-ext:auto-restart-to-modify;
                                            description "Enter the id context";

                                            choice id {
                                                case ipv4 {

                                                    leaf ipv4 {
                                                        type types-sros:ipv4-unicast-address;
                                                        sros-ext:auto-restart-to-modify;
                                                        description "The IPv4 Local ID.";
                                                    }

                                                }
                                                case ipv6 {

                                                    leaf ipv6 {
                                                        type types-sros:ip-address;
                                                        sros-ext:auto-restart-to-modify;
                                                        description "The IPv6 Local ID.";
                                                    }

                                                }
                                                case fqdn {

                                                    leaf fqdn {
                                                        type types-sros:fully-qualified-domain-name;
                                                        sros-ext:auto-restart-to-modify;
                                                        description "The Fully Qualified Domain Name (FQDN) Local ID.";
                                                    }

                                                }
                                            }
                                        } // container id

                                    } // container dynamic

                                }
                                case manual {

                                    container manual {
                                        presence "Manual key information.";
                                        sros-ext:auto-restart-to-modify;
                                        description "Enter the manual context";

                                        list keys {
                                            key "security-association direction";
                                            sros-ext:auto-restart-to-modify;
                                            description "Enter the keys list instance";

                                            leaf security-association {
                                                type uint32 {
                                                    range "1..16";
                                                }
                                                description "The unique identifier of an security association (SA).";
                                            }

                                            leaf direction {
                                                type enumeration {
                                                    enum "inbound"                      { value 1; }
                                                    enum "outbound"                     { value 2; }
                                                }
                                                description "The direction on the IPsec tunnel to which this SA can be applied.";
                                            }

                                            leaf ipsec-transform {
                                                type leafref {
                                                    path "../../../../../../../../../ipsec/ipsec-transform/id";
                                                }
                                                sros-ext:immutable;
                                                sros-ext:auto-restart-to-modify;
                                                mandatory true;
                                                description "IPsec transform used by the manual key.";
                                            }

                                            leaf spi {
                                                type uint32 {
                                                    range "256..16383";
                                                }
                                                sros-ext:immutable;
                                                sros-ext:auto-restart-to-modify;
                                                mandatory true;
                                                description "Security Parameter Index (SPI).";
                                            }

                                            leaf authentication-key {
                                                type types-sros:hex-string {
                                                    length "1..130";
                                                }
                                                sros-ext:immutable;
                                                sros-ext:auto-restart-to-modify;
                                                description "The key value used for the authentication algorithm defined by the IPsec transform.";
                                            }

                                            leaf encryption-key {
                                                type types-sros:hex-string {
                                                    length "1..66";
                                                }
                                                sros-ext:immutable;
                                                sros-ext:auto-restart-to-modify;
                                                description "The key value used for the encryption algorithm defined by the IPsec transform.";
                                            }

                                            leaf-list apply-groups {
                                                type leafref {
                                                    path "../../../../../../../../../groups/group/name";
                                                }
                                                max-elements 8;
                                                ordered-by user;
                                                sros-ext:auto-restart-to-modify;
                                                description "Apply a configuration group at this level";
                                            }

                                        } // list keys

                                    } // container manual

                                }
                            }
                        } // container key-exchange

                        container max-history-key-records {
                            sros-ext:auto-restart-to-modify;
                            description "Enter the max-history-key-records context";

                            leaf ike {
                                type uint32 {
                                    range "1..3";
                                }
                                sros-ext:auto-restart-to-modify;
                                description "The maximum number of historical IKE keys which can be recorded by the system.";
                            }

                            leaf esp {
                                type uint32 {
                                    range "1..48";
                                }
                                sros-ext:auto-restart-to-modify;
                                description "The maximum number of historical ESP keys which can be recorded by the system.";
                            }

                        } // container max-history-key-records

                        container tunnel-endpoint {
                            presence "IPsec tunnel endpoint information.";
                            sros-ext:auto-restart-to-modify;
                            description "Enter the tunnel-endpoint context";

                            leaf local-gateway-address {
                                type types-sros:ip-address;
                                sros-ext:auto-restart-to-modify;
                                mandatory true;
                                description "The IPsec local gateway address for this tunnel.";
                            }

                            leaf remote-ip-address {
                                type types-sros:ip-address;
                                sros-ext:auto-restart-to-modify;
                                mandatory true;
                                description "Remote IP address of this tunnel.";
                            }

                            leaf delivery-service {
                                type types-services:service-name;
                                sros-ext:auto-restart-to-modify;
                                mandatory true;
                                description "Delivery service name.";
                            }

                        } // container tunnel-endpoint

                        list dest-ip {
                            key "address";
                            max-elements 16;
                            sros-ext:auto-restart-to-modify;
                            description "Add a list entry for dest-ip";

                            leaf address {
                                type types-sros:ip-address;
                                description "Private IP address of the remote IP tunnel endpoint";
                            }

                        } // list dest-ip

                        container security-policy {
                            sros-ext:auto-restart-to-modify;
                            description "Enter the security-policy context";

                            leaf id {
                                type leafref {
                                    path "../../../../../ipsec/security-policy/id";
                                }
                                sros-ext:auto-restart-to-modify;
                                description "Security policy ID";
                            }

                            leaf strict-match {
                                type boolean;
                                sros-ext:auto-restart-to-modify;
                                default "false";
                                description "The system does a strict match when it receives a CREATE_CHILD exchange request, which is not for rekey, for this IPsec tunnel.";
                            }

                        } // container security-policy

                    } // list ipsec-tunnel

                    container static-host {
                        description "Enter the static-host context";

                        list ipv4 {
                            key "ip mac";
                            description "Enter the ipv4 list instance";

                            leaf ip {
                                type types-sros:ipv4-address;
                                description "IP address";
                            }

                            leaf mac {
                                type types-sros:mac-unicast-address;
                                description "MAC address";
                            }

                            leaf admin-state {
                                type types-sros:admin-state;
                                default "disable";
                                description "Administrative state of the static host";
                            }

                            leaf sub-profile {
                                type leafref {
                                    path "../../../../../../../subscriber-mgmt/sub-profile/name";
                                }
                                description "Sub-profile name";
                            }

                            leaf sla-profile {
                                type leafref {
                                    path "../../../../../../../subscriber-mgmt/sla-profile/name";
                                }
                                description "SLA profile name";
                            }

                            leaf ancp-string {
                                type types-submgt:ancp-string;
                                description "ANCP string";
                            }

                            leaf int-dest-id {
                                type types-submgt:int-dest-id;
                                description "Intermediate destination ID";
                            }

                            leaf-list apply-groups {
                                type leafref {
                                    path "../../../../../../../groups/group/name";
                                }
                                max-elements 8;
                                ordered-by user;
                                description "Apply a configuration group at this level";
                            }

                            container subscriber-id {
                                description "Enter the subscriber-id context";

                                choice subscriber-id {
                                    case string {

                                        leaf string {
                                            type types-submgt:subscriber-id;
                                            description "Subscriber identification";
                                        }

                                    }
                                    case use-sap-id {

                                        leaf use-sap-id {
                                            type empty;
                                            description "Use the SAP id as subscriber ID";
                                        }

                                    }
                                }
                            } // container subscriber-id

                        } // list ipv4

                    } // container static-host

                } // list sap

                list vpls {
                    when "../tunnel = 'false'";
                    key "vpls-name";
                    max-elements 1;
                    description "Enter the vpls list instance";

                    leaf vpls-name {
                        type types-sros:named-item-64;
                        description "VPLS service";
                    }

                    leaf-list apply-groups {
                        type leafref {
                            path "../../../../../groups/group/name";
                        }
                        max-elements 8;
                        ordered-by user;
                        description "Apply a configuration group at this level";
                    }

                    container evpn {
                        description "Enter the evpn context";

                        container arp {
                            description "Enter the arp context";

                            leaf learn-dynamic {
                                type boolean;
                                default "true";
                                description "Enable/disable dynamic entries learning.";
                            }

                            leaf flood-garp-and-unknown-req {
                                type boolean;
                                default "true";
                                description "Enable/disable flooding GARP and unknown requests.";
                            }

                            list advertise {
                                key "route-type";
                                description "Enter the advertise list instance";

                                leaf route-type {
                                    type enumeration {
                                        enum "static"                       { value 1; }
                                        enum "dynamic"                      { value 2; }
                                    }
                                    description "Controls what type of ARP or ND entries generate a host route.";
                                }

                                leaf route-tag {
                                    type uint32 {
                                        range "0..255";
                                    }
                                    sros-ext:immutable;
                                    description "Configure tag to use with the host route generated from an ARP or ND entry.";
                                }

                                leaf-list apply-groups {
                                    type leafref {
                                        path "../../../../../../../../groups/group/name";
                                    }
                                    max-elements 8;
                                    ordered-by user;
                                    description "Apply a configuration group at this level";
                                }

                            } // list advertise

                        } // container arp

                    } // container evpn

                    container evpn-tunnel {
                        presence "Interface as VPLS EVPN tunnel.";
                        description "Enter the evpn-tunnel context";

                        leaf ipv6-gateway-address {
                            type enumeration {
                                enum "ip"                           { value 0; }
                                enum "mac"                          { value 1; }
                            }
                            default "ip";
                            description "Type of IPv6 gateway address";
                        }

                        leaf supplementary-broadcast-domain {
                            type boolean;
                            sros-ext:immutable;
                            default "false";
                            description "Enable/disable evpn-tunnel use as supplementary broadcast domain.";
                        }

                    } // container evpn-tunnel

                    container egress {
                        description "Enter the egress context";

                        leaf reclassify-using-qos {
                            type leafref {
                                path "../../../../../../qos/sap-egress/sap-egress-policy-name";
                            }
                            description "Egress QoS policy";
                        }

                        container routed-override-filter {
                            description "Enter the routed-override-filter context";

                            leaf ip {
                                type leafref {
                                    path "../../../../../../../filter/ip-filter/filter-name";
                                }
                                description "IP filter";
                            }

                            leaf ipv6 {
                                type leafref {
                                    path "../../../../../../../filter/ipv6-filter/filter-name";
                                }
                                description "IPv6 filter";
                            }

                        } // container routed-override-filter

                    } // container egress

                    container ingress {
                        description "Enter the ingress context";

                        container routed-override-filter {
                            description "Enter the routed-override-filter context";

                            leaf ip {
                                type leafref {
                                    path "../../../../../../../filter/ip-filter/filter-name";
                                }
                                description "IP filter";
                            }

                            leaf ipv6 {
                                type leafref {
                                    path "../../../../../../../filter/ipv6-filter/filter-name";
                                }
                                description "IPv6 filter";
                            }

                        } // container routed-override-filter

                    } // container ingress

                } // list vpls

                container ipv6 {
                    presence "Enables/configures IPv6 for an interface.";
                    description "Enter the ipv6 context";

                    leaf qos-route-lookup {
                        type types-router:qos-route-lookup;
                        description "QoS Route lookup";
                    }

                    leaf forward-ipv4-packets {
                        type boolean;
                        default "false";
                        description "Forward unencapsulated IPv4 packets";
                    }

                    leaf tcp-mss {
                        type types-router:ipv6-tcp-mss-ext;
                        description "TCP maximum segment size for the interface";
                    }

                    leaf duplicate-address-detection {
                        type boolean;
                        default "true";
                        description "Enable/disable Duplicate Address Detection";
                    }

                    leaf local-dhcp-server {
                        when "../../tunnel = 'false'";
                        type leafref {
                            path "../../../dhcp-server/dhcpv6/name";
                        }
                        description "DHCP server for the interface";
                    }

                    container urpf-check {
                        presence "Enables uRPF information.";
                        description "Enter the urpf-check context";

                        leaf ignore-default {
                            type boolean;
                            default "false";
                            description "Ignore default route when performing a uRPF check";
                        }

                        leaf mode {
                            type types-router:urpf-check-mode;
                            default "strict";
                            description "Unicast RPF check mode";
                        }

                    } // container urpf-check

                    container icmp6 {
                        description "Enter the icmp6 context";

                        container packet-too-big {
                            description "Enter the packet-too-big context";

                            leaf admin-state {
                                type types-sros:admin-state;
                                default "enable";
                                description "Administrative state of packet-too-big messages";
                            }

                            leaf number {
                                type uint16 {
                                    range "10..1000";
                                }
                                default "100";
                                description "Number of packet-too-big messages";
                            }

                            leaf seconds {
                                type uint16 {
                                    range "1..60";
                                }
                                default "10";
                                description "Time to limit packet-too-big messages";
                            }

                        } // container packet-too-big

                        container param-problem {
                            description "Enter the param-problem context";

                            leaf admin-state {
                                type types-sros:admin-state;
                                default "enable";
                                description "Administrative state of param-problem messages";
                            }

                            leaf number {
                                type uint16 {
                                    range "10..1000";
                                }
                                default "100";
                                description "Number of parameter-problem messages";
                            }

                            leaf seconds {
                                type uint16 {
                                    range "1..60";
                                }
                                default "10";
                                description "Time to limit parameter problem messages";
                            }

                        } // container param-problem

                        container redirects {
                            description "Enter the redirects context";

                            leaf admin-state {
                                type types-sros:admin-state;
                                default "enable";
                                description "Administrative state of the redirect messages";
                            }

                            leaf number {
                                type uint16 {
                                    range "10..1000";
                                }
                                default "100";
                                description "Number of redirect messages";
                            }

                            leaf seconds {
                                type uint16 {
                                    range "1..60";
                                }
                                default "10";
                                description "Time to limit redirect messages";
                            }

                        } // container redirects

                        container time-exceeded {
                            description "Enter the time-exceeded context";

                            leaf admin-state {
                                type types-sros:admin-state;
                                default "enable";
                                description "Administrative state of the time-exceeded messages";
                            }

                            leaf number {
                                type uint16 {
                                    range "10..2000";
                                }
                                default "100";
                                description "Number of time-exceeded messages";
                            }

                            leaf seconds {
                                type uint16 {
                                    range "1..60";
                                }
                                default "10";
                                description "Time to limit time-exceeded messages";
                            }

                        } // container time-exceeded

                        container unreachables {
                            description "Enter the unreachables context";

                            leaf admin-state {
                                type types-sros:admin-state;
                                default "enable";
                                description "Administrative state of the unreachable messages";
                            }

                            leaf number {
                                type uint16 {
                                    range "10..2000";
                                }
                                default "100";
                                description "Number of unreachable messages";
                            }

                            leaf seconds {
                                type uint16 {
                                    range "1..60";
                                }
                                default "10";
                                description "Time to limit unreachable messages";
                            }

                        } // container unreachables

                    } // container icmp6

                    container bfd {
                        description "Enter the bfd context";

                        leaf admin-state {
                            type types-sros:admin-state;
                            default "disable";
                            description "Administrative state of BFD sessions";
                        }

                        leaf transmit-interval {
                            type uint32 {
                                range "10..100000";
                            }
                            units "milliseconds";
                            default "100";
                            description "BFD transmit interval over this interface";
                        }

                        leaf receive {
                            type uint32 {
                                range "10..100000";
                            }
                            units "milliseconds";
                            default "100";
                            description "BFD receive interval over this interface";
                        }

                        leaf multiplier {
                            type uint32 {
                                range "1..20";
                            }
                            default "3";
                            description "Number of consecutive BFD messages missed from the peer";
                        }

                        leaf echo-receive {
                            type uint32 {
                                range "100..100000";
                            }
                            units "milliseconds";
                            description "Minimum echo interval over this interface";
                        }

                        leaf type {
                            type enumeration {
                                enum "cpm-np"                       { value 1; }
                                enum "auto"                         { value 2; }
                                enum "fp"                           { value 3; }
                            }
                            default "auto";
                            description "Local termination point for BFD session";
                        }

                    } // container bfd

                    container link-local-address {
                        description "Enter the link-local-address context";

                        leaf address {
                            type types-sros:ipv6-address;
                            description "Link-local IPv6 address of this router interface";
                        }

                        leaf duplicate-address-detection {
                            type boolean;
                            default "true";
                            description "Enable/disable Duplicate Address Detection.";
                        }

                    } // container link-local-address

                    list address {
                        key "ipv6-address";
                        description "Enter the address list instance";

                        leaf ipv6-address {
                            type types-sros:ipv6-address;
                            description "IPv6 address assigned to the interface";
                        }

                        leaf prefix-length {
                            type uint32 {
                                range "0..128";
                            }
                            mandatory true;
                            description "IPv6 address prefix length";
                        }

                        leaf eui-64 {
                            type boolean;
                            sros-ext:immutable;
                            default "false";
                            description "Form complete IPv6 address from supplied prefix and 64-bit interface identifier";
                        }

                        leaf duplicate-address-detection {
                            type boolean;
                            sros-ext:immutable;
                            default "true";
                            description "Enable/disable Duplicate Address Detection.";
                        }

                        leaf primary-preference {
                            type uint32 {
                                range "1..4294967295";
                            }
                            description "Index assigned to the IPv6 address of the interface";
                        }

                        leaf-list apply-groups {
                            type leafref {
                                path "../../../../../../groups/group/name";
                            }
                            max-elements 8;
                            ordered-by user;
                            description "Apply a configuration group at this level";
                        }

                    } // list address

                    container dhcp6 {
                        when "../../tunnel = 'false'";
                        description "Enter the dhcp6 context";

                        leaf-list apply-groups {
                            type leafref {
                                path "../../../../../../groups/group/name";
                            }
                            max-elements 8;
                            ordered-by user;
                            description "Apply a configuration group at this level";
                        }

                        container relay {
                            description "Enter the relay context";

                            leaf description {
                                type types-sros:description;
                                description "Text description";
                            }

                            leaf admin-state {
                                type types-sros:admin-state;
                                default "disable";
                                description "Administrative state of DHCPv6 relay";
                            }

                            leaf link-address {
                                type types-sros:ipv6-address;
                                description "Link address of the DHCPv6 relay messages";
                            }

                            leaf neighbor-resolution {
                                type boolean;
                                default "false";
                                description "Enable neighbor resolution via DHCPv6 relay";
                            }

                            leaf python-policy {
                                type leafref {
                                    path "../../../../../../../python/python-policy/name";
                                }
                                description "Python policy name";
                            }

                            leaf source-address {
                                type types-sros:ipv6-unicast-or-linklocal-address;
                                description "Source IPv6 address of the DHCPv6 relay messages";
                            }

                            leaf user-db {
                                type leafref {
                                    path "../../../../../../../subscriber-mgmt/local-user-db/name";
                                }
                                description "Local user database for authentication";
                            }

                            leaf-list server {
                                type types-sros:ipv6-address-with-zone;
                                max-elements 8;
                                ordered-by user;
                                description "DHCPv6 server to which the DHCPv6 requests are forwarded";
                            }

                            leaf-list apply-groups {
                                type leafref {
                                    path "../../../../../../../groups/group/name";
                                }
                                max-elements 8;
                                ordered-by user;
                                description "Apply a configuration group at this level";
                            }

                            container lease-populate {
                                description "Enter the lease-populate context";

                                leaf max-nbr-of-leases {
                                    type int32 {
                                        range "0..32767";
                                    }
                                    default "0";
                                    description "Maximum number of lease states allocated by the DHCPv6 relay function, allowed on interface";
                                }

                                container route-populate {
                                    description "Enter the route-populate context";

                                    leaf na {
                                        type boolean;
                                        default "false";
                                        description "Create route based on IA_NA prefix option in relay-reply message";
                                    }

                                    leaf ta {
                                        type boolean;
                                        default "false";
                                        description "Create route based on IA_TA prefix option in relay-reply message";
                                    }

                                    container pd {
                                        presence
                                            "Specifies whether or not route-population PD via DHCP6 Relay
                                             must be enabled on this interface.";
                                        description "Enter the pd context";

                                        leaf exclude {
                                            type boolean;
                                            default "false";
                                            description "Create back hole route based on prefix exclude option in relay-reply message";
                                        }

                                    } // container pd

                                } // container route-populate

                            } // container lease-populate

                            container option {
                                description "Enter the option context";

                                leaf remote-id {
                                    type boolean;
                                    default "false";
                                    description "Allow remote ID option to be sent in the DHCPv6 relay packet";
                                }

                                leaf-list apply-groups {
                                    type leafref {
                                        path "../../../../../../../../groups/group/name";
                                    }
                                    max-elements 8;
                                    ordered-by user;
                                    description "Apply a configuration group at this level";
                                }

                                container interface-id {
                                    description "Enter the interface-id context";

                                    choice interface-id {
                                        case ascii-tuple {

                                            leaf ascii-tuple {
                                                type empty;
                                                description "Use ASCII-encoded concatenated tuple in interface ID option in DHCPv6 relay packet";
                                            }

                                        }
                                        case sap-id {

                                            leaf sap-id {
                                                type empty;
                                                description "Use SAP ID in interface ID option in DHCPv6 relay packet";
                                            }

                                        }
                                        case if-index {

                                            leaf if-index {
                                                type empty;
                                                description "Use interface index in interface ID option in DHCPv6 relay packet";
                                            }

                                        }
                                        case string {

                                            leaf string {
                                                type types-sros:string-not-all-spaces {
                                                    length "1..80";
                                                }
                                                description "String for interface ID option in DHCPv6 relay packet";
                                            }

                                        }
                                    }
                                } // container interface-id

                            } // container option

                        } // container relay

                        container server {
                            description "Enter the server context";

                            leaf max-nbr-of-leases {
                                type int32 {
                                    range "0..8000";
                                }
                                default "8000";
                                description "DHCPv6 leases allowed";
                            }

                            leaf-list apply-groups {
                                type leafref {
                                    path "../../../../../../../groups/group/name";
                                }
                                max-elements 8;
                                ordered-by user;
                                description "Apply a configuration group at this level";
                            }

                            container prefix-delegation {
                                description "Enter the prefix-delegation context";

                                leaf admin-state {
                                    type types-sros:admin-state;
                                    default "disable";
                                    description "Administrative state of the prefix delegation";
                                }

                                list prefix {
                                    key "ipv6-prefix";
                                    description "Enter the prefix list instance";

                                    leaf ipv6-prefix {
                                        type types-sros:ipv6-prefix;
                                        description "IPv6 prefix to be delegated";
                                    }

                                    leaf preferred-lifetime {
                                        type types-services:ipv6-prefix-lifetime;
                                        units "seconds";
                                        default "604800";
                                        description "IPv6 prefix/mask preferred life time";
                                    }

                                    leaf valid-lifetime {
                                        type types-services:ipv6-prefix-lifetime;
                                        units "seconds";
                                        default "2592000";
                                        description "IPv6 prefix/mask valid life time";
                                    }

                                    leaf-list apply-groups {
                                        type leafref {
                                            path "../../../../../../../../../groups/group/name";
                                        }
                                        max-elements 8;
                                        ordered-by user;
                                        description "Apply a configuration group at this level";
                                    }

                                    container client-id {
                                        description "Enter the client-id context";

                                        leaf duid {
                                            type string {
                                                length "1..130";
                                            }
                                            description "Requesting router ID";
                                        }

                                        leaf iaid {
                                            type uint32 {
                                                range "1..4294967295";
                                            }
                                            description "IAID from the requesting router that matches to delegate the prefix";
                                        }

                                    } // container client-id

                                } // list prefix

                            } // container prefix-delegation

                        } // container server

                    } // container dhcp6

                    container neighbor-discovery {
                        when "../../tunnel = 'false'";
                        description "Enter the neighbor-discovery context";

                        leaf reachable-time {
                            type types-router:neighbor-discovery-reachable-time;
                            description "Timer for neighbor reachability detection";
                        }

                        leaf stale-time {
                            type types-router:neighbor-discovery-stale-time;
                            description "Time during which a neighbor discovery cache entry remains stale";
                        }

                        leaf learn-unsolicited {
                            type types-router:ipv6-address-type-selection;
                            description "Type of entries learned from unsolicited NA messages";
                        }

                        leaf proactive-refresh {
                            type types-router:ipv6-address-type-selection;
                            description "Neighbor entries to be refreshed proactively";
                        }

                        leaf local-proxy-nd {
                            type boolean;
                            default "false";
                            description "Enable neighbor discovery on interface";
                        }

                        leaf-list proxy-nd-policy {
                            type leafref {
                                path "../../../../../../policy-options/policy-statement/name";
                            }
                            max-elements 5;
                            ordered-by user;
                            description "Name of the proxy Neighbor Discovery policies for the interface";
                        }

                        leaf populate-host {
                            status obsolete;
                            type boolean;
                            default "false";
                            description "Allow addition or deletion of host routes in route table derived from ARP entries in ARP cache";
                        }

                        leaf route-tag {
                            status obsolete;
                            type types-router:route-tag;
                            description "ARP route tag";
                        }

                        container host-route {
                            description "Configure which types of ARP or ND entries will be populated in the route-table.";

                            list populate {
                                key "route-type";

                                leaf route-type {
                                    type enumeration {
                                        enum "static"                       { value 1; }
                                        enum "dynamic"                      { value 2; }
                                        enum "evpn"                         { value 3; }
                                    }
                                    description "Controls what type of IPv4/IPv6 entries generate a host route.";
                                }

                                leaf route-tag {
                                    type uint32 {
                                        range "1..255";
                                    }
                                    sros-ext:immutable;
                                    description "Configure tag of the route.";
                                }

                                leaf-list apply-groups {
                                    type leafref {
                                        path "../../../../../../../../groups/group/name";
                                    }
                                    max-elements 8;
                                    ordered-by user;
                                    description "Apply a configuration group at this level";
                                }

                            } // list populate

                        } // container host-route

                        container secure-nd {
                            description "Enter the secure-nd context";

                            leaf allow-unsecured-msgs {
                                type boolean;
                                default "true";
                                description "Accept unsecured messages";
                            }

                            leaf public-key-min-bits {
                                type uint32 {
                                    range "512..1024";
                                }
                                default "1024";
                                description "Minimum acceptable key length for public keys";
                            }

                            leaf security-parameter {
                                type uint32 {
                                    range "0..1";
                                }
                                default "1";
                                description "Security parameter in the generation of a cryptographical address";
                            }

                            leaf admin-state {
                                type types-sros:admin-state;
                                default "disable";
                                description "Administrative state of secure neighbor discovery";
                            }

                        } // container secure-nd

                        container limit {
                            description "Enter the limit context";

                            leaf max-entries {
                                type types-router:ipv6-neighbor-limit;
                                description "Maximum number of entries that can be learned on an IP interface";
                            }

                            leaf log-only {
                                type boolean;
                                default "false";
                                description "Log warning messages at threshold or when limit is exceeded, however entries are learned above limit";
                            }

                            leaf threshold {
                                type uint32 {
                                    range "1..100";
                                }
                                units "percent";
                                default "90";
                                description "Threshold value that triggers a warning message to be sent";
                            }

                        } // container limit

                        list static-neighbor {
                            key "ipv6-address";
                            description "Enter the static-neighbor list instance";

                            leaf ipv6-address {
                                type types-sros:ipv6-address;
                                description "IPv6 address corresponding to the media-dependent physical address";
                            }

                            leaf mac-address {
                                type yang:mac-address;
                                mandatory true;
                                description "Media-dependent physical address";
                            }

                            leaf-list apply-groups {
                                type leafref {
                                    path "../../../../../../../groups/group/name";
                                }
                                max-elements 8;
                                ordered-by user;
                                description "Apply a configuration group at this level";
                            }

                        } // list static-neighbor

                    } // container neighbor-discovery

                    list vrrp {
                        key "virtual-router-id";
                        max-elements 1;
                        description "Enter the vrrp list instance";

                        leaf virtual-router-id {
                            type int32 {
                                range "1..255";
                            }
                            description "Virtual Router Identifier (VRID) for the VRRP virtual router instance";
                        }

                        leaf-list backup {
                            type types-sros:ipv6-address;
                            max-elements 4;
                            description "Virtual router IP addresses for the interface";
                        }

                        leaf message-interval {
                            type uint32 {
                                range "10..4095";
                            }
                            units "centiseconds";
                            default "100";
                            description "Interval for sending VRRP Advertisement messages";
                        }

                        leaf passive {
                            type boolean;
                            sros-ext:immutable;
                            default "false";
                            description "Suppress the transmission and reception of VRRP advertisement messages";
                        }

                        leaf init-delay {
                            type uint32 {
                                range "1..65535";
                            }
                            units "seconds";
                            description "VRRP initialization delay timer";
                        }

                        leaf mac {
                            type types-sros:mac-unicast-address;
                            description "MAC address used by virtual router instance overriding the VRRP default derived from the VRID";
                        }

                        leaf priority {
                            type uint32 {
                                range "1..255";
                            }
                            description "Base priority for the VRRP";
                        }

                        leaf oper-group {
                            type leafref {
                                path "../../../../../oper-group/name";
                            }
                            description "Operational group name associated with VRRP";
                        }

                        leaf-list apply-groups {
                            type leafref {
                                path "../../../../../../groups/group/name";
                            }
                            max-elements 8;
                            ordered-by user;
                            description "Apply a configuration group at this level";
                        }

                        choice owner-type {
                            default "non-owner";
                            case non-owner {

                                leaf admin-state {
                                    type types-sros:admin-state;
                                    default "enable";
                                    description "Administrative state of VRRP";
                                }

                                leaf master-int-inherit {
                                    type boolean;
                                    default "true";
                                    description "Allow the master instance to dictate the master down timer";
                                }

                                leaf ping-reply {
                                    type boolean;
                                    default "false";
                                    description "Allow non-owner master to reply to ICMP echo requests";
                                }

                                leaf policy {
                                    type leafref {
                                        path "../../../../../../vrrp/policy/policy-id";
                                    }
                                    description "VRRP priority control policy associated with the virtual router instance";
                                }

                                leaf preempt {
                                    type boolean;
                                    default "true";
                                    description "Allow the VRRP to override an existing non-owner master";
                                }

                                leaf telnet-reply {
                                    type boolean;
                                    default "false";
                                    description "Allow non-owner master to reply to Telnet requests";
                                }

                                leaf traceroute-reply {
                                    type boolean;
                                    default "false";
                                    description "Allow non-owner master to reply to traceroute requests";
                                }

                                leaf standby-forwarding {
                                    type boolean;
                                    default "false";
                                    description "Allow the forwarding of packets by a standby router";
                                }

                                leaf ntp-reply {
                                    type boolean;
                                    default "false";
                                    description "Allow/disallow non-owner master to reply to NTP requests.";
                                }

                            }
                            case owner {

                                leaf owner {
                                    type empty;
                                    sros-ext:immutable;
                                    description "Designate virtual router instance as owning the virtual router IP addresses";
                                }

                            }
                        }
                        container bfd-liveness {
                            presence "Enable bfd on this vrrp.";
                            description "Enter the bfd-liveness context";

                            leaf dest-ip {
                                type types-sros:ipv6-address;
                                sros-ext:immutable;
                                mandatory true;
                                description "ip-address.";
                            }

                            leaf service-name {
                                type types-services:service-name;
                                sros-ext:immutable;
                                description "Service name of interface running BFD";
                            }

                            leaf interface-name {
                                type types-sros:interface-name;
                                sros-ext:immutable;
                                mandatory true;
                                description "Name of interface running BFD";
                            }

                            leaf-list apply-groups {
                                type leafref {
                                    path "../../../../../../../groups/group/name";
                                }
                                max-elements 8;
                                ordered-by user;
                                description "Apply a configuration group at this level";
                            }

                        } // container bfd-liveness

                    } // list vrrp

                } // container ipv6

                container if-attribute {
                    description "Enter the if-attribute context";

                    leaf-list admin-group {
                        type leafref {
                            path "../../../../../routing-options/if-attribute/admin-group/group-name";
                        }
                        max-elements 32;
                        description "Names of the admin group memberships of the interface";
                    }

                    list srlg-group {
                        key "name";
                        description "Add a list entry for srlg-group";

                        leaf name {
                            type leafref {
                                path "../../../../../../routing-options/if-attribute/srlg-group/name";
                            }
                            description "Shared Risk Link Group (SRLG) name.";
                        }

                    } // list srlg-group

                } // container if-attribute

            } // list interface

            list network-interface {
                key "interface-name";
                description "Enter the network-interface list instance";

                leaf interface-name {
                    type types-sros:interface-name;
                    description "The administrative name assigned to this router interface. The interface name must be unique among entries with the same vRtrID value.";
                }

                leaf description {
                    type types-sros:very-long-description;
                    description "Text description";
                }

                leaf admin-state {
                    type types-sros:admin-state;
                    default "enable";
                    description "Administrative state of the interface";
                }

                leaf cpu-protection {
                    type leafref {
                        path "../../../../system/security/cpu-protection/policy/policy-id";
                    }
                    description "CPM Protection policy associated with an interface";
                }

                leaf ip-mtu {
                    type types-router:ip-mtu-ext;
                    units "bytes";
                    description "Interface IP MTU";
                }

                leaf mac {
                    type types-sros:mac-unicast-address;
                    description "MAC address for the interface";
                }

                leaf tos-marking-state {
                    type types-router:tos-marking-state;
                    default "trusted";
                    description "TOS marking state";
                }

                leaf dist-cpu-protection {
                    type leafref {
                        path "../../../../system/security/dist-cpu-protection/policy/policy-name";
                    }
                    description "Distributed CPU protection policy";
                }

                leaf ingress-stats {
                    type boolean;
                    default "false";
                    description "Collect ingress statistics";
                }

                leaf-list apply-groups {
                    type leafref {
                        path "../../../../groups/group/name";
                    }
                    max-elements 8;
                    ordered-by user;
                    description "Apply a configuration group at this level";
                }

                choice port-binding {
                    case port-encap {

                        leaf port {
                            type types-sros:port-and-encap;
                            description "Port to bind the interface";
                        }

                    }
                    case loopback {

                        leaf loopback {
                            type empty;
                            description "Use interface as a loopback interface";
                        }

                    }
                }
                container egress {
                    description "Enter the egress context";

                    container filter {
                        description "Enter the filter context";

                        leaf ip {
                            type leafref {
                                path "../../../../../../filter/ip-filter/filter-name";
                            }
                            description "IP filter";
                        }

                    } // container filter

                } // container egress

                container ingress {
                    description "Enter the ingress context";

                    container filter {
                        description "Enter the filter context";

                        leaf ip {
                            type leafref {
                                path "../../../../../../filter/ip-filter/filter-name";
                            }
                            description "IP filter";
                        }

                    } // container filter

                } // container ingress

                container load-balancing {
                    description "Enter the load-balancing context";

                    leaf lsr-load-balancing {
                        type types-router:lsr-load-balancing;
                        description "LSR load balancing algorithm";
                    }

                    leaf ip-load-balancing {
                        type types-router:ip-load-balancing;
                        default "both";
                        description "Configure IP load balancing algorithm.";
                    }

                    leaf spi-load-balancing {
                        type boolean;
                        default "false";
                        description "Allow use of SPI (Security Parameter Index) in hashing for ESP/AH encrypted IPv4/IPv6 traffic";
                    }

                    leaf teid-load-balancing {
                        type boolean;
                        default "false";
                        description "Include TEID in hashing algorithm for GTP-U/C encapsulated traffic";
                    }

                } // container load-balancing

                container lag {
                    description "Enter the lag context";

                    leaf link-map-profile {
                        type types-services:link-map-profile-id;
                        description "LAG link map profile applied to a SAP or network interface";
                    }

                    container per-link-hash {
                        description "Enter the per-link-hash context";

                        leaf class {
                            type types-services:sap-lag-per-link-hash-class;
                            default "1";
                            description "Class used on LAG egress when using weighted per-link-hash";
                        }

                        leaf weight {
                            type types-services:sap-lag-per-link-hash-weight;
                            default "1";
                            description "Weight used on LAG egress when using weighted per-link-hash";
                        }

                    } // container per-link-hash

                } // container lag

                container hold-time {
                    description "Enter the hold-time context";

                    container ipv4 {
                        description "Enter the ipv4 context";

                        container up {
                            description "Enter the up context";

                            leaf seconds {
                                type types-router:hold-time-seconds;
                                units "seconds";
                                description "Up hold time for the IP interface";
                            }

                        } // container up

                        container down {
                            description "Enter the down context";

                            leaf seconds {
                                type types-router:hold-time-seconds;
                                units "seconds";
                                description "Down hold time for the IP interface";
                            }

                            leaf init-only {
                                type boolean;
                                default "false";
                                description "Apply delay only at interface configuration or reboot";
                            }

                        } // container down

                    } // container ipv4

                } // container hold-time

                container cflowd-parameters {
                    description "Enter the cflowd-parameters context";

                    list sampling {
                        key "sampling-type";
                        description "Enter the sampling list instance";

                        leaf sampling-type {
                            type types-router:cflowd-sampling;
                            description "Unicast or multicast traffic";
                        }

                        leaf type {
                            when "not(../sampling-type = 'both')";
                            type enumeration {
                                enum "acl"                          { value 1; }
                                enum "interface"                    { value 2; }
                            }
                            mandatory true;
                            description "Type of cflowd analysis";
                        }

                        leaf direction {
                            type enumeration {
                                enum "ingress-only"                 { value 1; }
                                enum "egress-only"                  { value 2; }
                                enum "both"                         { value 3; }
                            }
                            default "ingress-only";
                            description "Direction of traffic for cflowd sampling";
                        }

                        leaf sample-profile {
                            type union {
                                type enumeration {
                                    enum "1"                            { value 1; }
                                }
                                type uint32;
                            }
                            description "Sample profile ID";
                        }

                        leaf-list apply-groups {
                            type leafref {
                                path "../../../../../../groups/group/name";
                            }
                            max-elements 8;
                            ordered-by user;
                            description "Apply a configuration group at this level";
                        }

                    } // list sampling

                } // container cflowd-parameters

                container qos {
                    description "Enter the qos context";

                    leaf network-policy {
                        type leafref {
                            path "../../../../../qos/network/network-policy-name";
                        }
                        description "Network policy name associated with a network interface";
                    }

                    leaf egress-port-redirect-group {
                        type leafref {
                            path "../../../../../qos/queue-group-templates/egress/queue-group/egress-queue-group-name";
                        }
                        description "QoS queue group name";
                    }

                    leaf egress-instance {
                        type types-services:qos-qgrp-instance-id;
                        description "Instance of the port egress queue group for this interface";
                    }

                    leaf ingress-fp-redirect-group {
                        type leafref {
                            path "../../../../../qos/queue-group-templates/ingress/queue-group/ingress-queue-group-name";
                        }
                        description "Forwarding-plane queue group policy for this interface";
                    }

                    leaf ingress-instance {
                        type types-services:qos-qgrp-instance-id;
                        description "Instance of the forwarding-plane ingress queue group for this interface";
                    }

                    leaf-list apply-groups {
                        type leafref {
                            path "../../../../../groups/group/name";
                        }
                        max-elements 8;
                        ordered-by user;
                        description "Apply a configuration group at this level";
                    }

                } // container qos

                container ipv4 {
                    description "Enter the ipv4 context";

                    leaf tcp-mss {
                        type types-router:ipv4-tcp-mss-ext;
                        description "TCP maximum segment size for the interface";
                    }

                    leaf allow-directed-broadcasts {
                        type boolean;
                        default "false";
                        description "Accept broadcasts that are directed to this interface";
                    }

                    container icmp {
                        description "Enter the icmp context";

                        leaf mask-reply {
                            type boolean;
                            default "true";
                            description "Allow responses to ICMP mask requests";
                        }

                        container redirects {
                            description "Enter the redirects context";

                            leaf admin-state {
                                type types-sros:admin-state;
                                default "enable";
                                description "Administrative state of sending ICMP redirects";
                            }

                            leaf number {
                                type uint16 {
                                    range "10..1000";
                                }
                                default "100";
                                description "Maximum number of ICMP redirect messages to send";
                            }

                            leaf seconds {
                                type uint16 {
                                    range "1..60";
                                }
                                units "seconds";
                                default "10";
                                description "Time used to limit the number of ICMP redirect messages";
                            }

                        } // container redirects

                        container ttl-expired {
                            description "Enter the ttl-expired context";

                            leaf admin-state {
                                type types-sros:admin-state;
                                default "enable";
                                description "Administrative state of sending TTL expired messages";
                            }

                            leaf number {
                                type uint16 {
                                    range "10..2000";
                                }
                                default "100";
                                description "Maximum number of TTL-expired messages to send";
                            }

                            leaf seconds {
                                type uint16 {
                                    range "1..60";
                                }
                                units "seconds";
                                default "10";
                                description "Time used to limit the number of TTL-expired messages";
                            }

                        } // container ttl-expired

                        container unreachables {
                            description "Enter the unreachables context";

                            leaf admin-state {
                                type types-sros:admin-state;
                                default "enable";
                                description "Administrative state of sending unreachable messages";
                            }

                            leaf number {
                                type uint16 {
                                    range "10..2000";
                                }
                                default "100";
                                description "Maximum number of unreachable messages to send";
                            }

                            leaf seconds {
                                type uint16 {
                                    range "1..60";
                                }
                                units "seconds";
                                default "10";
                                description "Time to limit the number of ICMP unreachable messages";
                            }

                        } // container unreachables

                        container param-problem {
                            description "Enter the param-problem context";

                            leaf admin-state {
                                type types-sros:admin-state;
                                default "enable";
                                description "Administrative state of sent Parameter Problem messages";
                            }

                            leaf number {
                                type uint32 {
                                    range "10..1000";
                                }
                                default "100";
                                description "Maximum number of parameter problem messages to send";
                            }

                            leaf seconds {
                                type uint32 {
                                    range "1..60";
                                }
                                units "seconds";
                                default "10";
                                description "Time used to limit number of parameter problem messages";
                            }

                        } // container param-problem

                    } // container icmp

                    container urpf-check {
                        presence "Enables/Configures unicast RPF check on this interface.";
                        description "Enter the urpf-check context";

                        leaf ignore-default {
                            type boolean;
                            default "false";
                            description "Ignore default route when performing a uRPF check";
                        }

                        leaf mode {
                            type types-router:urpf-check-mode;
                            default "strict";
                            description "Unicast RPF check mode";
                        }

                    } // container urpf-check

                    container primary {
                        presence "Primary IPv4 address for this router interface.";
                        description "Enter the primary context";

                        leaf address {
                            type types-sros:ipv4-unicast-address;
                            mandatory true;
                            description "Primary IPv4 address assigned to the interface";
                        }

                        leaf prefix-length {
                            type uint32 {
                                range "0..32";
                            }
                            mandatory true;
                            description "IPv4 address prefix length";
                        }

                        leaf broadcast {
                            type types-services:broadcast-address-format;
                            default "host-ones";
                            description "Broadcast address format";
                        }

                        leaf-list apply-groups {
                            type leafref {
                                path "../../../../../../groups/group/name";
                            }
                            max-elements 8;
                            ordered-by user;
                            description "Apply a configuration group at this level";
                        }

                    } // container primary

                    list secondary {
                        key "address";
                        description "Enter the secondary list instance";

                        leaf address {
                            type types-sros:ipv4-unicast-address;
                            description "Secondary IPv4 address assigned to the interface";
                        }

                        leaf prefix-length {
                            type uint32 {
                                range "0..32";
                            }
                            mandatory true;
                            description "IPv4 address prefix length";
                        }

                        leaf igp-inhibit {
                            type boolean;
                            default "false";
                            description "Secondary IP address that is not recognized as local interface by the running IGP";
                        }

                        leaf broadcast {
                            type types-services:broadcast-address-format;
                            default "host-ones";
                            description "Broadcast address format";
                        }

                        leaf-list apply-groups {
                            type leafref {
                                path "../../../../../../groups/group/name";
                            }
                            max-elements 8;
                            ordered-by user;
                            description "Apply a configuration group at this level";
                        }

                    } // list secondary

                    container bfd {
                        description "Enter the bfd context";

                        leaf admin-state {
                            type types-sros:admin-state;
                            default "disable";
                            description "Administrative state of BFD sessions";
                        }

                        leaf transmit-interval {
                            type uint32 {
                                range "10..100000";
                            }
                            units "milliseconds";
                            default "100";
                            description "BFD transmit interval over this interface";
                        }

                        leaf receive {
                            type uint32 {
                                range "10..100000";
                            }
                            units "milliseconds";
                            default "100";
                            description "BFD receive interval over this interface";
                        }

                        leaf multiplier {
                            type uint32 {
                                range "1..20";
                            }
                            default "3";
                            description "Number of consecutive BFD messages missed from the peer";
                        }

                        leaf echo-receive {
                            type uint32 {
                                range "100..100000";
                            }
                            units "milliseconds";
                            description "Minimum echo interval over this interface";
                        }

                        leaf type {
                            type enumeration {
                                enum "cpm-np"                       { value 1; }
                                enum "auto"                         { value 2; }
                                enum "fp"                           { value 3; }
                            }
                            default "auto";
                            description "Local termination point for BFD session";
                        }

                    } // container bfd

                    container neighbor-discovery {
                        description "Enter the neighbor-discovery context";

                        leaf timeout {
                            type uint32 {
                                range "0..65535";
                            }
                            units "seconds";
                            default "14400";
                            description "Timeout for an ARP entry learned on the interface";
                        }

                        leaf retry-timer {
                            type uint32 {
                                range "1..300";
                            }
                            units "deciseconds";
                            default "50";
                            description "ARP retry interval";
                        }

                        list static-neighbor {
                            key "ipv4-address";
                            description "Enter the static-neighbor list instance";

                            leaf ipv4-address {
                                type types-sros:ipv4-address;
                                description "IPv4 address corresponding to the media-dependent physical address";
                            }

                            leaf mac-address {
                                type yang:mac-address;
                                mandatory true;
                                description "Media-dependent physical address";
                            }

                            leaf-list apply-groups {
                                type leafref {
                                    path "../../../../../../../groups/group/name";
                                }
                                max-elements 8;
                                ordered-by user;
                                description "Apply a configuration group at this level";
                            }

                        } // list static-neighbor

                    } // container neighbor-discovery

                } // container ipv4

            } // list network-interface

            list redundant-interface {
                key "interface-name";
                description "Enter the redundant-interface list instance";

                leaf interface-name {
                    type types-sros:interface-name;
                    description "Name of the interface";
                }

                leaf description {
                    type types-sros:very-long-description;
                    description "Text description";
                }

                leaf admin-state {
                    type types-sros:admin-state;
                    default "enable";
                    description "Administrative state of the interface";
                }

                leaf ip-mtu {
                    type types-router:ip-mtu-ext;
                    units "bytes";
                    description "Interface IP MTU";
                }

                leaf-list apply-groups {
                    type leafref {
                        path "../../../../groups/group/name";
                    }
                    max-elements 8;
                    ordered-by user;
                    description "Apply a configuration group at this level";
                }

                container hold-time {
                    description "Enter the hold-time context";

                    container ipv4 {
                        description "Enter the ipv4 context";

                        container up {
                            description "Enter the up context";

                            leaf seconds {
                                type types-router:hold-time-seconds;
                                units "seconds";
                                description "Up hold time for the IP interface";
                            }

                        } // container up

                        container down {
                            description "Enter the down context";

                            leaf seconds {
                                type types-router:hold-time-seconds;
                                units "seconds";
                                description "Down hold time for the IP interface";
                            }

                            leaf init-only {
                                type boolean;
                                default "false";
                                description "Apply delay only at interface configuration or reboot";
                            }

                        } // container down

                    } // container ipv4

                } // container hold-time

                list spoke-sdp {
                    key "sdp-bind-id";
                    max-elements 1;
                    description "Enter the spoke-sdp list instance";

                    leaf sdp-bind-id {
                        type types-services:sdp-bind-id;
                        description "SDP Binding identifier as <sdp-id>:<vc-id>. sdp-id - [1..32767] vc-id - [1..4294967295].";
                    }

                    leaf description {
                        type types-sros:description;
                        description "Text description";
                    }

                    leaf admin-state {
                        type types-sros:admin-state;
                        default "enable";
                        description "Administrative state of the SDP binding to the service";
                    }

                    leaf control-word {
                        type boolean;
                        default "false";
                        description "Use the control word as preferred";
                    }

                    leaf-list apply-groups {
                        type leafref {
                            path "../../../../../groups/group/name";
                        }
                        max-elements 8;
                        ordered-by user;
                        description "Apply a configuration group at this level";
                    }

                    container ingress {
                        description "Enter the ingress context";

                        leaf vc-label {
                            type types-services:ingress-vc-label;
                            sros-ext:auto-restart-to-modify;
                            description "Static MPLS VC label used by the far end device to send packets through this SDP";
                        }

                        container filter {
                            description "Enter the filter context";

                            leaf ip {
                                type leafref {
                                    path "../../../../../../../filter/ip-filter/filter-name";
                                }
                                description "IP filter ID";
                            }

                        } // container filter

                    } // container ingress

                    container egress {
                        description "Enter the egress context";

                        leaf vc-label {
                            type types-services:egress-vc-label;
                            sros-ext:auto-restart-to-modify;
                            description "Static MPLS VC label that is used to send packets to the far end device through this SDP";
                        }

                        container filter {
                            description "Enter the filter context";

                            leaf ip {
                                type leafref {
                                    path "../../../../../../../filter/ip-filter/filter-name";
                                }
                                description "IP filter ID";
                            }

                        } // container filter

                    } // container egress

                } // list spoke-sdp

                container ipv4 {
                    description "Enter the ipv4 context";

                    container primary {
                        presence "Assigns an IP address/IP subnet format and a remote IP.";
                        description "Enter the primary context";

                        leaf address {
                            type types-sros:ipv4-unicast-address;
                            mandatory true;
                            description "IPv4 address to be assigned to the interface";
                        }

                        leaf prefix-length {
                            type uint32 {
                                range "0..32";
                            }
                            mandatory true;
                            description "The prefix length 0..32 for IPv4 Address.";
                        }

                        leaf remote-ip {
                            type types-sros:ipv4-unicast-address;
                            description "IP address of the remote redundant interface.";
                        }

                        leaf-list apply-groups {
                            type leafref {
                                path "../../../../../../groups/group/name";
                            }
                            max-elements 8;
                            ordered-by user;
                            description "Apply a configuration group at this level";
                        }

                    } // container primary

                } // container ipv4

            } // list redundant-interface

            list ip-mirror-interface {
                key "interface-name";
                description "Enter the ip-mirror-interface list instance";

                leaf interface-name {
                    type types-sros:interface-name;
                    description "Name of the interface";
                }

                leaf description {
                    type types-sros:very-long-description;
                    description "Text description";
                }

                leaf admin-state {
                    type types-sros:admin-state;
                    default "enable";
                    description "Administrative state of the interface";
                }

                leaf-list apply-groups {
                    type leafref {
                        path "../../../../groups/group/name";
                    }
                    max-elements 8;
                    ordered-by user;
                    description "Apply a configuration group at this level";
                }

                list spoke-sdp {
                    key "sdp-bind-id";
                    max-elements 1;
                    description "Enter the spoke-sdp list instance";

                    leaf sdp-bind-id {
                        type types-services:sdp-bind-id;
                        description "SDP Binding identifier as <sdp-id>:<vc-id>. sdp-id - [1..32767] vc-id - [1..4294967295].";
                    }

                    leaf description {
                        type types-sros:description;
                        description "Text description";
                    }

                    leaf admin-state {
                        type types-sros:admin-state;
                        default "enable";
                        description "Administrative state of the SDP binding to the service";
                    }

                    leaf-list apply-groups {
                        type leafref {
                            path "../../../../../groups/group/name";
                        }
                        max-elements 8;
                        ordered-by user;
                        description "Apply a configuration group at this level";
                    }

                    container ingress {
                        description "Enter the ingress context";

                        leaf vc-label {
                            type types-services:ingress-vc-label;
                            sros-ext:auto-restart-to-modify;
                            description "Static MPLS VC label used by the far end device to send packets through this SDP";
                        }

                        container filter {
                            description "Enter the filter context";

                            leaf ip {
                                type leafref {
                                    path "../../../../../../../filter/ip-filter/filter-name";
                                }
                                description "IP filter identifier";
                            }

                        } // container filter

                    } // container ingress

                } // list spoke-sdp

            } // list ip-mirror-interface

            container ipv6 {
                description "Enter the ipv6 context";

                container neighbor-discovery {
                    description "Enter the neighbor-discovery context";

                    leaf reachable-time {
                        type types-router:neighbor-discovery-reachable-time;
                        default "30";
                        description "Timer for neighbor reachability detection";
                    }

                    leaf stale-time {
                        type types-router:neighbor-discovery-stale-time;
                        default "14400";
                        description "Neighbor discovery cache entry stale time";
                    }

                } // container neighbor-discovery

                container router-advertisement {
                    description "Enter the router-advertisement context";

                    leaf-list apply-groups {
                        type leafref {
                            path "../../../../../groups/group/name";
                        }
                        max-elements 8;
                        ordered-by user;
                        description "Apply a configuration group at this level";
                    }

                    container dns-options {
                        presence "Enables DNS functionality on this router.";
                        description "Enter the dns-options context";

                        leaf rdnss-lifetime {
                            type union {
                                type enumeration {
                                    enum "infinite"                     { value -1; }
                                }
                                type int32 {
                                    range "0|4..3600";
                                }
                            }
                            units "seconds";
                            default "infinite";
                            description "Maximum time over which the RDNSS address is valid";
                        }

                        leaf-list server {
                            type types-sros:ipv6-address;
                            max-elements 4;
                            ordered-by user;
                            description "Router advertisements that are forwarded to servers";
                        }

                        leaf-list apply-groups {
                            type leafref {
                                path "../../../../../../groups/group/name";
                            }
                            max-elements 8;
                            ordered-by user;
                            description "Apply a configuration group at this level";
                        }

                    } // container dns-options

                    list interface {
                        key "ip-int-name";
                        description "Enter the interface list instance";

                        leaf ip-int-name {
                            type leafref {
                                path "../../../../interface/interface-name";
                            }
                            description "VPRN interface name";
                        }

                        leaf current-hop-limit {
                            type uint16 {
                                range "0..255";
                            }
                            default "64";
                            description "Hop limit to advertise in router advertisement messages";
                        }

                        leaf managed-configuration {
                            type boolean;
                            default "false";
                            description "Set the managed address configuration flag";
                        }

                        leaf max-advertisement-interval {
                            type uint32 {
                                range "4..1800";
                            }
                            units "seconds";
                            default "600";
                            description "Maximum time between sending router advertisement msgs";
                        }

                        leaf min-advertisement-interval {
                            type uint32 {
                                range "3..1350";
                            }
                            units "seconds";
                            default "200";
                            description "Minimum time between sending router advertisement msgs";
                        }

                        leaf mtu {
                            type uint32 {
                                range "1280..9800";
                            }
                            description "MTU for sending packets to the router";
                        }

                        leaf other-stateful-configuration {
                            type boolean;
                            default "false";
                            description "Set the other configuration flag";
                        }

                        leaf reachable-time {
                            type uint32 {
                                range "0..3600000";
                            }
                            units "milliseconds";
                            default "0";
                            description "Time the router is reachable by other hosts or nodes";
                        }

                        leaf retransmit-time {
                            type uint32 {
                                range "0..1800000";
                            }
                            units "milliseconds";
                            default "0";
                            description "Time to advertise ICMPv6 ND router advertisement msgs";
                        }

                        leaf router-lifetime {
                            type uint32 {
                                range "0|4..9000";
                            }
                            units "seconds";
                            default "1800";
                            description "Lifetime value in ICMPv6 ND router advertisement msgs";
                        }

                        leaf admin-state {
                            type types-sros:admin-state;
                            default "disable";
                            description "Administrative state of router advertisement";
                        }

                        leaf use-virtual-mac {
                            type boolean;
                            default "false";
                            description "Send router advert msg using VRRP virtual MAC addr";
                        }

                        leaf-list apply-groups {
                            type leafref {
                                path "../../../../../../groups/group/name";
                            }
                            max-elements 8;
                            ordered-by user;
                            description "Apply a configuration group at this level";
                        }

                        container dns-options {
                            presence "Enables DNS functionality on this interface.";
                            description "Enter the dns-options context";

                            leaf include-rdnss {
                                type boolean;
                                default "true";
                                description "Include the RDNSS option in the router advertisement";
                            }

                            leaf rdnss-lifetime {
                                type union {
                                    type int32 {
                                        range "0|4..3600";
                                    }
                                    type enumeration {
                                        enum "infinite"                     { value -1; }
                                    }
                                }
                                units "seconds";
                                description "Maximum time over which the RDNSS address 25 is valid";
                            }

                            leaf-list server {
                                type types-sros:ipv6-address;
                                max-elements 4;
                                ordered-by user;
                                description "Router advertisements that are forwarded to servers";
                            }

                            leaf-list apply-groups {
                                type leafref {
                                    path "../../../../../../../groups/group/name";
                                }
                                max-elements 8;
                                ordered-by user;
                                description "Apply a configuration group at this level";
                            }

                        } // container dns-options

                        list prefix {
                            key "ipv6-prefix";
                            max-elements 254;
                            description "Enter the prefix list instance";

                            leaf ipv6-prefix {
                                type types-sros:ipv6-prefix;
                                description "IPv6 address prefix";
                            }

                            leaf autonomous {
                                type boolean;
                                default "true";
                                description "Set the autonomous flag value";
                            }

                            leaf on-link {
                                type boolean;
                                default "true";
                                description "Use prefix for on-link determination";
                            }

                            leaf preferred-lifetime {
                                type union {
                                    type enumeration {
                                        enum "infinite"                     { value -1; }
                                    }
                                    type uint32 {
                                        range "0..4294967294";
                                    }
                                }
                                units "seconds";
                                default "604800";
                                description "Remaining time that the prefix remains preferred";
                            }

                            leaf valid-lifetime {
                                type union {
                                    type enumeration {
                                        enum "infinite"                     { value -1; }
                                    }
                                    type uint32 {
                                        range "0..4294967294";
                                    }
                                }
                                units "seconds";
                                default "2592000";
                                description "Remaining time in which the prefix is still valid";
                            }

                            leaf-list apply-groups {
                                type leafref {
                                    path "../../../../../../../groups/group/name";
                                }
                                max-elements 8;
                                ordered-by user;
                                description "Apply a configuration group at this level";
                            }

                        } // list prefix

                    } // list interface

                } // container router-advertisement

            } // container ipv6

            list spoke-sdp {
                key "sdp-bind-id";
                description "Enter the spoke-sdp list instance";

                leaf sdp-bind-id {
                    type types-services:sdp-bind-id;
                    description "SDP Binding identifier as <sdp-id>:<vc-id>. sdp-id - [1..32767] vc-id - [1..4294967295].";
                }

                leaf description {
                    type types-sros:description;
                    description "Text description";
                }

                leaf-list apply-groups {
                    type leafref {
                        path "../../../../groups/group/name";
                    }
                    max-elements 8;
                    ordered-by user;
                    description "Apply a configuration group at this level";
                }

            } // list spoke-sdp

            container source-address {
                description "Enter the source-address context";

                list ipv4 {
                    key "application";
                    description "Enter the ipv4 list instance";

                    leaf application {
                        type enumeration {
                            enum "telnet"                       { value 1; }
                            enum "ssh"                          { value 3; }
                            enum "ping"                         { value 8; }
                            enum "traceroute"                   { value 9; }
                            enum "ntp"                          { value 12; }
                            enum "cflowd"                       { value 13; }
                            enum "ptp"                          { value 23; }
                            enum "icmp-error"                   { value 29; }
                        }
                        description "Source IP address for the application";
                    }

                    leaf-list apply-groups {
                        type leafref {
                            path "../../../../../groups/group/name";
                        }
                        max-elements 8;
                        ordered-by user;
                        description "Apply a configuration group at this level";
                    }

                    choice source {
                        mandatory true;
                        case interface-name {

                            leaf interface-name {
                                type types-sros:interface-name;
                                sros-ext:immutable;
                                description "Interface name whose IP address to be used in all packets sent by the application";
                            }

                        }
                        case address {

                            leaf address {
                                type types-sros:ipv4-address;
                                sros-ext:immutable;
                                description "Source IPv4 address to be used in all packets sent by the application";
                            }

                        }
                    }
                } // list ipv4

                list ipv6 {
                    key "application";
                    description "Enter the ipv6 list instance";

                    leaf application {
                        type enumeration {
                            enum "telnet"                       { value 14; }
                            enum "ping"                         { value 20; }
                            enum "traceroute"                   { value 21; }
                            enum "cflowd"                       { value 25; }
                            enum "ntp"                          { value 26; }
                            enum "icmp6-error"                  { value 30; }
                        }
                        description "Source IPv6 address for the application";
                    }

                    leaf address {
                        type types-sros:ipv6-address;
                        sros-ext:immutable;
                        mandatory true;
                        description "Source IPv6 address to be used in all packets sent by the application";
                    }

                    leaf-list apply-groups {
                        type leafref {
                            path "../../../../../groups/group/name";
                        }
                        max-elements 8;
                        ordered-by user;
                        description "Apply a configuration group at this level";
                    }

                } // list ipv6

            } // container source-address

            container static-routes {
                description "Enter the static-routes context";

                leaf-list apply-groups {
                    type leafref {
                        path "../../../../groups/group/name";
                    }
                    max-elements 8;
                    ordered-by user;
                    description "Apply a configuration group at this level";
                }

                container hold-down {
                    presence "Enable/Disable hold down time for all static-routes on this router instance.";
                    description "Enter the hold-down context";

                    leaf initial {
                        type uint32 {
                            range "1..65535";
                        }
                        mandatory true;
                        description "Value for the initial hold down time";
                    }

                    leaf multiplier {
                        type uint32 {
                            range "1..10";
                        }
                        mandatory true;
                        description "Value by which the previous hold-down time is multiplied to calculate the new one";
                    }

                    leaf max-value {
                        type uint32 {
                            range "1..65535";
                        }
                        mandatory true;
                        description "Maximum value of the hold down time";
                    }

                } // container hold-down

                list route {
                    key "ip-prefix route-type";
                    description "Enter the route list instance";

                    leaf ip-prefix {
                        type types-sros:ip-prefix;
                        description "IP prefix and prefix length for the static routes";
                    }

                    leaf route-type {
                        type types-router:unicast-multicast;
                        description "Indicates the type of that static-route being configured, either for unicast routing or for use with multicast rpf.";
                    }

                    leaf-list community {
                        type types-sros:community;
                        max-elements 12;
                        ordered-by user;
                        description "Community ID associated with the static route";
                    }

                    leaf tag {
                        type uint32 {
                            range "1..max";
                        }
                        description "Static route tag";
                    }

                    leaf-list apply-groups {
                        type leafref {
                            path "../../../../../groups/group/name";
                        }
                        max-elements 8;
                        ordered-by user;
                        description "Apply a configuration group at this level";
                    }

                    container blackhole {
                        presence "Enables blackhole next-hop for static-routes-entry.";
                        description "Enter the blackhole context";

                        leaf description {
                            type types-sros:description-allow-all-white-spaces;
                            description "Text description";
                        }

                        leaf metric {
                            type uint32 {
                                range "0..65535";
                            }
                            default "1";
                            description "Static route metric";
                        }

                        leaf preference {
                            type uint32 {
                                range "1..255";
                            }
                            default "5";
                            description "Priority of this static route over the routes from different sources";
                        }

                        leaf tag {
                            type uint32 {
                                range "1..max";
                            }
                            description "Static route tag";
                        }

                        leaf community {
                            type types-sros:community;
                            description "Community ID associated with the static route";
                        }

                        leaf admin-state {
                            type types-sros:admin-state;
                            description "Administrative state of the static route next hop";
                        }

                        leaf generate-icmp {
                            type boolean;
                            default "false";
                            description "Send ICMP unreachable messages when received packets match a static route with black-hole next-hop";
                        }

                        leaf-list apply-groups {
                            type leafref {
                                path "../../../../../../groups/group/name";
                            }
                            max-elements 8;
                            ordered-by user;
                            description "Apply a configuration group at this level";
                        }

                        container prefix-list {
                            description "Enter the prefix-list context";

                            leaf name {
                                type leafref {
                                    path "../../../../../../../policy-options/prefix-list/name";
                                }
                                description "Name of a prefix list to match";
                            }

                            leaf flag {
                                type enumeration {
                                    enum "any"                          { value 0; }
                                    enum "all"                          { value 1; }
                                    enum "none"                         { value 2; }
                                }
                                default "any";
                                description "Static route match condition from prefixes in specified prefix list";
                            }

                        } // container prefix-list

                    } // container blackhole

                    container grt {
                        presence "Enables grt next-hop for static-routes-entry.";
                        description "Enter the grt context";

                        leaf description {
                            type types-sros:description-allow-all-white-spaces;
                            description "Text description";
                        }

                        leaf metric {
                            type uint32 {
                                range "0..65535";
                            }
                            default "1";
                            description "Static route metric";
                        }

                        leaf preference {
                            type uint32 {
                                range "1..255";
                            }
                            default "5";
                            description "Priority of this static route over the routes from different sources";
                        }

                        leaf admin-state {
                            type types-sros:admin-state;
                            description "Administrative state of the static route next hop";
                        }

                        leaf-list apply-groups {
                            type leafref {
                                path "../../../../../../groups/group/name";
                            }
                            max-elements 8;
                            ordered-by user;
                            description "Apply a configuration group at this level";
                        }

                    } // container grt

                    list indirect {
                        key "ip-address";
                        description "Enter the indirect list instance";

                        leaf ip-address {
                            type types-sros:ip-address;
                            description "Indirect next hop for static routes";
                        }

                        leaf description {
                            type types-sros:description-allow-all-white-spaces;
                            description "Text description";
                        }

                        leaf metric {
                            type uint32 {
                                range "0..65535";
                            }
                            default "1";
                            description "Static route metric";
                        }

                        leaf preference {
                            type uint32 {
                                range "1..255";
                            }
                            default "5";
                            description "Priority of this static route over the routes from different sources";
                        }

                        leaf tag {
                            type uint32 {
                                range "1..max";
                            }
                            description "Static route tag";
                        }

                        leaf community {
                            type types-sros:community;
                            description "Community ID associated with the static route";
                        }

                        leaf destination-class {
                            type types-sros:class-index;
                            description "Destination class for this static route";
                        }

                        leaf source-class {
                            type types-sros:class-index;
                            description "Source class for this static route";
                        }

                        leaf admin-state {
                            type types-sros:admin-state;
                            description "Administrative state of the static route next hop";
                        }

                        leaf-list apply-groups {
                            type leafref {
                                path "../../../../../../groups/group/name";
                            }
                            max-elements 8;
                            ordered-by user;
                            description "Apply a configuration group at this level";
                        }

                        container qos {
                            description "Enter the qos context";

                            leaf forwarding-class {
                                type types-sros:fc-name;
                                description "Forwarding class associated with the static route";
                            }

                            leaf priority {
                                type types-sros:priority;
                                description "Static route priority";
                            }

                        } // container qos

                        container prefix-list {
                            description "Enter the prefix-list context";

                            leaf name {
                                type leafref {
                                    path "../../../../../../../policy-options/prefix-list/name";
                                }
                                description "Name of a prefix list to match";
                            }

                            leaf flag {
                                type enumeration {
                                    enum "any"                          { value 0; }
                                    enum "all"                          { value 1; }
                                    enum "none"                         { value 2; }
                                }
                                default "any";
                                description "Static route match condition from prefixes in specified prefix list";
                            }

                        } // container prefix-list

                        list cpe-check {
                            key "address";
                            max-elements 1;
                            description "Enter the cpe-check list instance";

                            leaf address {
                                type types-sros:ip-address;
                                description "IP address of the target CPE device.";
                            }

                            leaf drop-count {
                                type uint32 {
                                    range "1..255";
                                }
                                default "3";
                                description "Number of consecutive ping replies that are missed before declaring the CPE down";
                            }

                            leaf interval {
                                type uint32 {
                                    range "1..255";
                                }
                                units "seconds";
                                default "1";
                                description "Time between ICMP pings to the target CPE IP address";
                            }

                            leaf log {
                                type boolean;
                                default "false";
                                description "Log the transitions between active and inactive based on the CPE connectivity check";
                            }

                            leaf padding-size {
                                type uint32 {
                                    range "0..16384";
                                }
                                units "bytes";
                                default "56";
                                description "Padding size for the ICMP ping test packet of the CPE connectivity check";
                            }

                            leaf-list apply-groups {
                                type leafref {
                                    path "../../../../../../../groups/group/name";
                                }
                                max-elements 8;
                                ordered-by user;
                                description "Apply a configuration group at this level";
                            }

                        } // list cpe-check

                    } // list indirect

                    list interface {
                        key "interface-name";
                        description "Enter the interface list instance";

                        leaf interface-name {
                            type types-sros:interface-name;
                            description "Router interface name.";
                        }

                        leaf description {
                            type types-sros:description-allow-all-white-spaces;
                            description "Text description";
                        }

                        leaf metric {
                            type uint32 {
                                range "0..65535";
                            }
                            default "1";
                            description "Static route metric";
                        }

                        leaf preference {
                            type uint32 {
                                range "1..255";
                            }
                            default "5";
                            description "Priority of this static route over the routes from different sources";
                        }

                        leaf tag {
                            type uint32 {
                                range "1..max";
                            }
                            description "Static route tag";
                        }

                        leaf community {
                            type types-sros:community;
                            description "Community ID associated with the static route";
                        }

                        leaf destination-class {
                            type types-sros:class-index;
                            description "Destination class for this static route";
                        }

                        leaf source-class {
                            type types-sros:class-index;
                            description "Source class for this static route";
                        }

                        leaf load-balancing-weight {
                            type uint32 {
                                range "1..max";
                            }
                            description "Load-balancing weight for all of the ECMP next hops";
                        }

                        leaf admin-state {
                            type types-sros:admin-state;
                            description "Administrative state of the static route next hop";
                        }

                        leaf-list apply-groups {
                            type leafref {
                                path "../../../../../../groups/group/name";
                            }
                            max-elements 8;
                            ordered-by user;
                            description "Apply a configuration group at this level";
                        }

                        container qos {
                            description "Enter the qos context";

                            leaf forwarding-class {
                                type types-sros:fc-name;
                                description "Forwarding class associated with the static route";
                            }

                            leaf priority {
                                type types-sros:priority;
                                description "Static route priority";
                            }

                        } // container qos

                        container prefix-list {
                            description "Enter the prefix-list context";

                            leaf name {
                                type leafref {
                                    path "../../../../../../../policy-options/prefix-list/name";
                                }
                                description "Name of a prefix list to match";
                            }

                            leaf flag {
                                type enumeration {
                                    enum "any"                          { value 0; }
                                    enum "all"                          { value 1; }
                                    enum "none"                         { value 2; }
                                }
                                default "any";
                                description "Static route match condition from prefixes in specified prefix list";
                            }

                        } // container prefix-list

                        list cpe-check {
                            key "address";
                            max-elements 1;
                            description "Enter the cpe-check list instance";

                            leaf address {
                                type types-sros:ip-address;
                                description "IP address of the target CPE device.";
                            }

                            leaf drop-count {
                                type uint32 {
                                    range "1..255";
                                }
                                default "3";
                                description "Number of consecutive ping replies that are missed before declaring the CPE down";
                            }

                            leaf interval {
                                type uint32 {
                                    range "1..255";
                                }
                                units "seconds";
                                default "1";
                                description "Time between ICMP pings to the target CPE IP address";
                            }

                            leaf log {
                                type boolean;
                                default "false";
                                description "Log the transitions between active and inactive based on the CPE connectivity check";
                            }

                            leaf padding-size {
                                type uint32 {
                                    range "0..16384";
                                }
                                units "bytes";
                                default "56";
                                description "Padding size for the ICMP ping test packet of the CPE connectivity check";
                            }

                            leaf-list apply-groups {
                                type leafref {
                                    path "../../../../../../../groups/group/name";
                                }
                                max-elements 8;
                                ordered-by user;
                                description "Apply a configuration group at this level";
                            }

                        } // list cpe-check

                    } // list interface

                    list ipsec-tunnel {
                        key "ipsec-tunnel-name";
                        description "Enter the ipsec-tunnel list instance";

                        leaf ipsec-tunnel-name {
                            type types-sros:named-item;
                            description "Ipsec tunnel name.";
                        }

                        leaf description {
                            type types-sros:description-allow-all-white-spaces;
                            description "Text description";
                        }

                        leaf metric {
                            type uint32 {
                                range "0..65535";
                            }
                            default "1";
                            description "Static route metric";
                        }

                        leaf preference {
                            type uint32 {
                                range "1..255";
                            }
                            default "5";
                            description "Priority of this static route over the routes from different sources";
                        }

                        leaf tag {
                            type uint32 {
                                range "1..max";
                            }
                            description "Static route tag";
                        }

                        leaf community {
                            type types-sros:community;
                            description "Community ID associated with the static route";
                        }

                        leaf destination-class {
                            type types-sros:class-index;
                            description "Destination class for this static route";
                        }

                        leaf source-class {
                            type types-sros:class-index;
                            description "Source class for this static route";
                        }

                        leaf admin-state {
                            type types-sros:admin-state;
                            description "Administrative state of the static route next hop";
                        }

                        leaf-list apply-groups {
                            type leafref {
                                path "../../../../../../groups/group/name";
                            }
                            max-elements 8;
                            ordered-by user;
                            description "Apply a configuration group at this level";
                        }

                        container qos {
                            description "Enter the qos context";

                            leaf forwarding-class {
                                type types-sros:fc-name;
                                description "Forwarding class associated with the static route";
                            }

                            leaf priority {
                                type types-sros:priority;
                                description "Static route priority";
                            }

                        } // container qos

                    } // list ipsec-tunnel

                    list next-hop {
                        key "ip-address";
                        description "Enter the next-hop list instance";

                        leaf ip-address {
                            type types-sros:ip-address-with-zone;
                            description "IP address of the next-hop.";
                        }

                        leaf description {
                            type types-sros:description-allow-all-white-spaces;
                            description "Text description";
                        }

                        leaf metric {
                            type uint32 {
                                range "0..65535";
                            }
                            default "1";
                            description "Static route metric";
                        }

                        leaf preference {
                            type uint32 {
                                range "1..255";
                            }
                            default "5";
                            description "Priority of this static route over the routes from different sources";
                        }

                        leaf tag {
                            type uint32 {
                                range "1..max";
                            }
                            description "Static route tag";
                        }

                        leaf community {
                            type types-sros:community;
                            description "Community ID associated with the static route";
                        }

                        leaf destination-class {
                            type types-sros:class-index;
                            description "Destination class for this static route";
                        }

                        leaf source-class {
                            type types-sros:class-index;
                            description "Source class for this static route";
                        }

                        leaf bfd-liveness {
                            type boolean;
                            default "false";
                            description "Use Bidirectional Forwarding Detection on this static route";
                        }

                        leaf validate-next-hop {
                            type boolean;
                            default "false";
                            description "Track the state of the next hop in the IPv4 ARP Cache or the IPv6 Neighbor Cache";
                        }

                        leaf load-balancing-weight {
                            type uint32 {
                                range "1..max";
                            }
                            description "Load-balancing weight for all of the ECMP next hops";
                        }

                        leaf admin-state {
                            type types-sros:admin-state;
                            description "Administrative state of the static route next hop";
                        }

                        leaf-list apply-groups {
                            type leafref {
                                path "../../../../../../groups/group/name";
                            }
                            max-elements 8;
                            ordered-by user;
                            description "Apply a configuration group at this level";
                        }

                        container qos {
                            description "Enter the qos context";

                            leaf forwarding-class {
                                type types-sros:fc-name;
                                description "Forwarding class associated with the static route";
                            }

                            leaf priority {
                                type types-sros:priority;
                                description "Static route priority";
                            }

                        } // container qos

                        container prefix-list {
                            description "Enter the prefix-list context";

                            leaf name {
                                type leafref {
                                    path "../../../../../../../policy-options/prefix-list/name";
                                }
                                description "Name of a prefix list to match";
                            }

                            leaf flag {
                                type enumeration {
                                    enum "any"                          { value 0; }
                                    enum "all"                          { value 1; }
                                    enum "none"                         { value 2; }
                                }
                                default "any";
                                description "Static route match condition from prefixes in specified prefix list";
                            }

                        } // container prefix-list

                        list cpe-check {
                            key "address";
                            max-elements 1;
                            description "Enter the cpe-check list instance";

                            leaf address {
                                type types-sros:ip-address;
                                description "IP address of the target CPE device.";
                            }

                            leaf drop-count {
                                type uint32 {
                                    range "1..255";
                                }
                                default "3";
                                description "Number of consecutive ping replies that are missed before declaring the CPE down";
                            }

                            leaf interval {
                                type uint32 {
                                    range "1..255";
                                }
                                units "seconds";
                                default "1";
                                description "Time between ICMP pings to the target CPE IP address";
                            }

                            leaf log {
                                type boolean;
                                default "false";
                                description "Log the transitions between active and inactive based on the CPE connectivity check";
                            }

                            leaf padding-size {
                                type uint32 {
                                    range "0..16384";
                                }
                                units "bytes";
                                default "56";
                                description "Padding size for the ICMP ping test packet of the CPE connectivity check";
                            }

                            leaf-list apply-groups {
                                type leafref {
                                    path "../../../../../../../groups/group/name";
                                }
                                max-elements 8;
                                ordered-by user;
                                description "Apply a configuration group at this level";
                            }

                        } // list cpe-check

                    } // list next-hop

                } // list route

            } // container static-routes

            container flowspec {
                description "Enter the flowspec context";

                leaf ip-filter-max-size {
                    type uint32 {
                        range "0..262143";
                    }
                    default "512";
                    description "Maximum number of flowspec rule entries in IPv4 filter";
                }

                leaf ipv6-filter-max-size {
                    type uint32 {
                        range "0..262143";
                    }
                    default "512";
                    description "Maximum number of flowspec rule entries in IPv6 filter";
                }

                leaf-list apply-groups {
                    type leafref {
                        path "../../../../groups/group/name";
                    }
                    max-elements 8;
                    ordered-by user;
                    description "Apply a configuration group at this level";
                }

            } // container flowspec

            container log {
                description "Enter the log context";

                leaf-list apply-groups {
                    type leafref {
                        path "../../../../groups/group/name";
                    }
                    max-elements 8;
                    ordered-by user;
                    description "Apply a configuration group at this level";
                }

                list filter {
                    key "filter-id";
                    description "Enter the filter list instance";

                    leaf filter-id {
                        type uint32 {
                            range "1..1500";
                        }
                        description "Identification number for an event log filter";
                    }

                    leaf description {
                        type types-sros:description;
                        description "Text description";
                    }

                    leaf default-action {
                        type types-log:filter-action;
                        default "forward";
                        description "Default action for the event filter";
                    }

                    leaf-list apply-groups {
                        type leafref {
                            path "../../../../../groups/group/name";
                        }
                        max-elements 8;
                        ordered-by user;
                        description "Apply a configuration group at this level";
                    }

                    list entry {
                        key "entry-id";
                        description "Enter the entry list instance";

                        leaf entry-id {
                            type uint32 {
                                range "1..999";
                            }
                            description "Identification number for an event log filter parameter";
                        }

                        leaf description {
                            type types-sros:description;
                            description "Text description";
                        }

                        leaf action {
                            type types-log:filter-action;
                            description "Action for this event filter entry";
                        }

                        leaf-list apply-groups {
                            type leafref {
                                path "../../../../../../groups/group/name";
                            }
                            max-elements 8;
                            ordered-by user;
                            description "Apply a configuration group at this level";
                        }

                        container match {
                            description "Enter the match context";

                            container application {
                                description "Enter the application context";

                                choice application-match {
                                    case eq {

                                        leaf eq {
                                            type types-log:application;
                                            description "Application to match";
                                        }

                                    }
                                    case neq {

                                        leaf neq {
                                            type types-log:application;
                                            description "Application to be filtered out";
                                        }

                                    }
                                }
                            } // container application

                            container message {
                                description "Enter the message context";

                                leaf regexp {
                                    type boolean;
                                    default "false";
                                    description "String comparison to determine if the log event matches the value of pattern";
                                }

                                choice message-match {
                                    case eq {

                                        leaf eq {
                                            type string {
                                                length "1..400";
                                            }
                                            description "Log event message to match";
                                        }

                                    }
                                    case neq {

                                        leaf neq {
                                            type string {
                                                length "1..400";
                                            }
                                            description "Log event message to be filtered out";
                                        }

                                    }
                                }
                            } // container message

                            container event {
                                description "Enter the event context";

                                choice event-match {
                                    case eq {

                                        leaf eq {
                                            type uint32 {
                                                range "1..max";
                                            }
                                            description "Log event message to match";
                                        }

                                    }
                                    case neq {

                                        leaf neq {
                                            type uint32 {
                                                range "1..max";
                                            }
                                            description "Log event message to filter out";
                                        }

                                    }
                                    case lt {

                                        leaf lt {
                                            type uint32 {
                                                range "1..max";
                                            }
                                            description "Number of the log event to match";
                                        }

                                    }
                                    case lte {

                                        leaf lte {
                                            type uint32 {
                                                range "1..max";
                                            }
                                            description "Number of the log event to match";
                                        }

                                    }
                                    case gt {

                                        leaf gt {
                                            type uint32 {
                                                range "1..max";
                                            }
                                            description "Number of the log event to match";
                                        }

                                    }
                                    case gte {

                                        leaf gte {
                                            type uint32 {
                                                range "1..max";
                                            }
                                            description "Number of the log event to match";
                                        }

                                    }
                                }
                            } // container event

                            container severity {
                                description "Enter the severity context";

                                choice severity-match {
                                    case eq {

                                        leaf eq {
                                            type types-log:severity-level;
                                            description "Log event severity level to match";
                                        }

                                    }
                                    case neq {

                                        leaf neq {
                                            type types-log:severity-level;
                                            description "Log event severity level to filter out";
                                        }

                                    }
                                    case lt {

                                        leaf lt {
                                            type types-log:severity-level;
                                            description "Log event severity level";
                                        }

                                    }
                                    case lte {

                                        leaf lte {
                                            type types-log:severity-level;
                                            description "Log event severity level";
                                        }

                                    }
                                    case gt {

                                        leaf gt {
                                            type types-log:severity-level;
                                            description "Log event severity level";
                                        }

                                    }
                                    case gte {

                                        leaf gte {
                                            type types-log:severity-level;
                                            description "Log event severity level";
                                        }

                                    }
                                }
                            } // container severity

                            container subject {
                                description "Enter the subject context";

                                leaf regexp {
                                    type boolean;
                                    default "false";
                                    description "String comparison to determine if the log event matches the value of subject";
                                }

                                choice subject-match {
                                    case eq {

                                        leaf eq {
                                            type types-sros:named-item;
                                            description "Log event subject string to match";
                                        }

                                    }
                                    case neq {

                                        leaf neq {
                                            type types-sros:named-item;
                                            description "Log event subject string to filter out";
                                        }

                                    }
                                }
                            } // container subject

                        } // container match

                    } // list entry

                } // list filter

                list log-id {
                    key "id";
                    max-elements 30;
                    description "Enter the log-id list instance";

                    leaf id {
                        type int32 {
                            range "1..100";
                        }
                        description "The value of id uniquely identifies an event stream log.";
                    }

                    leaf admin-state {
                        type types-sros:admin-state;
                        default "enable";
                        description "Administrative state of the log";
                    }

                    leaf description {
                        type types-sros:description;
                        description "Text description";
                    }

                    leaf netconf-stream {
                        type types-sros:named-item;
                        description "Destination NETCONF stream name";
                    }

                    leaf time-format {
                        type enumeration {
                            enum "utc"                          { value 1; }
                            enum "local"                        { value 2; }
                        }
                        default "utc";
                        description "Timestamp format for events sent to logs which have a value of either syslog, or file";
                    }

                    leaf filter {
                        type leafref {
                            path "../../filter/filter-id";
                        }
                        description "Filter for this log's source event stream to limit the event output in this log destination";
                    }

                    leaf python-policy {
                        type leafref {
                            path "../../../../../python/python-policy/name";
                        }
                        description "Python policy name";
                    }

                    leaf-list apply-groups {
                        type leafref {
                            path "../../../../../groups/group/name";
                        }
                        max-elements 8;
                        ordered-by user;
                        description "Apply a configuration group at this level";
                    }

                    container source {
                        description "Enter the source context";

                        leaf main {
                            type boolean;
                            default "false";
                            description "Source event streams main of log events";
                        }

                        leaf security {
                            type boolean;
                            default "false";
                            description "Source event streams security of log events";
                        }

                        leaf change {
                            type boolean;
                            default "false";
                            description "Source event streams change of log events";
                        }

                        leaf debug {
                            type boolean;
                            default "false";
                            description "Source event streams debug of log events";
                        }

                    } // container source

                    container destination {
                        description "Enter the destination context";

                        choice log-id-destination {
                            case syslog {

                                leaf syslog {
                                    type leafref {
                                        path "../../../syslog/syslog-id";
                                    }
                                    sros-ext:immutable;
                                    description "Index with the information to format event messages sent to a specific SYSLOG collector";
                                }

                            }
                            case snmp {

                                container snmp {
                                    presence "Send log events to the snmp-trap-group that has the same id as this log.";
                                    description "Enter the snmp context";

                                    leaf max-entries {
                                        type uint32 {
                                            range "50..3000";
                                        }
                                        sros-ext:immutable;
                                        default "100";
                                        description "Number of events stored in this snmp log.";
                                    }

                                } // container snmp

                            }
                            case netconf {

                                container netconf {
                                    presence "Send log events to the netconf.";
                                    description "Enter the netconf context";

                                    leaf max-entries {
                                        type uint32 {
                                            range "50..3000";
                                        }
                                        sros-ext:immutable;
                                        default "100";
                                        description "Number of events stored in this netconf log.";
                                    }

                                } // container netconf

                            }
                        }
                    } // container destination

                } // list log-id

                list snmp-trap-group {
                    key "log-id";
                    description "Enter the snmp-trap-group list instance";

                    leaf log-id {
                        type int32 {
                            range "1..100";
                        }
                        description "SNMP notification group associated with the event log";
                    }

                    leaf description {
                        type types-sros:description;
                        description "Text description";
                    }

                    leaf-list apply-groups {
                        type leafref {
                            path "../../../../../groups/group/name";
                        }
                        max-elements 8;
                        ordered-by user;
                        description "Apply a configuration group at this level";
                    }

                    list trap-target {
                        key "name";
                        max-elements 25;
                        description "Enter the trap-target list instance";

                        leaf name {
                            type string {
                                length "1..28";
                            }
                            description "Name for an SNMP notification destination within the SNMP notification group";
                        }

                        leaf description {
                            type types-sros:description;
                            description "Text description";
                        }

                        leaf address {
                            type types-sros:ip-unicast-address;
                            mandatory true;
                            description "IP address of the trap receiver";
                        }

                        leaf port {
                            type types-qos:tcp-udp-match-port;
                            default "162";
                            description "UDP port number to send messages to this remote SNMP notification collector";
                        }

                        leaf version {
                            type enumeration {
                                enum "snmpv1"                       { value 0; }
                                enum "snmpv2c"                      { value 1; }
                                enum "snmpv3"                       { value 3; }
                            }
                            default "snmpv3";
                            description "SNMP version to format notification messages sent to this SNMP notification collector";
                        }

                        leaf notify-community {
                            type string {
                                length "1..31";
                            }
                            mandatory true;
                            description "SNMPv1 or SNMPv2c community name string, or SNMPv3 security name, for sending a notification";
                        }

                        leaf security-level {
                            type enumeration {
                                enum "no-auth-no-privacy"           { value 1; }
                                enum "auth-no-privacy"              { value 2; }
                                enum "privacy"                      { value 3; }
                            }
                            default "no-auth-no-privacy";
                            description "Security level at which SNMP notification messages are sent to SNMP notification collector";
                        }

                        leaf replay {
                            type boolean;
                            default "false";
                            description "Retransmit missed notifications";
                        }

                        leaf-list apply-groups {
                            type leafref {
                                path "../../../../../../groups/group/name";
                            }
                            max-elements 8;
                            ordered-by user;
                            description "Apply a configuration group at this level";
                        }

                    } // list trap-target

                } // list snmp-trap-group

                list syslog {
                    key "syslog-id";
                    description "Enter the syslog list instance";

                    leaf syslog-id {
                        type int32 {
                            range "1..30";
                        }
                        description "Unique arbitrary identifier for this SYSLOG collector target";
                    }

                    leaf description {
                        type types-sros:description;
                        description "Text description";
                    }

                    leaf address {
                        type types-sros:ip-unicast-address;
                        description "Target syslog host address";
                    }

                    leaf facility {
                        type enumeration {
                            enum "kernel"                       { value 0; }
                            enum "user"                         { value 1; }
                            enum "mail"                         { value 2; }
                            enum "systemd"                      { value 3; }
                            enum "auth"                         { value 4; }
                            enum "syslogd"                      { value 5; }
                            enum "printer"                      { value 6; }
                            enum "netnews"                      { value 7; }
                            enum "uucp"                         { value 8; }
                            enum "cron"                         { value 9; }
                            enum "authpriv"                     { value 10; }
                            enum "ftp"                          { value 11; }
                            enum "ntp"                          { value 12; }
                            enum "logaudit"                     { value 13; }
                            enum "logalert"                     { value 14; }
                            enum "cron2"                        { value 15; }
                            enum "local0"                       { value 16; }
                            enum "local1"                       { value 17; }
                            enum "local2"                       { value 18; }
                            enum "local3"                       { value 19; }
                            enum "local4"                       { value 20; }
                            enum "local5"                       { value 21; }
                            enum "local6"                       { value 22; }
                            enum "local7"                       { value 23; }
                        }
                        default "local7";
                        description "Facility code for messages";
                    }

                    leaf severity {
                        type enumeration {
                            enum "emergency"                    { value 0; }
                            enum "alert"                        { value 1; }
                            enum "critical"                     { value 2; }
                            enum "error"                        { value 3; }
                            enum "warning"                      { value 4; }
                            enum "notice"                       { value 5; }
                            enum "info"                         { value 6; }
                            enum "debug"                        { value 7; }
                        }
                        default "info";
                        description "Severity level threshold for the syslog message";
                    }

                    leaf log-prefix {
                        type union {
                            type enumeration {
                                enum "no-prefix"                    { value -1; }
                            }
                            type string {
                                length "1..32";
                                pattern "([!-9;<>-~])+" {
                                    error-message "String must contain only printable characters between 33 - 126 ASCII except ':' and '='";
                                }
                            }
                        }
                        default "TMNX";
                        description "String that is prepended to every log message sent to this target syslog host";
                    }

                    leaf port {
                        type types-qos:tcp-udp-match-port;
                        default "514";
                        description "UDP port to generate syslog messages";
                    }

                    leaf-list apply-groups {
                        type leafref {
                            path "../../../../../groups/group/name";
                        }
                        max-elements 8;
                        ordered-by user;
                        description "Apply a configuration group at this level";
                    }

                } // list syslog

            } // container log

            container igmp-host-tracking {
                description "Enter the igmp-host-tracking context";

                leaf admin-state {
                    type types-sros:admin-state;
                    default "disable";
                    description "Administrative state of IGMP host tracking";
                }

                leaf expiry-time {
                    type types-sros:time-duration {
                        range "1..65535";
                    }
                    units "seconds";
                    default "260";
                    description "Time during which the system continues to track inactive hosts";
                }

                leaf-list apply-groups {
                    type leafref {
                        path "../../../../groups/group/name";
                    }
                    max-elements 8;
                    ordered-by user;
                    description "Apply a configuration group at this level";
                }

            } // container igmp-host-tracking

            container pcp {
                description "Enter the pcp context";

                list server {
                    key "name";
                    max-elements 8;
                    description "Enter the server list instance";

                    leaf name {
                        type types-sros:named-item;
                        description "PCP server name";
                    }

                    leaf admin-state {
                        type types-sros:admin-state;
                        default "disable";
                        description "Administrative state of this PCP server";
                    }

                    leaf description {
                        type types-sros:description;
                        description "Text description";
                    }

                    leaf dual-stack-lite-address {
                        type types-sros:ipv6-unicast-address;
                        description "Inside Dual Stack Lite AFTR address";
                    }

                    leaf fwd-inside-router {
                        type string;
                        description "PCP forwarding inside virtual router instance";
                    }

                    leaf policy {
                        type leafref {
                            path "../../../../nat/pcp-server-policy/name";
                        }
                        description "PCP server policy";
                    }

                    leaf-list apply-groups {
                        type leafref {
                            path "../../../../../groups/group/name";
                        }
                        max-elements 8;
                        ordered-by user;
                        description "Apply a configuration group at this level";
                    }

                    list interface {
                        key "name";
                        max-elements 32;
                        description "Add a list entry for interface";

                        leaf name {
                            type leafref {
                                path "../../../../interface/interface-name";
                            }
                            description "Interface name";
                        }

                    } // list interface

                } // list server

            } // container pcp

            container bgp-vpn-backup {
                description "Enter the bgp-vpn-backup context";

                leaf ipv4 {
                    type boolean;
                    default "false";
                    description "Allows BGP-VPN routes to be used as backup paths for IPv4 prefixes.";
                }

                leaf ipv6 {
                    type boolean;
                    default "false";
                    description "Allows BGP-VPN routes to be used as backup paths for IPv6 prefixes.";
                }

            } // container bgp-vpn-backup

            container grt-leaking {
                description "Enter the grt-leaking context";

                leaf export-limit {
                    type uint32 {
                        range "0..1000";
                    }
                    default "5";
                    description "Maximum number of routes that can be exported.";
                }

                leaf export-v6-limit {
                    type uint32 {
                        range "0..1000";
                    }
                    default "5";
                    description "Maximum number of IPv6 routes that can be exported.";
                }

                leaf grt-lookup {
                    type boolean;
                    default "false";
                    description "Enable/disable global route table lookup.";
                }

                leaf allow-local-management {
                    type boolean;
                    default "false";
                    description "Enable/disable management traffic from GRT-leaking enabled VPRN instances to reach local interfaces in the base routing instance.";
                }

                leaf-list apply-groups {
                    type leafref {
                        path "../../../../groups/group/name";
                    }
                    max-elements 8;
                    ordered-by user;
                    description "Apply a configuration group at this level";
                }

                container export-grt {
                    description "Enter the export-grt context";

                    leaf-list policy-name {
                        type string {
                            length "1..255";
                            pattern "(.{1,64})|(.*[\\[].*)" {
                                error-message "Policy name too long or expression not valid.";
                            }
                        }
                        max-elements 5;
                        ordered-by user;
                        description "Attribute policy-name for export-grt.";
                    }

                } // container export-grt

                container import-grt {
                    description "Enter the import-grt context";

                    leaf-list policy-name {
                        type string {
                            length "1..255";
                            pattern "(.{1,64})|(.*[\\[].*)" {
                                error-message "Policy name too long or expression not valid.";
                            }
                        }
                        max-elements 5;
                        ordered-by user;
                        description "Attribute policy-name for import-grt.";
                    }

                } // container import-grt

            } // container grt-leaking

            container gsmp {
                description "Enter the gsmp context";

                leaf admin-state {
                    type types-sros:admin-state;
                    default "disable";
                    description "Administrative state of GSMP";
                }

                leaf-list apply-groups {
                    type leafref {
                        path "../../../../groups/group/name";
                    }
                    max-elements 8;
                    ordered-by user;
                    description "Apply a configuration group at this level";
                }

                list group {
                    key "name";
                    max-elements 1024;
                    description "Enter the group list instance";

                    leaf name {
                        type types-sros:named-item;
                        description "GSMP neighbor group name";
                    }

                    leaf admin-state {
                        type types-sros:admin-state;
                        default "disable";
                        description "Administrative state of the GSMP group";
                    }

                    leaf description {
                        type types-sros:description;
                        description "Text description";
                    }

                    leaf keepalive {
                        type types-sros:time-duration {
                            range "1..25";
                        }
                        units "seconds";
                        default "10";
                        description "Keepalive value for the GSMP connections in this group";
                    }

                    leaf hold-multiplier {
                        type uint32 {
                            range "1..100";
                        }
                        default "3";
                        description "Hold-multiplier for the GSMP connections in this group";
                    }

                    leaf persistency {
                        type boolean;
                        default "false";
                        description "Store DSL line information when the GSMP connection terminates";
                    }

                    leaf idle-filter {
                        type boolean;
                        default "false";
                        description "Filter ANCP messages from IDLE DSL lines";
                    }

                    leaf-list apply-groups {
                        type leafref {
                            path "../../../../../groups/group/name";
                        }
                        max-elements 8;
                        ordered-by user;
                        description "Apply a configuration group at this level";
                    }

                    container ancp {
                        description "Enter the ancp context";

                        leaf dynamic-topology-discovery {
                            type boolean;
                            default "true";
                            description "Enable the ANCP dynamic topology discovery capability";
                        }

                        leaf oam {
                            type boolean;
                            default "false";
                            description "Enable GSMP ANCP OAM capability at startup of GSMP connection";
                        }

                    } // container ancp

                    list neighbor {
                        key "remote-address";
                        description "Enter the neighbor list instance";

                        leaf remote-address {
                            type types-sros:ipv4-unicast-address;
                            description "GSMP neighbor remote IP address";
                        }

                        leaf admin-state {
                            type types-sros:admin-state;
                            default "disable";
                            description "Administrative state of the GSMP neighbor";
                        }

                        leaf description {
                            type types-sros:description;
                            description "Text description";
                        }

                        leaf local-address {
                            type types-sros:ipv4-unicast-address;
                            sros-ext:auto-restart-to-modify;
                            description "Restrict connections to this local address only within the service running ANCP";
                        }

                        leaf-list apply-groups {
                            type leafref {
                                path "../../../../../../groups/group/name";
                            }
                            max-elements 8;
                            ordered-by user;
                            sros-ext:auto-restart-to-modify;
                            description "Apply a configuration group at this level";
                        }

                        container priority-marking {
                            sros-ext:auto-restart-to-modify;
                            description "Enter the priority-marking context";

                            choice priority-marking {
                                case dscp {

                                    leaf dscp {
                                        type types-qos:dscp-name;
                                        sros-ext:auto-restart-to-modify;
                                        description "DSCP that is used while remarking the in profile packets";
                                    }

                                }
                                case prec {

                                    leaf prec {
                                        type types-qos:precedence-value;
                                        sros-ext:auto-restart-to-modify;
                                        description "Precedence priority marking";
                                    }

                                }
                            }
                        } // container priority-marking

                    } // list neighbor

                } // list group

            } // container gsmp

            container vxlan {
                description "Enter the vxlan context";

                list tunnel-termination {
                    key "ip-address";
                    description "Enter the tunnel-termination list instance";

                    leaf ip-address {
                        type types-sros:ip-unicast-address;
                        description "Non system IP address to terminate the VXLAN";
                    }

                    leaf fpe-id {
                        type leafref {
                            path "../../../../../fwd-path-ext/fpe/fpe-id";
                        }
                        sros-ext:immutable;
                        mandatory true;
                        description "FPE id for this entry";
                    }

                    leaf-list apply-groups {
                        type leafref {
                            path "../../../../../groups/group/name";
                        }
                        max-elements 8;
                        ordered-by user;
                        description "Apply a configuration group at this level";
                    }

                } // list tunnel-termination

            } // container vxlan

            container ttl-propagate {
                description "Enter the ttl-propagate context";

                leaf local {
                    type types-router:vprn-ttl-propagate;
                    default "use-base";
                    description "Manage TTL propagation from IP header into label stack for local packets.";
                }

                leaf transit {
                    type types-router:vprn-ttl-propagate;
                    default "use-base";
                    description "Manage TTL propagation from IP header into label stack for transit packets.";
                }

            } // container ttl-propagate

            container sgt-qos {
                description "Enter the sgt-qos context";

                container dscp {
                    description "Enter the dscp context";

                    list application {
                        key "dscp-app-name";
                        description "Enter the application list instance";

                        leaf dscp-app-name {
                            type types-router:dscp-app-name-vprn;
                            description "DSCP application identifier on the NOKIA SR OS router that generates control traffic over IP";
                        }

                        leaf dscp {
                            type union {
                                type types-qos:dscp-name;
                                type int32 {
                                    range "0..63";
                                }
                            }
                            description "DSCP value to the traffic generated by this application";
                        }

                        leaf-list apply-groups {
                            type leafref {
                                path "../../../../../../groups/group/name";
                            }
                            max-elements 8;
                            ordered-by user;
                            description "Apply a configuration group at this level";
                        }

                    } // list application

                    list dscp-map {
                        key "dscp-name";
                        description "Enter the dscp-map list instance";

                        leaf dscp-name {
                            type types-qos:dscp-name;
                            description "DSCP name mapped to forwarding class";
                        }

                        leaf fc {
                            type types-sros:fc-name;
                            description "Value for the forwarding class for this mapping";
                        }

                        leaf-list apply-groups {
                            type leafref {
                                path "../../../../../../groups/group/name";
                            }
                            max-elements 8;
                            ordered-by user;
                            description "Apply a configuration group at this level";
                        }

                    } // list dscp-map

                } // container dscp

                container dot1p {
                    description "Enter the dot1p context";

                    list application {
                        key "dot1p-app-name";
                        description "Enter the application list instance";

                        leaf dot1p-app-name {
                            type types-router:dot1p-app-name;
                            description "Dot1p application identifier on the NOKIA SR OS router that generates control traffic over IP";
                        }

                        leaf dot1p {
                            type union {
                                type types-sros:fc-name;
                                type int32 {
                                    range "0..7";
                                }
                            }
                            description "Dot1p value to the traffic generated by this application";
                        }

                        leaf-list apply-groups {
                            type leafref {
                                path "../../../../../../groups/group/name";
                            }
                            max-elements 8;
                            ordered-by user;
                            description "Apply a configuration group at this level";
                        }

                    } // list application

                } // container dot1p

            } // container sgt-qos

            container snmp {
                description "Enter the snmp context";

                leaf access {
                    type boolean;
                    default "false";
                    description "Enable/Disable SNMP access for the vprn service";
                }

                list community {
                    key "community-string";
                    description "Enter the community list instance";

                    leaf community-string {
                        type types-sros:encrypted-leaf {
                            length "1..114";
                        }
                        description "Community string for which this entry represents a configuration. community-string - [64 chars max] hash-key - [113 chars max] hash2-key - [114 chars max]";
                    }

                    leaf access-permissions {
                        type enumeration {
                            enum "r"                            { value 1; }
                            enum "rw"                           { value 2; }
                        }
                        mandatory true;
                        description "Community string for which this entry represents a configuration.";
                    }

                    leaf version {
                        type enumeration {
                            enum "v1"                           { value 1; }
                            enum "v2c"                          { value 2; }
                            enum "both"                         { value 3; }
                        }
                        default "both";
                        description "SNMP version.";
                    }

                    leaf source-access-list {
                        type leafref {
                            path "../../../../../system/security/snmp/source-access-list/list-name";
                        }
                        description "The context in which management information is accessed when using the community string.";
                    }

                    leaf-list apply-groups {
                        type leafref {
                            path "../../../../../groups/group/name";
                        }
                        max-elements 8;
                        ordered-by user;
                        description "Apply a configuration group at this level";
                    }

                } // list community

            } // container snmp

            container network {
                description "Enter the network context";

                leaf-list apply-groups {
                    type leafref {
                        path "../../../../groups/group/name";
                    }
                    max-elements 8;
                    ordered-by user;
                    description "Apply a configuration group at this level";
                }

                container ingress {
                    description "Enter the ingress context";

                    leaf urpf-check {
                        type boolean;
                        default "true";
                        description "Enable/disable URPF checking when the network interface is in selective VPRN mode";
                    }

                    container qos {
                        description "Enter the qos context";

                        leaf network-policy {
                            type leafref {
                                path "../../../../../../qos/network/network-policy-name";
                            }
                            description "Network policy name associated with a VPRN";
                        }

                        leaf fp-redirect-group {
                            type leafref {
                                path "../../../../../../qos/queue-group-templates/ingress/queue-group/ingress-queue-group-name";
                            }
                            description "The forwarding-plane queue group Policy for this VPRN";
                        }

                        leaf instance {
                            type types-services:qos-qgrp-instance-id;
                            description "The instance of the forwarding-plane ingress Queue Group for this VPRN";
                        }

                    } // container qos

                    container filter {
                        description "Enter the filter context";

                        leaf ip {
                            type leafref {
                                path "../../../../../../filter/ip-filter/filter-name";
                            }
                            description "Apply IP filter";
                        }

                        leaf ipv6 {
                            type leafref {
                                path "../../../../../../filter/ipv6-filter/filter-name";
                            }
                            description "Apply IPv6 filter";
                        }

                    } // container filter

                } // container ingress

            } // container network

            container management {
                presence "management protocols configuration.";
                description "Enter the management context";

                leaf allow-telnet {
                    type boolean;
                    default "false";
                    description "Allow/disallow access to telnet server.";
                }

                leaf allow-telnet6 {
                    type boolean;
                    default "false";
                    description "Allow/disallow access to telnet IPv6 server.";
                }

                leaf allow-ftp {
                    type boolean;
                    default "false";
                    description "Allow/disallow access to ftp server.";
                }

                leaf allow-ssh {
                    type boolean;
                    default "false";
                    description "Allow/disallow access to ssh server.";
                }

                leaf allow-netconf {
                    type boolean;
                    default "false";
                    description "Allow/disallow access to netconf server.";
                }

                leaf allow-grpc {
                    type boolean;
                    default "false";
                    description "Allow/disallow access to grpc server.";
                }

                leaf-list apply-groups {
                    type leafref {
                        path "../../../../groups/group/name";
                    }
                    max-elements 8;
                    ordered-by user;
                    description "Apply a configuration group at this level";
                }

            } // container management

            uses conf-svc-vprn-dhcp-server;
            uses conf-svc-vprn-isis;
            uses conf-svc-vprn-msdp;
            uses conf-svc-vprn-ospf;
            uses conf-svc-vprn-ospf3;
            uses conf-svc-vprn-radius;
            uses conf-svc-vprn-rip;
            uses conf-svc-vprn-ripng;
            uses conf-svc-vprn-sub-if-subscriber-interface;
            uses conf-svc-vprn-twamp-light;
            uses conf-svc-vprn-vdo-if-video-interface;
        } // list vprn

    } // grouping conf-svc-vprn

}
