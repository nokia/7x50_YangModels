submodule nokia-state-isa {

    yang-version "1.1";

    belongs-to nokia-state { prefix "state"; }

    import ietf-yang-types                { prefix "yang"; }
    import nokia-sros-yang-extensions     { prefix "sros-ext"; }
    import nokia-types-isa                { prefix "types-isa"; }
    import nokia-types-l2tp               { prefix "types-l2tp"; }
    import nokia-types-nat                { prefix "types-nat"; }
    import nokia-types-redundancy         { prefix "types-redundancy"; }
    import nokia-types-sros               { prefix "types-sros"; }

    include nokia-state-card;
    include nokia-state-isa-video-group;
    include nokia-state-port;
    include nokia-state-service;

    sros-ext:sros-major-release "rel20";

    organization "Nokia";

    contact
        "Nokia SR OS Support
         Web: <http://www.nokia.com>";

    description
        "Nokia YANG Data model with operational state for ISA configuration on SR OS based routers.

         Copyright 2016 Nokia. All rights reserved. Reproduction of this document
         is authorized on the condition that the foregoing copyright notice is included.

         This nokia-state-isa YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";

    revision "2020-01-20";

    grouping state-isa {
        container isa {
            description "Enter the isa context";

            list tunnel-group {
                key "id";
                description "Enter the tunnel-group list instance";

                leaf id {
                    type types-redundancy:tunnel-group-id;
                    description "The unique identifier of the tunnel group.";
                }

                leaf oper-state {
                    type types-sros:oper-state;
                    description "The operational status of ISA tunnel group.";
                }

                leaf active-isa {
                    type types-isa:slot-mda;
                    description "The active ISA that is being used for this module group.";
                }

                leaf tunnel-count {
                    type uint32;
                    description "The number of IPsec tunnels being used for this module group.";
                }

                leaf max-tunnel {
                    type uint32;
                    description
                        "The maximum number of IPsec tunnels available for this module
                         group.";
                }

                leaf oper-flags {
                    type bits {
                        bit admin-down                     { position 0; }
                        bit no-active                      { position 1; }
                        bit no-resources                   { position 2; }
                        bit mc-admin-down                  { position 3; }
                    }
                    description "The operational flags to determine the ISA tunnel group.";
                }

                leaf ip-tunnel-count {
                    type uint32;
                    description "The number of IP tunnels being used for this module group.";
                }

                leaf ip-max-tunnel {
                    type uint32;
                    description
                        "The maximum number of IP tunnels available for this module
                         group.";
                }

                choice redundancy {
                    description "Redundancy mode for ISAs in this tunnel group";
                    case multi-active {

                        container multi-active {
                            description "Enter the multi-active context";

                            list isa {
                                key "isa-id";
                                description "Add a list entry for isa";

                                leaf isa-id {
                                    type types-isa:slot-mda;
                                    description "The ISA associated with this tunnel group.";
                                }

                                leaf tunnel-group-in-use {
                                    type boolean;
                                    description
                                        "Activate this ISA in the Integrated Service Adaptor (ISA)
                                         tunnel group. The value is only meaningful when
                                         multi-active is true.";
                                }

                            } // list isa

                        } // container multi-active

                    }
                }
                container statistics {
                    description "ISA Tunnel Group statistics.";

                    container ip-tunnel {

                        container number-of-tunnels {

                            container current {
                                description "Current number of operational up IP tunnels.";

                                leaf gre {
                                    type yang:counter64;
                                    description "Number of GRE tunnels.";
                                }

                                leaf ip {
                                    type yang:counter64;
                                    description "Number of IP tunnels.";
                                }

                                leaf l2tpv3 {
                                    type yang:counter64;
                                    description "Number of L2TPv3 tunnels.";
                                }

                                leaf start-time {
                                    type yang:date-and-time;
                                    description "The time when the sampling interval started.";
                                }

                            } // container current

                        } // container number-of-tunnels

                        container throughput {

                            container gre {

                                container current {
                                    description "Current statistics of the GRE tunnel encap and decap throughput.";

                                    leaf start-time {
                                        type yang:date-and-time;
                                        description "The time when the sampling interval started.";
                                    }

                                    leaf sampling-duration {
                                        type types-sros:time-duration;
                                        description "The duration of the corresponding sampling interval.";
                                    }

                                    container packets {

                                        leaf encapsulated {
                                            type yang:counter64;
                                            units "packets per second";
                                            description "Encapsulated GRE tunnel throughput.";
                                        }

                                        leaf decapsulated {
                                            type yang:counter64;
                                            units "packets per second";
                                            description "Decapsulated GRE tunnel throughput.";
                                        }

                                        leaf total {
                                            type yang:counter64;
                                            units "packets per second";
                                            description "Encapsulated and decapsulated GRE tunnel throughput.";
                                        }

                                    } // container packets

                                    container bytes {

                                        leaf encapsulated {
                                            type yang:counter64;
                                            units "megabps";
                                            description "Encapsulated GRE tunnel throughput.";
                                        }

                                        leaf decapsulated {
                                            type yang:counter64;
                                            units "megabps";
                                            description "Decapsulated GRE tunnel throughput.";
                                        }

                                        leaf total {
                                            type yang:counter64;
                                            units "megabps";
                                            description "Encapsulated and decapsulated GRE tunnel throughput.";
                                        }

                                    } // container bytes

                                } // container current

                                list historical {
                                    key "index";
                                    description "Historical statistics of the GRE tunnel encap and decap throughput.";

                                    leaf index {
                                        type uint32 {
                                            range "2..max";
                                        }
                                        description
                                            "The index of the finished sampling interval period for this statistic.
                                             It starts with '2' and is ordered by start time of intervals so that
                                             smaller index indicate more recent intervals.";
                                    }

                                    leaf start-time {
                                        type yang:date-and-time;
                                        description "The time when the sampling interval started.";
                                    }

                                    leaf sampling-duration {
                                        type types-sros:time-duration;
                                        description "The duration of the corresponding sampling interval.";
                                    }

                                    container packets {

                                        leaf encapsulated {
                                            type yang:counter64;
                                            units "packets per second";
                                            description "Encapsulated GRE tunnel throughput.";
                                        }

                                        leaf decapsulated {
                                            type yang:counter64;
                                            units "packets per second";
                                            description "Decapsulated GRE tunnel throughput.";
                                        }

                                        leaf total {
                                            type yang:counter64;
                                            units "packets per second";
                                            description "Encapsulated and decapsulated GRE tunnel throughput.";
                                        }

                                    } // container packets

                                    container bytes {

                                        leaf encapsulated {
                                            type yang:counter64;
                                            units "megabps";
                                            description "Encapsulated GRE tunnel throughput.";
                                        }

                                        leaf decapsulated {
                                            type yang:counter64;
                                            units "megabps";
                                            description "Decapsulated GRE tunnel throughput.";
                                        }

                                        leaf total {
                                            type yang:counter64;
                                            units "megabps";
                                            description "Encapsulated and decapsulated GRE tunnel throughput.";
                                        }

                                    } // container bytes

                                } // list historical

                            } // container gre

                            container ip {

                                container current {
                                    description "Current statistics of the IP tunnel encap and decap throughput.";

                                    leaf start-time {
                                        type yang:date-and-time;
                                        description "The time when the sampling interval started.";
                                    }

                                    leaf sampling-duration {
                                        type types-sros:time-duration;
                                        description "The duration of the corresponding sampling interval.";
                                    }

                                    container packets {

                                        leaf encapsulated {
                                            type yang:counter64;
                                            units "packets per second";
                                            description "Encapsulated IP tunnel throughput.";
                                        }

                                        leaf decapsulated {
                                            type yang:counter64;
                                            units "packets per second";
                                            description "Decapsulated IP tunnel throughput.";
                                        }

                                        leaf total {
                                            type yang:counter64;
                                            units "packets per second";
                                            description "Encapsulated and decapsulated IP tunnel throughput.";
                                        }

                                    } // container packets

                                    container bytes {

                                        leaf encapsulated {
                                            type yang:counter64;
                                            units "megabps";
                                            description "Encapsulated IP tunnel throughput.";
                                        }

                                        leaf decapsulated {
                                            type yang:counter64;
                                            units "megabps";
                                            description "Decapsulated IP tunnel throughput.";
                                        }

                                        leaf total {
                                            type yang:counter64;
                                            units "megabps";
                                            description "Encapsulated and decapsulated IP tunnel throughput.";
                                        }

                                    } // container bytes

                                } // container current

                                list historical {
                                    key "index";
                                    description "Historical statistics of the IP tunnel encap and decap throughput.";

                                    leaf index {
                                        type uint32 {
                                            range "2..max";
                                        }
                                        description
                                            "The index of the finished sampling interval period for this statistic.
                                             It starts with '2' and is ordered by start time of intervals so that
                                             smaller index indicate more recent intervals.";
                                    }

                                    leaf start-time {
                                        type yang:date-and-time;
                                        description "The time when the sampling interval started.";
                                    }

                                    leaf sampling-duration {
                                        type types-sros:time-duration;
                                        description "The duration of the corresponding sampling interval.";
                                    }

                                    container packets {

                                        leaf encapsulated {
                                            type yang:counter64;
                                            units "packets per second";
                                            description "Encapsulated IP tunnel throughput.";
                                        }

                                        leaf decapsulated {
                                            type yang:counter64;
                                            units "packets per second";
                                            description "Decapsulated IP tunnel throughput.";
                                        }

                                        leaf total {
                                            type yang:counter64;
                                            units "packets per second";
                                            description "Encapsulated and decapsulated IP tunnel throughput.";
                                        }

                                    } // container packets

                                    container bytes {

                                        leaf encapsulated {
                                            type yang:counter64;
                                            units "megabps";
                                            description "Encapsulated IP tunnel throughput.";
                                        }

                                        leaf decapsulated {
                                            type yang:counter64;
                                            units "megabps";
                                            description "Decapsulated IP tunnel throughput.";
                                        }

                                        leaf total {
                                            type yang:counter64;
                                            units "megabps";
                                            description "Encapsulated and decapsulated IP tunnel throughput.";
                                        }

                                    } // container bytes

                                } // list historical

                            } // container ip

                            container l2tpv3 {

                                container current {
                                    description "Current statistics of the L2TPV3 tunnel encap and decap throughput.";

                                    leaf start-time {
                                        type yang:date-and-time;
                                        description "The time when the sampling interval started.";
                                    }

                                    leaf sampling-duration {
                                        type types-sros:time-duration;
                                        description "The duration of the corresponding sampling interval.";
                                    }

                                    container packets {

                                        leaf encapsulated {
                                            type yang:counter64;
                                            units "packets per second";
                                            description "Encapsulated L2TPv3 tunnel throughput.";
                                        }

                                        leaf decapsulated {
                                            type yang:counter64;
                                            units "packets per second";
                                            description "Decapsulated L2TPv3 tunnel throughput.";
                                        }

                                        leaf total {
                                            type yang:counter64;
                                            units "packets per second";
                                            description "Encapsulated and decapsulated L2TPv3 tunnel throughput.";
                                        }

                                    } // container packets

                                    container bytes {

                                        leaf encapsulated {
                                            type yang:counter64;
                                            units "megabps";
                                            description "Encapsulated L2TPv3 tunnel throughput.";
                                        }

                                        leaf decapsulated {
                                            type yang:counter64;
                                            units "megabps";
                                            description "Decapsulated L2TPv3 tunnel throughput.";
                                        }

                                        leaf total {
                                            type yang:counter64;
                                            units "megabps";
                                            description "Encapsulated and decapsulated L2TPv3 tunnel throughput.";
                                        }

                                    } // container bytes

                                } // container current

                                list historical {
                                    key "index";
                                    description "Historical statistics of the L2TPV3 tunnel encap and decap throughput.";

                                    leaf index {
                                        type uint32 {
                                            range "2..max";
                                        }
                                        description
                                            "The index of the finished sampling interval period for this statistic.
                                             It starts with '2' and is ordered by start time of intervals so that
                                             smaller index indicate more recent intervals.";
                                    }

                                    leaf start-time {
                                        type yang:date-and-time;
                                        description "The time when the sampling interval started.";
                                    }

                                    leaf sampling-duration {
                                        type types-sros:time-duration;
                                        description "The duration of the corresponding sampling interval.";
                                    }

                                    container packets {

                                        leaf encapsulated {
                                            type yang:counter64;
                                            units "packets per second";
                                            description "Encapsulated L2TPv3 tunnel throughput.";
                                        }

                                        leaf decapsulated {
                                            type yang:counter64;
                                            units "packets per second";
                                            description "Decapsulated L2TPv3 tunnel throughput.";
                                        }

                                        leaf total {
                                            type yang:counter64;
                                            units "packets per second";
                                            description "Encapsulated and decapsulated L2TPv3 tunnel throughput.";
                                        }

                                    } // container packets

                                    container bytes {

                                        leaf encapsulated {
                                            type yang:counter64;
                                            units "megabps";
                                            description "Encapsulated L2TPv3 tunnel throughput.";
                                        }

                                        leaf decapsulated {
                                            type yang:counter64;
                                            units "megabps";
                                            description "Decapsulated L2TPv3 tunnel throughput.";
                                        }

                                        leaf total {
                                            type yang:counter64;
                                            units "megabps";
                                            description "Encapsulated and decapsulated L2TPv3 tunnel throughput.";
                                        }

                                    } // container bytes

                                } // list historical

                            } // container l2tpv3

                        } // container throughput

                    } // container ip-tunnel

                    container ipsec {

                        container number-of-tunnels {

                            container current {
                                description "Current number of operational up IPsec tunnels.";

                                leaf static-lan-to-lan {
                                    type yang:counter64;
                                    description "Number of IPsec static LAN-to-LAN (SL2L) tunnels.";
                                }

                                leaf dynamic-lan-to-lan {
                                    type yang:counter64;
                                    description "Number of IPsec dynamic LAN-to-LAN (DL2L) tunnels.";
                                }

                                leaf remote-access {
                                    type yang:counter64;
                                    description "Number of IPsec remote access (RA) tunnels.";
                                }

                                leaf total {
                                    type yang:counter64;
                                    description "Total number of IPsec tunnels.";
                                }

                                leaf start-time {
                                    type yang:date-and-time;
                                    description "The time when the sampling interval started.";
                                }

                            } // container current

                            list historical {
                                key "index";
                                description "Historical number of operational up IPsec tunnels.";

                                leaf index {
                                    type uint32 {
                                        range "2..max";
                                    }
                                    description
                                        "The index of the finished sampling interval period for this statistic.
                                         It starts with '2' and is ordered by start time of intervals so that
                                         smaller index indicate more recent intervals.";
                                }

                                leaf static-lan-to-lan {
                                    type yang:counter64;
                                    description "Number of IPsec static LAN-to-LAN (SL2L) tunnels.";
                                }

                                leaf dynamic-lan-to-lan {
                                    type yang:counter64;
                                    description "Number of IPsec dynamic LAN-to-LAN (DL2L) tunnels.";
                                }

                                leaf remote-access {
                                    type yang:counter64;
                                    description "Number of IPsec remote access (RA) tunnels.";
                                }

                                leaf total {
                                    type yang:counter64;
                                    description "Total number of IPsec tunnels.";
                                }

                                leaf start-time {
                                    type yang:date-and-time;
                                    description "The time when the sampling interval started.";
                                }

                            } // list historical

                        } // container number-of-tunnels

                        container throughput {

                            container current {
                                description "Current statistics of the encrypted and decrypted IPsec throughput.";

                                leaf start-time {
                                    type yang:date-and-time;
                                    description "The time when the sampling interval started.";
                                }

                                leaf sampling-duration {
                                    type types-sros:time-duration;
                                    description "The duration of the corresponding sampling interval.";
                                }

                                container packets {

                                    leaf encrypted {
                                        type yang:counter64;
                                        units "packets per second";
                                        description "Encrypted IPsec traffic throughput.";
                                    }

                                    leaf decrypted {
                                        type yang:counter64;
                                        units "packets per second";
                                        description "Decrypted IPsec traffic throughput.";
                                    }

                                    leaf total {
                                        type yang:counter64;
                                        units "packets per second";
                                        description "Encrypted and decrypted IPsec traffic throughput.";
                                    }

                                } // container packets

                                container bytes {

                                    leaf encrypted {
                                        type yang:counter64;
                                        units "megabps";
                                        description "Encrypted IPsec traffic throughput.";
                                    }

                                    leaf decrypted {
                                        type yang:counter64;
                                        units "megabps";
                                        description "Decrypted IPsec traffic throughput.";
                                    }

                                    leaf total {
                                        type yang:counter64;
                                        units "megabps";
                                        description "Encrypted and decrypted IPsec traffic throughput.";
                                    }

                                } // container bytes

                            } // container current

                            list historical {
                                key "index";
                                description "Historical statistics of the encrypted and decrypted IPsec throughput.";

                                leaf index {
                                    type uint32 {
                                        range "2..max";
                                    }
                                    description
                                        "The index of the finished sampling interval period for this statistic.
                                         It starts with '2' and is ordered by start time of intervals so that
                                         smaller index indicate more recent intervals.";
                                }

                                leaf start-time {
                                    type yang:date-and-time;
                                    description "The time when the sampling interval started.";
                                }

                                leaf sampling-duration {
                                    type types-sros:time-duration;
                                    description "The duration of the corresponding sampling interval.";
                                }

                                container packets {

                                    leaf encrypted {
                                        type yang:counter64;
                                        units "packets per second";
                                        description "Encrypted IPsec traffic throughput.";
                                    }

                                    leaf decrypted {
                                        type yang:counter64;
                                        units "packets per second";
                                        description "Decrypted IPsec traffic throughput.";
                                    }

                                    leaf total {
                                        type yang:counter64;
                                        units "packets per second";
                                        description "Encrypted and decrypted IPsec traffic throughput.";
                                    }

                                } // container packets

                                container bytes {

                                    leaf encrypted {
                                        type yang:counter64;
                                        units "megabps";
                                        description "Encrypted IPsec traffic throughput.";
                                    }

                                    leaf decrypted {
                                        type yang:counter64;
                                        units "megabps";
                                        description "Decrypted IPsec traffic throughput.";
                                    }

                                    leaf total {
                                        type yang:counter64;
                                        units "megabps";
                                        description "Encrypted and decrypted IPsec traffic throughput.";
                                    }

                                } // container bytes

                            } // list historical

                        } // container throughput

                        container tunnel-setup-rate {

                            container current {
                                description "Current statistics of successfully established IPsec tunnels.";

                                leaf static-lan-to-lan {
                                    type decimal64 {
                                        fraction-digits 2;
                                    }
                                    units "tunnels per second";
                                    description "Static LAN-to-LAN (SL2L) tunnel setup rate.";
                                }

                                leaf total {
                                    type decimal64 {
                                        fraction-digits 2;
                                    }
                                    units "tunnels per second";
                                    description "Total IPsec tunnel setup rate.";
                                }

                                leaf dynamic-lan-to-lan {
                                    type decimal64 {
                                        fraction-digits 2;
                                    }
                                    units "tunnels per second";
                                    description "Dynamic LAN-to-LAN (DL2L) tunnel setup rate.";
                                }

                                leaf remote-access {
                                    type decimal64 {
                                        fraction-digits 2;
                                    }
                                    units "tunnels per second";
                                    description "Remote access (RA) tunnel setup rate.";
                                }

                                leaf start-time {
                                    type yang:date-and-time;
                                    description "The time when the sampling interval started.";
                                }

                                leaf sampling-duration {
                                    type types-sros:time-duration;
                                    description "The duration of the corresponding sampling interval.";
                                }

                            } // container current

                            list historical {
                                key "index";
                                description "Historical statistics of successfully established IPsec tunnels.";

                                leaf index {
                                    type uint32 {
                                        range "2..max";
                                    }
                                    description
                                        "The index of the finished sampling interval period for this statistic.
                                         It starts with '2' and is ordered by start time of intervals so that
                                         smaller index indicate more recent intervals.";
                                }

                                leaf static-lan-to-lan {
                                    type decimal64 {
                                        fraction-digits 2;
                                    }
                                    units "tunnels per second";
                                    description "Static LAN-to-LAN (SL2L) tunnel setup rate.";
                                }

                                leaf total {
                                    type decimal64 {
                                        fraction-digits 2;
                                    }
                                    units "tunnels per second";
                                    description "Total IPsec tunnel setup rate.";
                                }

                                leaf dynamic-lan-to-lan {
                                    type decimal64 {
                                        fraction-digits 2;
                                    }
                                    units "tunnels per second";
                                    description "Dynamic LAN-to-LAN (DL2L) tunnel setup rate.";
                                }

                                leaf remote-access {
                                    type decimal64 {
                                        fraction-digits 2;
                                    }
                                    units "tunnels per second";
                                    description "Remote access (RA) tunnel setup rate.";
                                }

                                leaf start-time {
                                    type yang:date-and-time;
                                    description "The time when the sampling interval started.";
                                }

                                leaf sampling-duration {
                                    type types-sros:time-duration;
                                    description "The duration of the corresponding sampling interval.";
                                }

                            } // list historical

                        } // container tunnel-setup-rate

                        container ike-exchange-failure-rate {

                            container current {
                                description "Current statistics of IKE exchange failures.";

                                leaf start-time {
                                    type yang:date-and-time;
                                    description "The time when the sampling interval started.";
                                }

                                leaf sampling-duration {
                                    type types-sros:time-duration;
                                    description "The duration of the corresponding sampling interval.";
                                }

                                container auth-failure {

                                    leaf count {
                                        type decimal64 {
                                            fraction-digits 2;
                                        }
                                        units "failures per second";
                                        description "IKE exchange failure rate - authentication.";
                                    }

                                    leaf first-failure {
                                        type yang:date-and-time;
                                        description
                                            "The time when the first IKE exchange failure happened
                                             in the corresponding sampling interval.";
                                    }

                                    leaf first-failure-description {
                                        type types-sros:long-description;
                                        description "The description of the place where the first IKE exchange failure happened.";
                                    }

                                    leaf last-failure {
                                        type yang:date-and-time;
                                        description
                                            "The time when the last IKE exchange failure happened
                                             in the corresponding sampling interval.";
                                    }

                                    leaf last-failure-description {
                                        type types-sros:long-description;
                                        description "The description of the place where the last IKE exchange failure happened.";
                                    }

                                } // container auth-failure

                                container non-proposal-chosen {

                                    leaf count {
                                        type decimal64 {
                                            fraction-digits 2;
                                        }
                                        units "failures per second";
                                        description "IKE exchange failure rate - non-proposal chosen.";
                                    }

                                    leaf first-failure {
                                        type yang:date-and-time;
                                        description
                                            "The time when the first IKE exchange failure happened
                                             in the corresponding sampling interval.";
                                    }

                                    leaf first-failure-description {
                                        type types-sros:long-description;
                                        description "The description of the place where the first IKE exchange failure happened.";
                                    }

                                    leaf last-failure {
                                        type yang:date-and-time;
                                        description
                                            "The time when the last IKE exchange failure happened
                                             in the corresponding sampling interval.";
                                    }

                                    leaf last-failure-description {
                                        type types-sros:long-description;
                                        description "The description of the place where the last IKE exchange failure happened.";
                                    }

                                } // container non-proposal-chosen

                                container internal-address-assignment {

                                    leaf count {
                                        type decimal64 {
                                            fraction-digits 2;
                                        }
                                        units "failures per second";
                                        description "IKE exchange failure rate - address assignment.";
                                    }

                                    leaf first-failure {
                                        type yang:date-and-time;
                                        description
                                            "The time when the first IKE exchange failure happened
                                             in the corresponding sampling interval.";
                                    }

                                    leaf first-failure-description {
                                        type types-sros:long-description;
                                        description "The description of the place where the first IKE exchange failure happened.";
                                    }

                                    leaf last-failure {
                                        type yang:date-and-time;
                                        description
                                            "The time when the last IKE exchange failure happened
                                             in the corresponding sampling interval.";
                                    }

                                    leaf last-failure-description {
                                        type types-sros:long-description;
                                        description "The description of the place where the last IKE exchange failure happened.";
                                    }

                                } // container internal-address-assignment

                                container invalid-ts {

                                    leaf count {
                                        type decimal64 {
                                            fraction-digits 2;
                                        }
                                        units "failures per second";
                                        description "IKE exchange failure rate - invalid traffic selector.";
                                    }

                                    leaf first-failure {
                                        type yang:date-and-time;
                                        description
                                            "The time when the first IKE exchange failure happened
                                             in the corresponding sampling interval.";
                                    }

                                    leaf first-failure-description {
                                        type types-sros:long-description;
                                        description "The description of the place where the first IKE exchange failure happened.";
                                    }

                                    leaf last-failure {
                                        type yang:date-and-time;
                                        description
                                            "The time when the last IKE exchange failure happened
                                             in the corresponding sampling interval.";
                                    }

                                    leaf last-failure-description {
                                        type types-sros:long-description;
                                        description "The description of the place where the last IKE exchange failure happened.";
                                    }

                                } // container invalid-ts

                                container invalid-ke {

                                    leaf count {
                                        type decimal64 {
                                            fraction-digits 2;
                                        }
                                        units "failures per second";
                                        description "IKE exchange failure rate - invalid key exchange.";
                                    }

                                    leaf first-failure {
                                        type yang:date-and-time;
                                        description
                                            "The time when the first IKE exchange failure happened
                                             in the corresponding sampling interval.";
                                    }

                                    leaf first-failure-description {
                                        type types-sros:long-description;
                                        description "The description of the place where the first IKE exchange failure happened.";
                                    }

                                    leaf last-failure {
                                        type yang:date-and-time;
                                        description
                                            "The time when the last IKE exchange failure happened
                                             in the corresponding sampling interval.";
                                    }

                                    leaf last-failure-description {
                                        type types-sros:long-description;
                                        description "The description of the place where the last IKE exchange failure happened.";
                                    }

                                } // container invalid-ke

                                container dpd-timeout {

                                    leaf count {
                                        type decimal64 {
                                            fraction-digits 2;
                                        }
                                        units "failures per second";
                                        description "IKE exchange failure rate - DPD timeout.";
                                    }

                                    leaf first-failure {
                                        type yang:date-and-time;
                                        description
                                            "The time when the first IKE exchange failure happened
                                             in the corresponding sampling interval.";
                                    }

                                    leaf first-failure-description {
                                        type types-sros:long-description;
                                        description "The description of the place where the first IKE exchange failure happened.";
                                    }

                                    leaf last-failure {
                                        type yang:date-and-time;
                                        description
                                            "The time when the last IKE exchange failure happened
                                             in the corresponding sampling interval.";
                                    }

                                    leaf last-failure-description {
                                        type types-sros:long-description;
                                        description "The description of the place where the last IKE exchange failure happened.";
                                    }

                                } // container dpd-timeout

                                container other {

                                    leaf count {
                                        type decimal64 {
                                            fraction-digits 2;
                                        }
                                        units "failures per second";
                                        description "IKE exchange failure rate - other failure reasons.";
                                    }

                                    leaf first-failure {
                                        type yang:date-and-time;
                                        description
                                            "The time when the first IKE exchange failure happened
                                             in the corresponding sampling interval.";
                                    }

                                    leaf first-failure-description {
                                        type types-sros:long-description;
                                        description "The description of the place where the first IKE exchange failure happened.";
                                    }

                                    leaf last-failure {
                                        type yang:date-and-time;
                                        description
                                            "The time when the last IKE exchange failure happened
                                             in the corresponding sampling interval.";
                                    }

                                    leaf last-failure-description {
                                        type types-sros:long-description;
                                        description "The description of the place where the last IKE exchange failure happened.";
                                    }

                                } // container other

                            } // container current

                            list historical {
                                key "index";
                                description "Historical statistics of IKE exchange failures.";

                                leaf index {
                                    type uint32 {
                                        range "2..max";
                                    }
                                    description
                                        "The index of the finished sampling interval period for this statistic.
                                         It starts with '2' and is ordered by start time of intervals so that
                                         smaller index indicate more recent intervals.";
                                }

                                leaf start-time {
                                    type yang:date-and-time;
                                    description "The time when the sampling interval started.";
                                }

                                leaf sampling-duration {
                                    type types-sros:time-duration;
                                    description "The duration of the corresponding sampling interval.";
                                }

                                container auth-failure {

                                    leaf count {
                                        type decimal64 {
                                            fraction-digits 2;
                                        }
                                        units "failures per second";
                                        description "IKE exchange failure rate - authentication.";
                                    }

                                    leaf first-failure {
                                        type yang:date-and-time;
                                        description
                                            "The time when the first IKE exchange failure happened
                                             in the corresponding sampling interval.";
                                    }

                                    leaf first-failure-description {
                                        type types-sros:long-description;
                                        description "The description of the place where the first IKE exchange failure happened.";
                                    }

                                    leaf last-failure {
                                        type yang:date-and-time;
                                        description
                                            "The time when the last IKE exchange failure happened
                                             in the corresponding sampling interval.";
                                    }

                                    leaf last-failure-description {
                                        type types-sros:long-description;
                                        description "The description of the place where the last IKE exchange failure happened.";
                                    }

                                } // container auth-failure

                                container non-proposal-chosen {

                                    leaf count {
                                        type decimal64 {
                                            fraction-digits 2;
                                        }
                                        units "failures per second";
                                        description "IKE exchange failure rate - non-proposal chosen.";
                                    }

                                    leaf first-failure {
                                        type yang:date-and-time;
                                        description
                                            "The time when the first IKE exchange failure happened
                                             in the corresponding sampling interval.";
                                    }

                                    leaf first-failure-description {
                                        type types-sros:long-description;
                                        description "The description of the place where the first IKE exchange failure happened.";
                                    }

                                    leaf last-failure {
                                        type yang:date-and-time;
                                        description
                                            "The time when the last IKE exchange failure happened
                                             in the corresponding sampling interval.";
                                    }

                                    leaf last-failure-description {
                                        type types-sros:long-description;
                                        description "The description of the place where the last IKE exchange failure happened.";
                                    }

                                } // container non-proposal-chosen

                                container internal-address-assignment {

                                    leaf count {
                                        type decimal64 {
                                            fraction-digits 2;
                                        }
                                        units "failures per second";
                                        description "IKE exchange failure rate - address assignment.";
                                    }

                                    leaf first-failure {
                                        type yang:date-and-time;
                                        description
                                            "The time when the first IKE exchange failure happened
                                             in the corresponding sampling interval.";
                                    }

                                    leaf first-failure-description {
                                        type types-sros:long-description;
                                        description "The description of the place where the first IKE exchange failure happened.";
                                    }

                                    leaf last-failure {
                                        type yang:date-and-time;
                                        description
                                            "The time when the last IKE exchange failure happened
                                             in the corresponding sampling interval.";
                                    }

                                    leaf last-failure-description {
                                        type types-sros:long-description;
                                        description "The description of the place where the last IKE exchange failure happened.";
                                    }

                                } // container internal-address-assignment

                                container invalid-ts {

                                    leaf count {
                                        type decimal64 {
                                            fraction-digits 2;
                                        }
                                        units "failures per second";
                                        description "IKE exchange failure rate - invalid traffic selector.";
                                    }

                                    leaf first-failure {
                                        type yang:date-and-time;
                                        description
                                            "The time when the first IKE exchange failure happened
                                             in the corresponding sampling interval.";
                                    }

                                    leaf first-failure-description {
                                        type types-sros:long-description;
                                        description "The description of the place where the first IKE exchange failure happened.";
                                    }

                                    leaf last-failure {
                                        type yang:date-and-time;
                                        description
                                            "The time when the last IKE exchange failure happened
                                             in the corresponding sampling interval.";
                                    }

                                    leaf last-failure-description {
                                        type types-sros:long-description;
                                        description "The description of the place where the last IKE exchange failure happened.";
                                    }

                                } // container invalid-ts

                                container invalid-ke {

                                    leaf count {
                                        type decimal64 {
                                            fraction-digits 2;
                                        }
                                        units "failures per second";
                                        description "IKE exchange failure rate - invalid key exchange.";
                                    }

                                    leaf first-failure {
                                        type yang:date-and-time;
                                        description
                                            "The time when the first IKE exchange failure happened
                                             in the corresponding sampling interval.";
                                    }

                                    leaf first-failure-description {
                                        type types-sros:long-description;
                                        description "The description of the place where the first IKE exchange failure happened.";
                                    }

                                    leaf last-failure {
                                        type yang:date-and-time;
                                        description
                                            "The time when the last IKE exchange failure happened
                                             in the corresponding sampling interval.";
                                    }

                                    leaf last-failure-description {
                                        type types-sros:long-description;
                                        description "The description of the place where the last IKE exchange failure happened.";
                                    }

                                } // container invalid-ke

                                container dpd-timeout {

                                    leaf count {
                                        type decimal64 {
                                            fraction-digits 2;
                                        }
                                        units "failures per second";
                                        description "IKE exchange failure rate - DPD timeout.";
                                    }

                                    leaf first-failure {
                                        type yang:date-and-time;
                                        description
                                            "The time when the first IKE exchange failure happened
                                             in the corresponding sampling interval.";
                                    }

                                    leaf first-failure-description {
                                        type types-sros:long-description;
                                        description "The description of the place where the first IKE exchange failure happened.";
                                    }

                                    leaf last-failure {
                                        type yang:date-and-time;
                                        description
                                            "The time when the last IKE exchange failure happened
                                             in the corresponding sampling interval.";
                                    }

                                    leaf last-failure-description {
                                        type types-sros:long-description;
                                        description "The description of the place where the last IKE exchange failure happened.";
                                    }

                                } // container dpd-timeout

                                container other {

                                    leaf count {
                                        type decimal64 {
                                            fraction-digits 2;
                                        }
                                        units "failures per second";
                                        description "IKE exchange failure rate - other failure reasons.";
                                    }

                                    leaf first-failure {
                                        type yang:date-and-time;
                                        description
                                            "The time when the first IKE exchange failure happened
                                             in the corresponding sampling interval.";
                                    }

                                    leaf first-failure-description {
                                        type types-sros:long-description;
                                        description "The description of the place where the first IKE exchange failure happened.";
                                    }

                                    leaf last-failure {
                                        type yang:date-and-time;
                                        description
                                            "The time when the last IKE exchange failure happened
                                             in the corresponding sampling interval.";
                                    }

                                    leaf last-failure-description {
                                        type types-sros:long-description;
                                        description "The description of the place where the last IKE exchange failure happened.";
                                    }

                                } // container other

                            } // list historical

                        } // container ike-exchange-failure-rate

                    } // container ipsec

                } // container statistics

            } // list tunnel-group

            list nat-group {
                key "id";
                description "Enter the nat-group list instance";

                leaf id {
                    type uint32 {
                        range "1..4";
                    }
                    description "Nat-group identifier";
                }

                leaf oper-state {
                    type types-sros:oper-state;
                    description
                        "The value of tmnxNatIsaGrpOperState indicates
                         the operational status of this NAT ISA group";
                }

                leaf degraded {
                    type boolean;
                    description
                        "indicates if this NAT ISA group is degraded,
                         while operationally still in service";
                }

                container redundancy {
                    description "Enter the redundancy context";

                    choice redundancy-mode {
                    }
                } // container redundancy

                list member {
                    key "id";
                    description "Information about a NAT group member";

                    leaf id {
                        type types-nat:bb-group-member;
                        description "Nat-group member identifier";
                    }

                    leaf state {
                        type enumeration {
                            enum "inactive"                     { value 1; }
                            enum "active"                       { value 2; }
                            enum "needs-reset"                  { value 3; }
                            enum "resetting"                    { value 4; }
                            enum "needs-reconcile"              { value 5; }
                            enum "reconciling"                  { value 6; }
                            enum "needs-audit"                  { value 7; }
                            enum "auditing"                     { value 8; }
                            enum "failed-bypass"                { value 9; }
                            enum "active-bypass"                { value 10; }
                        }
                        description "The state of the MDA associated with this member";
                    }

                    leaf associated-mda {
                        type types-isa:slot-mda;
                        description "MDA on which this member resides";
                    }

                    leaf allocated-resources {
                        type uint32 {
                            range "0..100";
                        }
                        description "the ratio of allocated resources to total resources on this NAT ISA member";
                    }

                    leaf reserved-outside-ip-addresses {
                        type yang:gauge32;
                        description "The number of outside IP addresses reserved for the MDA associated with this member";
                    }

                    leaf outside-port-blocks {
                        type yang:gauge32;
                        description "The number of outside port blocks reserved for the MDA associated with this member";
                    }

                    leaf session-usage {
                        type types-isa:nat-usage-level;
                        description "The session usage of the MDA associated with this member";
                    }

                    leaf high-session-usage {
                        type boolean;
                        description
                            "Indicates if the session usage of the MDA associated with this member is high
                             according to the values of watermark definitions";
                    }

                    leaf prioritized-sessions {
                        type yang:gauge32;
                        description "The current number of active prioritized sessions of the MDA associated with this member";
                    }

                    container resources {
                        description "Resource consumption per member";

                        container port-ranges {

                            container configured {

                                leaf value {
                                    type yang:gauge64;
                                    description "Actual consumed value";
                                }

                                leaf max {
                                    type uint64;
                                    description "The max value this resource can have, depending on the configuration";
                                }

                                leaf peak {
                                    type yang:gauge64;
                                    description "The peak value for the resource";
                                }

                                leaf peak-timestamp {
                                    type types-sros:date-time;
                                    description "The timestamp when the peak value was observed";
                                }

                            } // container configured

                            container used {

                                leaf value {
                                    type yang:gauge64;
                                    description "Actual consumed value";
                                }

                                leaf max {
                                    type uint64;
                                    description "The max value this resource can have, depending on the configuration";
                                }

                                leaf peak {
                                    type yang:gauge64;
                                    description "The peak value for the resource";
                                }

                                leaf peak-timestamp {
                                    type types-sros:date-time;
                                    description "The timestamp when the peak value was observed";
                                }

                            } // container used

                            container retained {

                                leaf value {
                                    type yang:gauge64;
                                    description "Actual consumed value";
                                }

                                leaf max {
                                    type uint64;
                                    description "The max value this resource can have, depending on the configuration";
                                }

                                leaf peak {
                                    type yang:gauge64;
                                    description "The peak value for the resource";
                                }

                                leaf peak-timestamp {
                                    type types-sros:date-time;
                                    description "The timestamp when the peak value was observed";
                                }

                            } // container retained

                        } // container port-ranges

                        container ports {

                            leaf value {
                                type yang:gauge64;
                                description "Actual consumed value";
                            }

                            leaf max {
                                type uint64;
                                description "The max value this resource can have, depending on the configuration";
                            }

                            leaf peak {
                                type yang:gauge64;
                                description "The peak value for the resource";
                            }

                            leaf peak-timestamp {
                                type types-sros:date-time;
                                description "The timestamp when the peak value was observed";
                            }

                        } // container ports

                        container ip-addresses {

                            leaf value {
                                type yang:gauge64;
                                description "Actual consumed value";
                            }

                            leaf max {
                                type uint64;
                                description "The max value this resource can have, depending on the configuration";
                            }

                            leaf peak {
                                type yang:gauge64;
                                description "The peak value for the resource";
                            }

                            leaf peak-timestamp {
                                type types-sros:date-time;
                                description "The timestamp when the peak value was observed";
                            }

                        } // container ip-addresses

                        container one-to-one-ip-addresses {

                            leaf value {
                                type yang:gauge64;
                                description "Actual consumed value";
                            }

                            leaf max {
                                type uint64;
                                description "The max value this resource can have, depending on the configuration";
                            }

                            leaf peak {
                                type yang:gauge64;
                                description "The peak value for the resource";
                            }

                            leaf peak-timestamp {
                                type types-sros:date-time;
                                description "The timestamp when the peak value was observed";
                            }

                        } // container one-to-one-ip-addresses

                        container large-scale-hosts {

                            leaf value {
                                type yang:gauge64;
                                description "Actual consumed value";
                            }

                            leaf max {
                                type uint64;
                                description "The max value this resource can have, depending on the configuration";
                            }

                            leaf peak {
                                type yang:gauge64;
                                description "The peak value for the resource";
                            }

                            leaf peak-timestamp {
                                type types-sros:date-time;
                                description "The timestamp when the peak value was observed";
                            }

                        } // container large-scale-hosts

                        container l2-aware {

                            container subscribers {

                                leaf value {
                                    type yang:gauge64;
                                    description "Actual consumed value";
                                }

                                leaf max {
                                    type uint64;
                                    description "The max value this resource can have, depending on the configuration";
                                }

                                leaf peak {
                                    type yang:gauge64;
                                    description "The peak value for the resource";
                                }

                                leaf peak-timestamp {
                                    type types-sros:date-time;
                                    description "The timestamp when the peak value was observed";
                                }

                            } // container subscribers

                            container hosts {

                                leaf value {
                                    type yang:gauge64;
                                    description "Actual consumed value";
                                }

                                leaf max {
                                    type uint64;
                                    description "The max value this resource can have, depending on the configuration";
                                }

                                leaf peak {
                                    type yang:gauge64;
                                    description "The peak value for the resource";
                                }

                                leaf peak-timestamp {
                                    type types-sros:date-time;
                                    description "The timestamp when the peak value was observed";
                                }

                            } // container hosts

                        } // container l2-aware

                    } // container resources

                } // list member

                list mda {
                    key "mda-id";
                    description "Add a list entry for mda";

                    leaf mda-id {
                        type types-isa:slot-mda;
                        description "MDA ID for ISA NAT group";
                    }

                    leaf layer-2-hosts-bypassed {
                        type uint32;
                        description "number of Layer-2 aware NAT hosts being bypassed for this ISA MDA";
                    }

                    leaf oper-state {
                        type types-isa:nat-mda-operational-state;
                        description "the operational state of this NAT ISA MDA";
                    }

                    leaf allocated-resources {
                        type uint32 {
                            range "0..100";
                        }
                        description "the ratio of allocated resources to total resources on this NAT ISA MDA";
                    }

                    leaf peak-values-last-reset {
                        type yang:date-and-time;
                        description
                            "Moment when the peak values were last reset
                             (applicable to both NAT ISA MDA and member resources)";
                    }

                    container resources {
                        description "Resource consumption per mda";

                        container flows {

                            leaf value {
                                type yang:gauge64;
                                description "Actual consumed value";
                            }

                            leaf max {
                                type uint64;
                                description "The max value this resource can have, depending on the configuration";
                            }

                            leaf peak {
                                type yang:gauge64;
                                description "The peak value for the resource";
                            }

                            leaf peak-timestamp {
                                type types-sros:date-time;
                                description "The timestamp when the peak value was observed";
                            }

                        } // container flows

                        container policies {

                            leaf value {
                                type yang:gauge64;
                                description "Actual consumed value";
                            }

                            leaf max {
                                type uint64;
                                description "The max value this resource can have, depending on the configuration";
                            }

                            leaf peak {
                                type yang:gauge64;
                                description "The peak value for the resource";
                            }

                            leaf peak-timestamp {
                                type types-sros:date-time;
                                description "The timestamp when the peak value was observed";
                            }

                        } // container policies

                        container subscriber-cache-entries {

                            leaf value {
                                type yang:gauge64;
                                description "Actual consumed value";
                            }

                            leaf max {
                                type uint64;
                                description "The max value this resource can have, depending on the configuration";
                            }

                            leaf peak {
                                type yang:gauge64;
                                description "The peak value for the resource";
                            }

                            leaf peak-timestamp {
                                type types-sros:date-time;
                                description "The timestamp when the peak value was observed";
                            }

                        } // container subscriber-cache-entries

                        container delayed-icmps {

                            leaf value {
                                type yang:gauge64;
                                description "Actual consumed value";
                            }

                            leaf max {
                                type uint64;
                                description "The max value this resource can have, depending on the configuration";
                            }

                            leaf peak {
                                type yang:gauge64;
                                description "The peak value for the resource";
                            }

                            leaf peak-timestamp {
                                type types-sros:date-time;
                                description "The timestamp when the peak value was observed";
                            }

                        } // container delayed-icmps

                        container alg-session {

                            leaf value {
                                type yang:gauge64;
                                description "Actual consumed value";
                            }

                            leaf max {
                                type uint64;
                                description "The max value this resource can have, depending on the configuration";
                            }

                            leaf peak {
                                type yang:gauge64;
                                description "The peak value for the resource";
                            }

                            leaf peak-timestamp {
                                type types-sros:date-time;
                                description "The timestamp when the peak value was observed";
                            }

                        } // container alg-session

                        container fragment-lists {

                            container upstream {

                                leaf value {
                                    type yang:gauge64;
                                    description "Actual consumed value";
                                }

                                leaf max {
                                    type uint64;
                                    description "The max value this resource can have, depending on the configuration";
                                }

                                leaf peak {
                                    type yang:gauge64;
                                    description "The peak value for the resource";
                                }

                                leaf peak-timestamp {
                                    type types-sros:date-time;
                                    description "The timestamp when the peak value was observed";
                                }

                            } // container upstream

                            container downstream {

                                leaf value {
                                    type yang:gauge64;
                                    description "Actual consumed value";
                                }

                                leaf max {
                                    type uint64;
                                    description "The max value this resource can have, depending on the configuration";
                                }

                                leaf peak {
                                    type yang:gauge64;
                                    description "The peak value for the resource";
                                }

                                leaf peak-timestamp {
                                    type types-sros:date-time;
                                    description "The timestamp when the peak value was observed";
                                }

                            } // container downstream

                        } // container fragment-lists

                        container fragment-holes {

                            container upstream {

                                leaf value {
                                    type yang:gauge64;
                                    description "Actual consumed value";
                                }

                                leaf max {
                                    type uint64;
                                    description "The max value this resource can have, depending on the configuration";
                                }

                                leaf peak {
                                    type yang:gauge64;
                                    description "The peak value for the resource";
                                }

                                leaf peak-timestamp {
                                    type types-sros:date-time;
                                    description "The timestamp when the peak value was observed";
                                }

                            } // container upstream

                            container downstream {

                                leaf value {
                                    type yang:gauge64;
                                    description "Actual consumed value";
                                }

                                leaf max {
                                    type uint64;
                                    description "The max value this resource can have, depending on the configuration";
                                }

                                leaf peak {
                                    type yang:gauge64;
                                    description "The peak value for the resource";
                                }

                                leaf peak-timestamp {
                                    type types-sros:date-time;
                                    description "The timestamp when the peak value was observed";
                                }

                            } // container downstream

                        } // container fragment-holes

                        container fragment-bufs {

                            container upstream {

                                leaf value {
                                    type yang:gauge64;
                                    description "Actual consumed value";
                                }

                                leaf max {
                                    type uint64;
                                    description "The max value this resource can have, depending on the configuration";
                                }

                                leaf peak {
                                    type yang:gauge64;
                                    description "The peak value for the resource";
                                }

                                leaf peak-timestamp {
                                    type types-sros:date-time;
                                    description "The timestamp when the peak value was observed";
                                }

                            } // container upstream

                            container downstream {

                                leaf value {
                                    type yang:gauge64;
                                    description "Actual consumed value";
                                }

                                leaf max {
                                    type uint64;
                                    description "The max value this resource can have, depending on the configuration";
                                }

                                leaf peak {
                                    type yang:gauge64;
                                    description "The peak value for the resource";
                                }

                                leaf peak-timestamp {
                                    type types-sros:date-time;
                                    description "The timestamp when the peak value was observed";
                                }

                            } // container downstream

                        } // container fragment-bufs

                        container upnp {

                            container mappings {

                                leaf value {
                                    type yang:gauge64;
                                    description "Actual consumed value";
                                }

                                leaf max {
                                    type uint64;
                                    description "The max value this resource can have, depending on the configuration";
                                }

                                leaf peak {
                                    type yang:gauge64;
                                    description "The peak value for the resource";
                                }

                                leaf peak-timestamp {
                                    type types-sros:date-time;
                                    description "The timestamp when the peak value was observed";
                                }

                            } // container mappings

                            container sessions {

                                leaf value {
                                    type yang:gauge64;
                                    description "Actual consumed value";
                                }

                                leaf max {
                                    type uint64;
                                    description "The max value this resource can have, depending on the configuration";
                                }

                                leaf peak {
                                    type yang:gauge64;
                                    description "The peak value for the resource";
                                }

                                leaf peak-timestamp {
                                    type types-sros:date-time;
                                    description "The timestamp when the peak value was observed";
                                }

                            } // container sessions

                        } // container upnp

                        container pppoe-sessions {

                            leaf value {
                                type yang:gauge64;
                                description "Actual consumed value";
                            }

                            leaf max {
                                type uint64;
                                description "The max value this resource can have, depending on the configuration";
                            }

                            leaf peak {
                                type yang:gauge64;
                                description "The peak value for the resource";
                            }

                            leaf peak-timestamp {
                                type types-sros:date-time;
                                description "The timestamp when the peak value was observed";
                            }

                        } // container pppoe-sessions

                    } // container resources

                    container statistics {
                        description "ISA statistics";

                        container ip-forwarding {
                            description "IP forwarding statistics per MDA";

                            leaf fragments {
                                type yang:counter64;
                                description "Fragments handled";
                            }

                            leaf reassembled-packets {
                                type yang:counter64;
                                description "Frames reassembled";
                            }

                            leaf forwarded-packets {
                                type yang:counter64;
                                description "Frames forwarded";
                            }

                            container receive-errors {
                                description "Receive errors";

                                leaf l2-error {
                                    type yang:counter64;
                                    description "L2 parse error";
                                }

                                leaf l3-not-ip {
                                    type yang:counter64;
                                    description "L3 is not IPv4 or IPv6";
                                }

                                leaf ip-invalid-checksum {
                                    type yang:counter64;
                                    description "IPv4 invalid checksum";
                                }

                                leaf ip-malformed-header {
                                    type yang:counter64;
                                    description "IP malformed header";
                                }

                                leaf ip-malformed-packet {
                                    type yang:counter64;
                                    description "IP malformed packet";
                                }

                                leaf ip-zero-ttl {
                                    type yang:counter64;
                                    description "IP zero ttl";
                                }

                                leaf ip-opts-or-ext-headers {
                                    type yang:counter64;
                                    description "IPv4 options or IPv6 extension headers";
                                }

                                leaf ip-fragment-unsupported {
                                    type yang:counter64;
                                    description "IP fragment unsupported";
                                }

                                leaf ip-error {
                                    type yang:counter64;
                                    description "IP parse error";
                                }

                                leaf tcp-udp-malformed-header {
                                    type yang:counter64;
                                    description "TCP/UDP malformed header";
                                }

                                leaf tcp-udp-invalid-checksum {
                                    type yang:counter64;
                                    description "TCP/UDP invalid checksum";
                                }

                                leaf other {
                                    type yang:counter64;
                                    description "Other parse error";
                                }

                            } // container receive-errors

                            container reassembly-errors {
                                description "Reassembly errors";

                                leaf too-many-fragmented-packets {
                                    type yang:counter64;
                                    description "Too many fragmented packets";
                                }

                                leaf too-many-fragment-buffers {
                                    type yang:counter64;
                                    description "Too many fragment buffers";
                                }

                                leaf too-many-fragment-holes {
                                    type yang:counter64;
                                    description "Too many fragment holes";
                                }

                                leaf fragment-filtered {
                                    type yang:counter64;
                                    description "Fragments filtered";
                                }

                                leaf fragment-not-supported {
                                    type yang:counter64;
                                    description "Fragment not supported";
                                }

                                leaf fragment-list-expired {
                                    type yang:counter64;
                                    description "Fragment list expired";
                                }

                                leaf fragment-list-cleanup-in-progress {
                                    type yang:counter64;
                                    description "Fragment list cleanup in progress";
                                }

                                leaf reassembly-failed {
                                    type yang:counter64;
                                    description "Reassembly failed";
                                }

                            } // container reassembly-errors

                        } // container ip-forwarding

                        container pppoe-client {
                            description "PPPoE-client statistics per MDA";

                            leaf rx-error-l2 {
                                type yang:counter64;
                                description "Number of packets received with layer 2 parse errors";
                            }

                            leaf rx-error-invalid-headers {
                                type yang:counter64;
                                description "Number of packets received with invalid PPPoE headers";
                            }

                            leaf rx-error-invalid-magic {
                                type yang:counter64;
                                description "Number of LCP echo-request or echo-reply packets received with an invalid magic number";
                            }

                            leaf rx-error-no-session {
                                type yang:counter64;
                                description "Number of LCP echo or data packets received without an associated session";
                            }

                            leaf rx-discovery {
                                type yang:counter64;
                                description "Number of PPPoE discovery packets received";
                            }

                            leaf rx-ppp-control {
                                type yang:counter64;
                                description "Number of PPP control packets received";
                            }

                            leaf rx-lcp-echo-request {
                                type yang:counter64;
                                description "Number of LCP echo-request packets received";
                            }

                            leaf rx-lcp-echo-reply {
                                type yang:counter64;
                                description "Number of LCP echo-reply packets received";
                            }

                            leaf tx-lcp-echo-request {
                                type yang:counter64;
                                description "Number of LCP echo-request packets transmitted";
                            }

                            leaf tx-lcp-echo-reply {
                                type yang:counter64;
                                description "Number of LCP echo-reply packets transmitted";
                            }

                        } // container pppoe-client

                        container nat {
                            description "NAT statistics per MDA";

                            container dropped {
                                description "NAT related drop counters";

                                container general {
                                    description "General drop reasons";

                                    leaf arp {
                                        type yang:counter64;
                                        description "ARP frames are ignored";
                                    }

                                    leaf checksum-calculation-error {
                                        type yang:counter64;
                                        description "Error while calculating L4 checksum before transmitting";
                                    }

                                    leaf send-error {
                                        type yang:counter64;
                                        description "Packet send error";
                                    }

                                    leaf no-copy-buffer {
                                        type yang:counter64;
                                        description "No buffer to copy frame";
                                    }

                                    leaf mtu-exceeded {
                                        type yang:counter64;
                                        description "Egress MTU exceeded";
                                    }

                                    leaf multicast {
                                        type yang:counter64;
                                        description "Multicast dropped";
                                    }

                                } // container general

                                container receive-errors {
                                    description "Errors in incoming frame format";

                                    leaf l2-error {
                                        type yang:counter64;
                                        description "L2 parse error";
                                    }

                                    leaf l3-not-ip {
                                        type yang:counter64;
                                        description "L3 is not IPv4 or IPv6";
                                    }

                                    leaf ip-invalid-checksum {
                                        type yang:counter64;
                                        description "IPv4 invalid checksum";
                                    }

                                    leaf ip-malformed-header {
                                        type yang:counter64;
                                        description "IP malformed header";
                                    }

                                    leaf ip-malformed-packet {
                                        type yang:counter64;
                                        description "IP malformed packet";
                                    }

                                    leaf ip-zero-ttl {
                                        type yang:counter64;
                                        description "IP zero ttl";
                                    }

                                    leaf ip-opts-or-ext-headers {
                                        type yang:counter64;
                                        description "IPv4 options or IPv6 extension headers";
                                    }

                                    leaf ip-parse-error {
                                        type yang:counter64;
                                        description "IP parse error";
                                    }

                                    leaf ipv6-fragments-unsupported {
                                        type yang:counter64;
                                        description "IPv6 fragments unsupported";
                                    }

                                    leaf ipv6-extension-header-parse-error {
                                        type yang:counter64;
                                        description "IPv6 extension headers parse error";
                                    }

                                    leaf dslite-unsupported-next-header {
                                        type yang:counter64;
                                        description "Dual-stack-lite next header unsupported";
                                    }

                                    leaf l4-unsupported-protocol {
                                        type yang:counter64;
                                        description "Unsupported L4 protocol";
                                    }

                                    leaf tcp-udp-malformed-header {
                                        type yang:counter64;
                                        description "TCP/UDP malformed header";
                                    }

                                    leaf tcp-udp-invalid-checksum {
                                        type yang:counter64;
                                        description "TCP/UDP invalid checksum";
                                    }

                                    leaf icmp-embedded-ipv6-extension-header-parse-error {
                                        type yang:counter64;
                                        description "ICMP embedded IPv6 extension header parse error";
                                    }

                                    leaf other-parse-error {
                                        type yang:counter64;
                                        description "Other parse error";
                                    }

                                } // container receive-errors

                                container flow {
                                    description "NAT flow drop reasons";

                                    leaf no-matching-flow {
                                        type yang:counter64;
                                        description "No matching flow";
                                    }

                                    leaf forwarding-blocked {
                                        type yang:counter64;
                                        description
                                            "Management core has blocked new flow creation or forwarding.
                                             Reasons include policies or port-blocks being released.";
                                    }

                                    leaf tcp-resetting {
                                        type yang:counter64;
                                        description "TCP flow is in reset state but not yet cleaned up";
                                    }

                                } // container flow

                                container flow-creation-failed {
                                    description "NAT flow could not be created";

                                    leaf no-resources {
                                        type yang:counter64;
                                        description "No resources";
                                    }

                                    leaf no-host-resources {
                                        type yang:counter64;
                                        description "Could not create host";
                                    }

                                    leaf no-ip-or-port-resources {
                                        type yang:counter64;
                                        description "Could not allocate ip or port-range";
                                    }

                                    leaf max-flows-exceeded {
                                        type yang:counter64;
                                        description "Max number of flows exceeded";
                                    }

                                    leaf ipv6-downstream-prohibited {
                                        type yang:counter64;
                                        description "IPv6 downstream traffic prohibited";
                                    }

                                    leaf address-dependent-filtering {
                                        type yang:counter64;
                                        description "Address dependent filtering";
                                    }

                                    leaf firewall-address-dependent-filtering {
                                        type yang:counter64;
                                        description "Firewall address dependent filtering";
                                    }

                                    leaf transient-no-policy {
                                        type yang:counter64;
                                        description "Policy could temporarily not be used";
                                    }

                                    leaf unmatched-policy {
                                        type yang:counter64;
                                        description "Matched policy not in use by subscriber";
                                    }

                                    leaf conflicting-policies {
                                        type yang:counter64;
                                        description "Conflicting policies";
                                    }

                                    leaf port-range-log-failed {
                                        type yang:counter64;
                                        description "Logging of port range allocation failed";
                                    }

                                    leaf flow-log-failed {
                                        type yang:counter64;
                                        description "Logging of flow creation failed";
                                    }

                                    leaf multiple-host-or-subscriber-ip {
                                        type yang:counter64;
                                        description "No multiple host or subscriber IPs allowed";
                                    }

                                    leaf destination-nat-destination-mismatch {
                                        type yang:counter64;
                                        description "Destination NAT destination IP mismatch";
                                    }

                                    leaf destination-nat-foreign-mismatch {
                                        type yang:counter64;
                                        description "Destination NAT foreign IP mismatch";
                                    }

                                    leaf ambiguous-flow-key {
                                        type yang:counter64;
                                        description "Ambiguous flow key";
                                    }

                                    leaf requested-port-not-in-host-range {
                                        type yang:counter64;
                                        description "Requested port not in host port range";
                                    }

                                    leaf destination-not-routable {
                                        type yang:counter64;
                                        description "Destination IP is not routable";
                                    }

                                    leaf dslite-unknown-aftr {
                                        type yang:counter64;
                                        description "Dual-stack-lite unknown AFTR address";
                                    }

                                    leaf pppoe-uplink-down {
                                        type yang:counter64;
                                        description "PPPoE uplink down";
                                    }

                                    leaf subscriber-id-unknown {
                                        type yang:counter64;
                                        description "Subscriber-id unknown";
                                    }

                                    leaf tcp-unexpected-rst {
                                        type yang:counter64;
                                        description "No flow creation on TCP RST";
                                    }

                                    leaf tcp-unexpected-fin {
                                        type yang:counter64;
                                        description "No flow creation on TCP FIN";
                                    }

                                    leaf tcp-unexpected-flags {
                                        type yang:counter64;
                                        description "No flow creation for invalid flags combinations";
                                    }

                                    leaf portrange-outside-ip-conflict {
                                        type yang:counter64;
                                        description "conflict between forced port range and outside IP of existing flow";
                                    }

                                    leaf requested-outside-port-conflict {
                                        type yang:counter64;
                                        description "conflict between requested outside port and outside port of existing flow";
                                    }

                                } // container flow-creation-failed

                                container icmp {
                                    description "ICMP";

                                    leaf unsupported-type-v4 {
                                        type yang:counter64;
                                        description "ICMP type unsupported";
                                    }

                                    leaf unsupported-type-v6 {
                                        type yang:counter64;
                                        description "ICMPv6 type unsupported";
                                    }

                                    leaf unsupported-type-for-translation {
                                        type yang:counter64;
                                        description "ICMP type unsupported for 4 to 6 translation";
                                    }

                                    leaf unsupported-length-for-translation {
                                        type yang:counter64;
                                        description "ICMP length error for 4 to 6 translation";
                                    }

                                    leaf unsupported-local {
                                        type yang:counter64;
                                        description "ICMP to l2aware-host gateway address unsupported";
                                    }

                                    leaf invalid-checksum {
                                        type yang:counter64;
                                        description "ICMP/ICMPv6 invalid checksum";
                                    }

                                    leaf embedded-invalid-checksum {
                                        type yang:counter64;
                                        description "ICMP invalid embedded IP checksum";
                                    }

                                    leaf unsupported-embedded-l3 {
                                        type yang:counter64;
                                        description "ICMP/ICMPv6 invalid embedded IP";
                                    }

                                    leaf unsupported-embedded-l4 {
                                        type yang:counter64;
                                        description "ICMP/ICMPv6 invalid embedded L4";
                                    }

                                    leaf too-short {
                                        type yang:counter64;
                                        description "ICMP/ICMPv6 too short";
                                    }

                                    leaf invalid-length {
                                        type yang:counter64;
                                        description "ICMP/ICMPv6 invalid length";
                                    }

                                    leaf fragmented {
                                        type yang:counter64;
                                        description "ICMP/ICMPv6 fragmentation";
                                    }

                                    leaf icmp6-packet-too-big {
                                        type yang:counter64;
                                        description "ICMP6 Packet-Too-Big with mtu < 1280";
                                    }

                                } // container icmp

                                container nat64 {
                                    description "NAT64";

                                    leaf disabled {
                                        type yang:counter64;
                                        description "NAT64 disabled";
                                    }

                                    leaf invalid-source-address {
                                        type yang:counter64;
                                        description "NAT64 invalid source address";
                                    }

                                    leaf fragment-zero-checksum {
                                        type yang:counter64;
                                        description "NAT64 fragment has zero checksum";
                                    }

                                    leaf ipv4-zero-checksum {
                                        type yang:counter64;
                                        description "NAT64 IPv4 zero checksum";
                                    }

                                    leaf icmp-fragment-unsupported {
                                        type yang:counter64;
                                        description "NAT64 ICMP fragments unsupported";
                                    }

                                    leaf unknown-next-header {
                                        type yang:counter64;
                                        description "NAT64 unknown next header";
                                    }

                                    leaf embedded-ipv4-options {
                                        type yang:counter64;
                                        description "NAT64 ICMP embedded IPv4 options";
                                    }

                                } // container nat64

                                container fragments {
                                    description "Fragments";

                                    leaf too-many-fragmented-packets {
                                        type yang:counter64;
                                        description "Too many fragmented packets";
                                    }

                                    leaf too-many-fragment-buffers {
                                        type yang:counter64;
                                        description "Fragmentation buffers exhausted";
                                    }

                                    leaf too-many-fragment-holes {
                                        type yang:counter64;
                                        description "Too many fragment holes";
                                    }

                                    leaf too-many-fragments-per-packet {
                                        type yang:counter64;
                                        description "Too many fragments for IP packet";
                                    }

                                    leaf too-many-fragment-lists-for-flow {
                                        type yang:counter64;
                                        description "Too many fragment lists for flow";
                                    }

                                    leaf fragment-list-expired {
                                        type yang:counter64;
                                        description "Fragment list expired";
                                    }

                                    leaf fragment-list-cleanup-in-progress {
                                        type yang:counter64;
                                        description "Fragment list cleanup in progress";
                                    }

                                    leaf reassembly-failed {
                                        type yang:counter64;
                                        description "Reassembly failed";
                                    }

                                } // container fragments

                                container radius {
                                    description "RADIUS";

                                    leaf error {
                                        type yang:counter64;
                                        description "Error while processing RADIUS packet";
                                    }

                                    leaf no-send-resources {
                                        type yang:counter64;
                                        description "No resources to send RADIUS packet";
                                    }

                                } // container radius

                                container upnp {
                                    description "UPnP";

                                    leaf ssdp {
                                        type yang:counter64;
                                        description "SSDP dropped";
                                    }

                                    leaf control {
                                        type yang:counter64;
                                        description "UPnP control dropped";
                                    }

                                } // container upnp

                                container service-chaining {
                                    description "Service-Chaining";

                                    leaf tx-error {
                                        type yang:counter64;
                                        description "Transmit error";
                                    }

                                    leaf rx-error {
                                        type yang:counter64;
                                        description "Receive error";
                                    }

                                    leaf rx-unsupported {
                                        type yang:counter64;
                                        description "Unhandled frames";
                                    }

                                    leaf filter-action-drop {
                                        type yang:counter64;
                                        description "Frames dropped by vas-filter";
                                    }

                                } // container service-chaining

                                container inter-chassis-sync {
                                    description "Inter-Chassis Synchronisation";

                                    leaf standby-drop {
                                        type yang:counter64;
                                        description "Standby drop";
                                    }

                                } // container inter-chassis-sync

                            } // container dropped

                            container flow {
                                description "NAT flow statistics";

                                leaf new-flow {
                                    type yang:counter64;
                                    description "New flow created";
                                }

                                leaf found-flow {
                                    type yang:counter64;
                                    description "Frame matched existing flow";
                                }

                                leaf tcp-closed {
                                    type yang:counter64;
                                    description "Flow terminated by TCP session close";
                                }

                                container timeouts {
                                    description "NAT flow timeouts";

                                    leaf tcp-expired {
                                        type yang:counter64;
                                        description "TCP flow expired";
                                    }

                                    leaf udp-expired {
                                        type yang:counter64;
                                        description "UDP flow expired";
                                    }

                                    leaf icmp-expired {
                                        type yang:counter64;
                                        description "ICMP/ICMPv6 flow expired";
                                    }

                                    leaf gre-expired {
                                        type yang:counter64;
                                        description "GRE flow expired";
                                    }

                                    leaf ipv6-any-l4-expired {
                                        type yang:counter64;
                                        description "Any IPv6 L4 flow expired";
                                    }

                                } // container timeouts

                            } // container flow

                            container icmp {
                                description "ICMP";

                                leaf to-local {
                                    type yang:counter64;
                                    description "ICMP to local address";
                                }

                            } // container icmp

                            container dslite {
                                description "Dual-Stack Lite";

                                leaf forward {
                                    type yang:counter64;
                                    description "IPv6 dual-stack-lite frame forwarded";
                                }

                            } // container dslite

                            container fragmentation {
                                description "Fragmentation";

                                leaf ipv6 {
                                    type yang:counter64;
                                    description "IPv6 frame was fragmented";
                                }

                            } // container fragmentation

                            container reassembly {
                                description "Reassembly";

                                leaf packets {
                                    type yang:counter64;
                                    description "Reassembled frames";
                                }

                            } // container reassembly

                            container flow-log {
                                description "Flow logging";

                                leaf logged-flow-create {
                                    type yang:counter64;
                                    description "Flow create logged";
                                }

                                leaf logged-flow-delete {
                                    type yang:counter64;
                                    description "Flow delete logged";
                                }

                                leaf tx-packet {
                                    type yang:counter64;
                                    description "Transmitted flow log frames";
                                }

                                leaf rate-limit-drop {
                                    type yang:counter64;
                                    description "Flow log frames dropped by rate limiting";
                                }

                            } // container flow-log

                            container radius {
                                description "RADIUS";

                                leaf to-local {
                                    type yang:counter64;
                                    description "Frame handled by local radius client";
                                }

                            } // container radius

                            container subscriber-id-cache {
                                description "Subscriber id cache";

                                leaf cached {
                                    type yang:counter64;
                                    description "Subscriber-id cached";
                                }

                                leaf delayed {
                                    type yang:counter64;
                                    description "Subscriber-id delayed";
                                }

                                leaf cache-timeout {
                                    type yang:counter64;
                                    description "Subscriber-id timeout";
                                }

                            } // container subscriber-id-cache

                            container fragments {
                                description "Fragments";

                                leaf rx-large-scale {
                                    type yang:counter64;
                                    description "Fragments received on large-scale nat interface";
                                }

                                leaf rx-dual-stack-lite {
                                    type yang:counter64;
                                    description "Fragments received on dual-stack-lite interface";
                                }

                                leaf rx-l2aware {
                                    type yang:counter64;
                                    description "Fragments received on l2aware interface";
                                }

                                leaf rx-outside {
                                    type yang:counter64;
                                    description "Fragments received on outside interface";
                                }

                                leaf tx-large-scale {
                                    type yang:counter64;
                                    description "Fragments transmitted on large-scale nat interface";
                                }

                                leaf tx-dual-stack-lite {
                                    type yang:counter64;
                                    description "Fragments transmitted on dual-stack-lite interface";
                                }

                                leaf tx-l2aware {
                                    type yang:counter64;
                                    description "Fragments transmitted on l2aware interface";
                                }

                                leaf tx-nat64 {
                                    type yang:counter64;
                                    description "Fragments transmitted on nat64 interface";
                                }

                                leaf tx-outside {
                                    type yang:counter64;
                                    description "Fragments transmitted on outside interface";
                                }

                            } // container fragments

                            container upnp {
                                description "UPnP";

                                leaf ssdp-rx {
                                    type yang:counter64;
                                    description "SSDP frames received";
                                }

                                leaf ssdp-tx {
                                    type yang:counter64;
                                    description "SSDP frames transmitted";
                                }

                                leaf control-rx {
                                    type yang:counter64;
                                    description "UPnP control frames received";
                                }

                                leaf control-tx {
                                    type yang:counter64;
                                    description "UPnP control frames transmitted";
                                }

                                leaf rate-limited-request {
                                    type yang:counter64;
                                    description "UPnP query rate limited";
                                }

                                leaf pinhole-without-default-policy {
                                    type yang:counter64;
                                    description "Attempt to create pinhole without default policy";
                                }

                                leaf pinhole-without-source-nat {
                                    type yang:counter64;
                                    description "Attempt to create pinhole with source-nat disabled";
                                }

                            } // container upnp

                            container service-chaining {
                                description "Service-Chaining";

                                leaf rx {
                                    type yang:counter64;
                                    description "Service-chaining frames received";
                                }

                                leaf tx {
                                    type yang:counter64;
                                    description "Service-chaining frames transmitted";
                                }

                            } // container service-chaining

                        } // container nat

                    } // container statistics

                } // list mda

            } // list nat-group

            list wlan-gw-group {
                key "id";
                description "Enter the wlan-gw-group list instance";

                leaf id {
                    type types-isa:wlan-gw-group-id;
                    description "Unique value which to identify the WLAN-GW group within a chassis in system";
                }

                leaf oper-state {
                    type types-sros:oper-state;
                    description "Operational status of a WLAN-GW group";
                }

                leaf degraded {
                    type boolean;
                    description
                        "Indicates if the WLAN-GW group is degraded,
                         while operationally still in service.";
                }

                list iom {
                    key "slot-number";
                    description "Add a list entry for iom";

                    leaf slot-number {
                        type leafref {
                            path "../../../../card/slot-number";
                        }
                        description "IOM slot to use in the WLAN-GW group";
                    }

                    leaf oper-state {
                        type types-isa:wlan-gw-isa-iom-oper-state;
                        description "Operational status of a WLAN-GW group IOM";
                    }

                    list mda {
                        key "mda-id";
                        description "MDAs used for WLAN-GW functionality";

                        leaf mda-id {
                            type types-isa:slot-mda;
                            description "MDA slot value";
                        }

                        leaf oper-state {
                            type types-isa:nat-mda-operational-state;
                            description "Operational status of a WLAN-GW group MDA";
                        }

                        container nat {
                            description "NAT resources";

                            leaf peak-values-last-reset {
                                type yang:date-and-time;
                                description "Moment when the peak values were last reset";
                            }

                            container resources {
                                description "Resource consumption per group mda";

                                container flows {

                                    leaf value {
                                        type yang:gauge64;
                                        description "Actual consumed value";
                                    }

                                    leaf max {
                                        type uint64;
                                        description "The max value this resource can have, depending on the configuration";
                                    }

                                    leaf peak {
                                        type yang:gauge64;
                                        description "The peak value for the resource";
                                    }

                                    leaf peak-timestamp {
                                        type types-sros:date-time;
                                        description "The timestamp when the peak value was observed";
                                    }

                                } // container flows

                                container policies {

                                    leaf value {
                                        type yang:gauge64;
                                        description "Actual consumed value";
                                    }

                                    leaf max {
                                        type uint64;
                                        description "The max value this resource can have, depending on the configuration";
                                    }

                                    leaf peak {
                                        type yang:gauge64;
                                        description "The peak value for the resource";
                                    }

                                    leaf peak-timestamp {
                                        type types-sros:date-time;
                                        description "The timestamp when the peak value was observed";
                                    }

                                } // container policies

                                container subscriber-cache-entries {

                                    leaf value {
                                        type yang:gauge64;
                                        description "Actual consumed value";
                                    }

                                    leaf max {
                                        type uint64;
                                        description "The max value this resource can have, depending on the configuration";
                                    }

                                    leaf peak {
                                        type yang:gauge64;
                                        description "The peak value for the resource";
                                    }

                                    leaf peak-timestamp {
                                        type types-sros:date-time;
                                        description "The timestamp when the peak value was observed";
                                    }

                                } // container subscriber-cache-entries

                                container delayed-icmps {

                                    leaf value {
                                        type yang:gauge64;
                                        description "Actual consumed value";
                                    }

                                    leaf max {
                                        type uint64;
                                        description "The max value this resource can have, depending on the configuration";
                                    }

                                    leaf peak {
                                        type yang:gauge64;
                                        description "The peak value for the resource";
                                    }

                                    leaf peak-timestamp {
                                        type types-sros:date-time;
                                        description "The timestamp when the peak value was observed";
                                    }

                                } // container delayed-icmps

                                container alg-session {

                                    leaf value {
                                        type yang:gauge64;
                                        description "Actual consumed value";
                                    }

                                    leaf max {
                                        type uint64;
                                        description "The max value this resource can have, depending on the configuration";
                                    }

                                    leaf peak {
                                        type yang:gauge64;
                                        description "The peak value for the resource";
                                    }

                                    leaf peak-timestamp {
                                        type types-sros:date-time;
                                        description "The timestamp when the peak value was observed";
                                    }

                                } // container alg-session

                                container fragment-lists {

                                    container upstream {

                                        leaf value {
                                            type yang:gauge64;
                                            description "Actual consumed value";
                                        }

                                        leaf max {
                                            type uint64;
                                            description "The max value this resource can have, depending on the configuration";
                                        }

                                        leaf peak {
                                            type yang:gauge64;
                                            description "The peak value for the resource";
                                        }

                                        leaf peak-timestamp {
                                            type types-sros:date-time;
                                            description "The timestamp when the peak value was observed";
                                        }

                                    } // container upstream

                                    container downstream {

                                        leaf value {
                                            type yang:gauge64;
                                            description "Actual consumed value";
                                        }

                                        leaf max {
                                            type uint64;
                                            description "The max value this resource can have, depending on the configuration";
                                        }

                                        leaf peak {
                                            type yang:gauge64;
                                            description "The peak value for the resource";
                                        }

                                        leaf peak-timestamp {
                                            type types-sros:date-time;
                                            description "The timestamp when the peak value was observed";
                                        }

                                    } // container downstream

                                } // container fragment-lists

                                container fragment-holes {

                                    container upstream {

                                        leaf value {
                                            type yang:gauge64;
                                            description "Actual consumed value";
                                        }

                                        leaf max {
                                            type uint64;
                                            description "The max value this resource can have, depending on the configuration";
                                        }

                                        leaf peak {
                                            type yang:gauge64;
                                            description "The peak value for the resource";
                                        }

                                        leaf peak-timestamp {
                                            type types-sros:date-time;
                                            description "The timestamp when the peak value was observed";
                                        }

                                    } // container upstream

                                    container downstream {

                                        leaf value {
                                            type yang:gauge64;
                                            description "Actual consumed value";
                                        }

                                        leaf max {
                                            type uint64;
                                            description "The max value this resource can have, depending on the configuration";
                                        }

                                        leaf peak {
                                            type yang:gauge64;
                                            description "The peak value for the resource";
                                        }

                                        leaf peak-timestamp {
                                            type types-sros:date-time;
                                            description "The timestamp when the peak value was observed";
                                        }

                                    } // container downstream

                                } // container fragment-holes

                                container fragment-bufs {

                                    container upstream {

                                        leaf value {
                                            type yang:gauge64;
                                            description "Actual consumed value";
                                        }

                                        leaf max {
                                            type uint64;
                                            description "The max value this resource can have, depending on the configuration";
                                        }

                                        leaf peak {
                                            type yang:gauge64;
                                            description "The peak value for the resource";
                                        }

                                        leaf peak-timestamp {
                                            type types-sros:date-time;
                                            description "The timestamp when the peak value was observed";
                                        }

                                    } // container upstream

                                    container downstream {

                                        leaf value {
                                            type yang:gauge64;
                                            description "Actual consumed value";
                                        }

                                        leaf max {
                                            type uint64;
                                            description "The max value this resource can have, depending on the configuration";
                                        }

                                        leaf peak {
                                            type yang:gauge64;
                                            description "The peak value for the resource";
                                        }

                                        leaf peak-timestamp {
                                            type types-sros:date-time;
                                            description "The timestamp when the peak value was observed";
                                        }

                                    } // container downstream

                                } // container fragment-bufs

                                container dormant-subscribers {

                                    leaf value {
                                        type yang:gauge64;
                                        description "Actual consumed value";
                                    }

                                    leaf max {
                                        type uint64;
                                        description "The max value this resource can have, depending on the configuration";
                                    }

                                    leaf peak {
                                        type yang:gauge64;
                                        description "The peak value for the resource";
                                    }

                                    leaf peak-timestamp {
                                        type types-sros:date-time;
                                        description "The timestamp when the peak value was observed";
                                    }

                                } // container dormant-subscribers

                                container upnp {

                                    container mappings {

                                        leaf value {
                                            type yang:gauge64;
                                            description "Actual consumed value";
                                        }

                                        leaf max {
                                            type uint64;
                                            description "The max value this resource can have, depending on the configuration";
                                        }

                                        leaf peak {
                                            type yang:gauge64;
                                            description "The peak value for the resource";
                                        }

                                        leaf peak-timestamp {
                                            type types-sros:date-time;
                                            description "The timestamp when the peak value was observed";
                                        }

                                    } // container mappings

                                    container sessions {

                                        leaf value {
                                            type yang:gauge64;
                                            description "Actual consumed value";
                                        }

                                        leaf max {
                                            type uint64;
                                            description "The max value this resource can have, depending on the configuration";
                                        }

                                        leaf peak {
                                            type yang:gauge64;
                                            description "The peak value for the resource";
                                        }

                                        leaf peak-timestamp {
                                            type types-sros:date-time;
                                            description "The timestamp when the peak value was observed";
                                        }

                                    } // container sessions

                                } // container upnp

                                container pppoe-sessions {

                                    leaf value {
                                        type yang:gauge64;
                                        description "Actual consumed value";
                                    }

                                    leaf max {
                                        type uint64;
                                        description "The max value this resource can have, depending on the configuration";
                                    }

                                    leaf peak {
                                        type yang:gauge64;
                                        description "The peak value for the resource";
                                    }

                                    leaf peak-timestamp {
                                        type types-sros:date-time;
                                        description "The timestamp when the peak value was observed";
                                    }

                                } // container pppoe-sessions

                            } // container resources

                            container statistics {
                                description "ISA statistics";

                                container ip-forwarding {
                                    description "IP forwarding statistics per MDA";

                                    leaf fragments {
                                        type yang:counter64;
                                        description "Fragments handled";
                                    }

                                    leaf reassembled-packets {
                                        type yang:counter64;
                                        description "Frames reassembled";
                                    }

                                    leaf forwarded-packets {
                                        type yang:counter64;
                                        description "Frames forwarded";
                                    }

                                    container receive-errors {
                                        description "Receive errors";

                                        leaf l2-error {
                                            type yang:counter64;
                                            description "L2 parse error";
                                        }

                                        leaf l3-not-ip {
                                            type yang:counter64;
                                            description "L3 is not IPv4 or IPv6";
                                        }

                                        leaf ip-invalid-checksum {
                                            type yang:counter64;
                                            description "IPv4 invalid checksum";
                                        }

                                        leaf ip-malformed-header {
                                            type yang:counter64;
                                            description "IP malformed header";
                                        }

                                        leaf ip-malformed-packet {
                                            type yang:counter64;
                                            description "IP malformed packet";
                                        }

                                        leaf ip-zero-ttl {
                                            type yang:counter64;
                                            description "IP zero ttl";
                                        }

                                        leaf ip-opts-or-ext-headers {
                                            type yang:counter64;
                                            description "IPv4 options or IPv6 extension headers";
                                        }

                                        leaf ip-fragment-unsupported {
                                            type yang:counter64;
                                            description "IP fragment unsupported";
                                        }

                                        leaf ip-error {
                                            type yang:counter64;
                                            description "IP parse error";
                                        }

                                        leaf tcp-udp-malformed-header {
                                            type yang:counter64;
                                            description "TCP/UDP malformed header";
                                        }

                                        leaf tcp-udp-invalid-checksum {
                                            type yang:counter64;
                                            description "TCP/UDP invalid checksum";
                                        }

                                        leaf other {
                                            type yang:counter64;
                                            description "Other parse error";
                                        }

                                    } // container receive-errors

                                    container reassembly-errors {
                                        description "Reassembly errors";

                                        leaf too-many-fragmented-packets {
                                            type yang:counter64;
                                            description "Too many fragmented packets";
                                        }

                                        leaf too-many-fragment-buffers {
                                            type yang:counter64;
                                            description "Too many fragment buffers";
                                        }

                                        leaf too-many-fragment-holes {
                                            type yang:counter64;
                                            description "Too many fragment holes";
                                        }

                                        leaf fragment-filtered {
                                            type yang:counter64;
                                            description "Fragments filtered";
                                        }

                                        leaf fragment-not-supported {
                                            type yang:counter64;
                                            description "Fragment not supported";
                                        }

                                        leaf fragment-list-expired {
                                            type yang:counter64;
                                            description "Fragment list expired";
                                        }

                                        leaf fragment-list-cleanup-in-progress {
                                            type yang:counter64;
                                            description "Fragment list cleanup in progress";
                                        }

                                        leaf reassembly-failed {
                                            type yang:counter64;
                                            description "Reassembly failed";
                                        }

                                    } // container reassembly-errors

                                } // container ip-forwarding

                                container pppoe-client {
                                    description "PPPoE-client statistics per MDA";

                                    leaf rx-error-l2 {
                                        type yang:counter64;
                                        description "Number of packets received with layer 2 parse errors";
                                    }

                                    leaf rx-error-invalid-headers {
                                        type yang:counter64;
                                        description "Number of packets received with invalid PPPoE headers";
                                    }

                                    leaf rx-error-invalid-magic {
                                        type yang:counter64;
                                        description "Number of LCP echo-request or echo-reply packets received with an invalid magic number";
                                    }

                                    leaf rx-error-no-session {
                                        type yang:counter64;
                                        description "Number of LCP echo or data packets received without an associated session";
                                    }

                                    leaf rx-discovery {
                                        type yang:counter64;
                                        description "Number of PPPoE discovery packets received";
                                    }

                                    leaf rx-ppp-control {
                                        type yang:counter64;
                                        description "Number of PPP control packets received";
                                    }

                                    leaf rx-lcp-echo-request {
                                        type yang:counter64;
                                        description "Number of LCP echo-request packets received";
                                    }

                                    leaf rx-lcp-echo-reply {
                                        type yang:counter64;
                                        description "Number of LCP echo-reply packets received";
                                    }

                                    leaf tx-lcp-echo-request {
                                        type yang:counter64;
                                        description "Number of LCP echo-request packets transmitted";
                                    }

                                    leaf tx-lcp-echo-reply {
                                        type yang:counter64;
                                        description "Number of LCP echo-reply packets transmitted";
                                    }

                                } // container pppoe-client

                                container nat {
                                    description "NAT statistics per MDA";

                                    container dropped {
                                        description "NAT related drop counters";

                                        container general {
                                            description "General drop reasons";

                                            leaf arp {
                                                type yang:counter64;
                                                description "ARP frames are ignored";
                                            }

                                            leaf checksum-calculation-error {
                                                type yang:counter64;
                                                description "Error while calculating L4 checksum before transmitting";
                                            }

                                            leaf send-error {
                                                type yang:counter64;
                                                description "Packet send error";
                                            }

                                            leaf no-copy-buffer {
                                                type yang:counter64;
                                                description "No buffer to copy frame";
                                            }

                                            leaf mtu-exceeded {
                                                type yang:counter64;
                                                description "Egress MTU exceeded";
                                            }

                                            leaf multicast {
                                                type yang:counter64;
                                                description "Multicast dropped";
                                            }

                                        } // container general

                                        container receive-errors {
                                            description "Errors in incoming frame format";

                                            leaf l2-error {
                                                type yang:counter64;
                                                description "L2 parse error";
                                            }

                                            leaf l3-not-ip {
                                                type yang:counter64;
                                                description "L3 is not IPv4 or IPv6";
                                            }

                                            leaf ip-invalid-checksum {
                                                type yang:counter64;
                                                description "IPv4 invalid checksum";
                                            }

                                            leaf ip-malformed-header {
                                                type yang:counter64;
                                                description "IP malformed header";
                                            }

                                            leaf ip-malformed-packet {
                                                type yang:counter64;
                                                description "IP malformed packet";
                                            }

                                            leaf ip-zero-ttl {
                                                type yang:counter64;
                                                description "IP zero ttl";
                                            }

                                            leaf ip-opts-or-ext-headers {
                                                type yang:counter64;
                                                description "IPv4 options or IPv6 extension headers";
                                            }

                                            leaf ip-parse-error {
                                                type yang:counter64;
                                                description "IP parse error";
                                            }

                                            leaf ipv6-fragments-unsupported {
                                                type yang:counter64;
                                                description "IPv6 fragments unsupported";
                                            }

                                            leaf ipv6-extension-header-parse-error {
                                                type yang:counter64;
                                                description "IPv6 extension headers parse error";
                                            }

                                            leaf dslite-unsupported-next-header {
                                                type yang:counter64;
                                                description "Dual-stack-lite next header unsupported";
                                            }

                                            leaf l4-unsupported-protocol {
                                                type yang:counter64;
                                                description "Unsupported L4 protocol";
                                            }

                                            leaf tcp-udp-malformed-header {
                                                type yang:counter64;
                                                description "TCP/UDP malformed header";
                                            }

                                            leaf tcp-udp-invalid-checksum {
                                                type yang:counter64;
                                                description "TCP/UDP invalid checksum";
                                            }

                                            leaf icmp-embedded-ipv6-extension-header-parse-error {
                                                type yang:counter64;
                                                description "ICMP embedded IPv6 extension header parse error";
                                            }

                                            leaf other-parse-error {
                                                type yang:counter64;
                                                description "Other parse error";
                                            }

                                        } // container receive-errors

                                        container flow {
                                            description "NAT flow drop reasons";

                                            leaf no-matching-flow {
                                                type yang:counter64;
                                                description "No matching flow";
                                            }

                                            leaf forwarding-blocked {
                                                type yang:counter64;
                                                description
                                                    "Management core has blocked new flow creation or forwarding.
                                                     Reasons include policies or port-blocks being released.";
                                            }

                                            leaf tcp-resetting {
                                                type yang:counter64;
                                                description "TCP flow is in reset state but not yet cleaned up";
                                            }

                                        } // container flow

                                        container flow-creation-failed {
                                            description "NAT flow could not be created";

                                            leaf no-resources {
                                                type yang:counter64;
                                                description "No resources";
                                            }

                                            leaf no-host-resources {
                                                type yang:counter64;
                                                description "Could not create host";
                                            }

                                            leaf no-ip-or-port-resources {
                                                type yang:counter64;
                                                description "Could not allocate ip or port-range";
                                            }

                                            leaf max-flows-exceeded {
                                                type yang:counter64;
                                                description "Max number of flows exceeded";
                                            }

                                            leaf ipv6-downstream-prohibited {
                                                type yang:counter64;
                                                description "IPv6 downstream traffic prohibited";
                                            }

                                            leaf address-dependent-filtering {
                                                type yang:counter64;
                                                description "Address dependent filtering";
                                            }

                                            leaf firewall-address-dependent-filtering {
                                                type yang:counter64;
                                                description "Firewall address dependent filtering";
                                            }

                                            leaf transient-no-policy {
                                                type yang:counter64;
                                                description "Policy could temporarily not be used";
                                            }

                                            leaf unmatched-policy {
                                                type yang:counter64;
                                                description "Matched policy not in use by subscriber";
                                            }

                                            leaf conflicting-policies {
                                                type yang:counter64;
                                                description "Conflicting policies";
                                            }

                                            leaf port-range-log-failed {
                                                type yang:counter64;
                                                description "Logging of port range allocation failed";
                                            }

                                            leaf flow-log-failed {
                                                type yang:counter64;
                                                description "Logging of flow creation failed";
                                            }

                                            leaf multiple-host-or-subscriber-ip {
                                                type yang:counter64;
                                                description "No multiple host or subscriber IPs allowed";
                                            }

                                            leaf destination-nat-destination-mismatch {
                                                type yang:counter64;
                                                description "Destination NAT destination IP mismatch";
                                            }

                                            leaf destination-nat-foreign-mismatch {
                                                type yang:counter64;
                                                description "Destination NAT foreign IP mismatch";
                                            }

                                            leaf ambiguous-flow-key {
                                                type yang:counter64;
                                                description "Ambiguous flow key";
                                            }

                                            leaf requested-port-not-in-host-range {
                                                type yang:counter64;
                                                description "Requested port not in host port range";
                                            }

                                            leaf destination-not-routable {
                                                type yang:counter64;
                                                description "Destination IP is not routable";
                                            }

                                            leaf dslite-unknown-aftr {
                                                type yang:counter64;
                                                description "Dual-stack-lite unknown AFTR address";
                                            }

                                            leaf pppoe-uplink-down {
                                                type yang:counter64;
                                                description "PPPoE uplink down";
                                            }

                                            leaf subscriber-id-unknown {
                                                type yang:counter64;
                                                description "Subscriber-id unknown";
                                            }

                                            leaf tcp-unexpected-rst {
                                                type yang:counter64;
                                                description "No flow creation on TCP RST";
                                            }

                                            leaf tcp-unexpected-fin {
                                                type yang:counter64;
                                                description "No flow creation on TCP FIN";
                                            }

                                            leaf tcp-unexpected-flags {
                                                type yang:counter64;
                                                description "No flow creation for invalid flags combinations";
                                            }

                                            leaf portrange-outside-ip-conflict {
                                                type yang:counter64;
                                                description "conflict between forced port range and outside IP of existing flow";
                                            }

                                            leaf requested-outside-port-conflict {
                                                type yang:counter64;
                                                description "conflict between requested outside port and outside port of existing flow";
                                            }

                                        } // container flow-creation-failed

                                        container icmp {
                                            description "ICMP";

                                            leaf unsupported-type-v4 {
                                                type yang:counter64;
                                                description "ICMP type unsupported";
                                            }

                                            leaf unsupported-type-v6 {
                                                type yang:counter64;
                                                description "ICMPv6 type unsupported";
                                            }

                                            leaf unsupported-type-for-translation {
                                                type yang:counter64;
                                                description "ICMP type unsupported for 4 to 6 translation";
                                            }

                                            leaf unsupported-length-for-translation {
                                                type yang:counter64;
                                                description "ICMP length error for 4 to 6 translation";
                                            }

                                            leaf unsupported-local {
                                                type yang:counter64;
                                                description "ICMP to l2aware-host gateway address unsupported";
                                            }

                                            leaf invalid-checksum {
                                                type yang:counter64;
                                                description "ICMP/ICMPv6 invalid checksum";
                                            }

                                            leaf embedded-invalid-checksum {
                                                type yang:counter64;
                                                description "ICMP invalid embedded IP checksum";
                                            }

                                            leaf unsupported-embedded-l3 {
                                                type yang:counter64;
                                                description "ICMP/ICMPv6 invalid embedded IP";
                                            }

                                            leaf unsupported-embedded-l4 {
                                                type yang:counter64;
                                                description "ICMP/ICMPv6 invalid embedded L4";
                                            }

                                            leaf too-short {
                                                type yang:counter64;
                                                description "ICMP/ICMPv6 too short";
                                            }

                                            leaf invalid-length {
                                                type yang:counter64;
                                                description "ICMP/ICMPv6 invalid length";
                                            }

                                            leaf fragmented {
                                                type yang:counter64;
                                                description "ICMP/ICMPv6 fragmentation";
                                            }

                                            leaf icmp6-packet-too-big {
                                                type yang:counter64;
                                                description "ICMP6 Packet-Too-Big with mtu < 1280";
                                            }

                                        } // container icmp

                                        container nat64 {
                                            description "NAT64";

                                            leaf disabled {
                                                type yang:counter64;
                                                description "NAT64 disabled";
                                            }

                                            leaf invalid-source-address {
                                                type yang:counter64;
                                                description "NAT64 invalid source address";
                                            }

                                            leaf fragment-zero-checksum {
                                                type yang:counter64;
                                                description "NAT64 fragment has zero checksum";
                                            }

                                            leaf ipv4-zero-checksum {
                                                type yang:counter64;
                                                description "NAT64 IPv4 zero checksum";
                                            }

                                            leaf icmp-fragment-unsupported {
                                                type yang:counter64;
                                                description "NAT64 ICMP fragments unsupported";
                                            }

                                            leaf unknown-next-header {
                                                type yang:counter64;
                                                description "NAT64 unknown next header";
                                            }

                                            leaf embedded-ipv4-options {
                                                type yang:counter64;
                                                description "NAT64 ICMP embedded IPv4 options";
                                            }

                                        } // container nat64

                                        container fragments {
                                            description "Fragments";

                                            leaf too-many-fragmented-packets {
                                                type yang:counter64;
                                                description "Too many fragmented packets";
                                            }

                                            leaf too-many-fragment-buffers {
                                                type yang:counter64;
                                                description "Fragmentation buffers exhausted";
                                            }

                                            leaf too-many-fragment-holes {
                                                type yang:counter64;
                                                description "Too many fragment holes";
                                            }

                                            leaf too-many-fragments-per-packet {
                                                type yang:counter64;
                                                description "Too many fragments for IP packet";
                                            }

                                            leaf too-many-fragment-lists-for-flow {
                                                type yang:counter64;
                                                description "Too many fragment lists for flow";
                                            }

                                            leaf fragment-list-expired {
                                                type yang:counter64;
                                                description "Fragment list expired";
                                            }

                                            leaf fragment-list-cleanup-in-progress {
                                                type yang:counter64;
                                                description "Fragment list cleanup in progress";
                                            }

                                            leaf reassembly-failed {
                                                type yang:counter64;
                                                description "Reassembly failed";
                                            }

                                        } // container fragments

                                        container radius {
                                            description "RADIUS";

                                            leaf error {
                                                type yang:counter64;
                                                description "Error while processing RADIUS packet";
                                            }

                                            leaf no-send-resources {
                                                type yang:counter64;
                                                description "No resources to send RADIUS packet";
                                            }

                                        } // container radius

                                        container upnp {
                                            description "UPnP";

                                            leaf ssdp {
                                                type yang:counter64;
                                                description "SSDP dropped";
                                            }

                                            leaf control {
                                                type yang:counter64;
                                                description "UPnP control dropped";
                                            }

                                        } // container upnp

                                        container service-chaining {
                                            description "Service-Chaining";

                                            leaf tx-error {
                                                type yang:counter64;
                                                description "Transmit error";
                                            }

                                            leaf rx-error {
                                                type yang:counter64;
                                                description "Receive error";
                                            }

                                            leaf rx-unsupported {
                                                type yang:counter64;
                                                description "Unhandled frames";
                                            }

                                            leaf filter-action-drop {
                                                type yang:counter64;
                                                description "Frames dropped by vas-filter";
                                            }

                                        } // container service-chaining

                                        container inter-chassis-sync {
                                            description "Inter-Chassis Synchronisation";

                                            leaf standby-drop {
                                                type yang:counter64;
                                                description "Standby drop";
                                            }

                                        } // container inter-chassis-sync

                                    } // container dropped

                                    container flow {
                                        description "NAT flow statistics";

                                        leaf new-flow {
                                            type yang:counter64;
                                            description "New flow created";
                                        }

                                        leaf found-flow {
                                            type yang:counter64;
                                            description "Frame matched existing flow";
                                        }

                                        leaf tcp-closed {
                                            type yang:counter64;
                                            description "Flow terminated by TCP session close";
                                        }

                                        container timeouts {
                                            description "NAT flow timeouts";

                                            leaf tcp-expired {
                                                type yang:counter64;
                                                description "TCP flow expired";
                                            }

                                            leaf udp-expired {
                                                type yang:counter64;
                                                description "UDP flow expired";
                                            }

                                            leaf icmp-expired {
                                                type yang:counter64;
                                                description "ICMP/ICMPv6 flow expired";
                                            }

                                            leaf gre-expired {
                                                type yang:counter64;
                                                description "GRE flow expired";
                                            }

                                            leaf ipv6-any-l4-expired {
                                                type yang:counter64;
                                                description "Any IPv6 L4 flow expired";
                                            }

                                        } // container timeouts

                                    } // container flow

                                    container icmp {
                                        description "ICMP";

                                        leaf to-local {
                                            type yang:counter64;
                                            description "ICMP to local address";
                                        }

                                    } // container icmp

                                    container dslite {
                                        description "Dual-Stack Lite";

                                        leaf forward {
                                            type yang:counter64;
                                            description "IPv6 dual-stack-lite frame forwarded";
                                        }

                                    } // container dslite

                                    container fragmentation {
                                        description "Fragmentation";

                                        leaf ipv6 {
                                            type yang:counter64;
                                            description "IPv6 frame was fragmented";
                                        }

                                    } // container fragmentation

                                    container reassembly {
                                        description "Reassembly";

                                        leaf packets {
                                            type yang:counter64;
                                            description "Reassembled frames";
                                        }

                                    } // container reassembly

                                    container flow-log {
                                        description "Flow logging";

                                        leaf logged-flow-create {
                                            type yang:counter64;
                                            description "Flow create logged";
                                        }

                                        leaf logged-flow-delete {
                                            type yang:counter64;
                                            description "Flow delete logged";
                                        }

                                        leaf tx-packet {
                                            type yang:counter64;
                                            description "Transmitted flow log frames";
                                        }

                                        leaf rate-limit-drop {
                                            type yang:counter64;
                                            description "Flow log frames dropped by rate limiting";
                                        }

                                    } // container flow-log

                                    container radius {
                                        description "RADIUS";

                                        leaf to-local {
                                            type yang:counter64;
                                            description "Frame handled by local radius client";
                                        }

                                    } // container radius

                                    container subscriber-id-cache {
                                        description "Subscriber id cache";

                                        leaf cached {
                                            type yang:counter64;
                                            description "Subscriber-id cached";
                                        }

                                        leaf delayed {
                                            type yang:counter64;
                                            description "Subscriber-id delayed";
                                        }

                                        leaf cache-timeout {
                                            type yang:counter64;
                                            description "Subscriber-id timeout";
                                        }

                                    } // container subscriber-id-cache

                                    container fragments {
                                        description "Fragments";

                                        leaf rx-large-scale {
                                            type yang:counter64;
                                            description "Fragments received on large-scale nat interface";
                                        }

                                        leaf rx-dual-stack-lite {
                                            type yang:counter64;
                                            description "Fragments received on dual-stack-lite interface";
                                        }

                                        leaf rx-dormant {
                                            type yang:counter64;
                                            description "Fragments received on dormant interface";
                                        }

                                        leaf rx-l2aware {
                                            type yang:counter64;
                                            description "Fragments received on l2aware interface";
                                        }

                                        leaf rx-outside {
                                            type yang:counter64;
                                            description "Fragments received on outside interface";
                                        }

                                        leaf tx-large-scale {
                                            type yang:counter64;
                                            description "Fragments transmitted on large-scale nat interface";
                                        }

                                        leaf tx-dual-stack-lite {
                                            type yang:counter64;
                                            description "Fragments transmitted on dual-stack-lite interface";
                                        }

                                        leaf tx-dormant {
                                            type yang:counter64;
                                            description "Fragments transmitted on dormant interface";
                                        }

                                        leaf tx-l2aware {
                                            type yang:counter64;
                                            description "Fragments transmitted on l2aware interface";
                                        }

                                        leaf tx-nat64 {
                                            type yang:counter64;
                                            description "Fragments transmitted on nat64 interface";
                                        }

                                        leaf tx-outside {
                                            type yang:counter64;
                                            description "Fragments transmitted on outside interface";
                                        }

                                    } // container fragments

                                    container upnp {
                                        description "UPnP";

                                        leaf ssdp-rx {
                                            type yang:counter64;
                                            description "SSDP frames received";
                                        }

                                        leaf ssdp-tx {
                                            type yang:counter64;
                                            description "SSDP frames transmitted";
                                        }

                                        leaf control-rx {
                                            type yang:counter64;
                                            description "UPnP control frames received";
                                        }

                                        leaf control-tx {
                                            type yang:counter64;
                                            description "UPnP control frames transmitted";
                                        }

                                        leaf rate-limited-request {
                                            type yang:counter64;
                                            description "UPnP query rate limited";
                                        }

                                        leaf pinhole-without-default-policy {
                                            type yang:counter64;
                                            description "Attempt to create pinhole without default policy";
                                        }

                                        leaf pinhole-without-source-nat {
                                            type yang:counter64;
                                            description "Attempt to create pinhole with source-nat disabled";
                                        }

                                    } // container upnp

                                    container service-chaining {
                                        description "Service-Chaining";

                                        leaf rx {
                                            type yang:counter64;
                                            description "Service-chaining frames received";
                                        }

                                        leaf tx {
                                            type yang:counter64;
                                            description "Service-chaining frames transmitted";
                                        }

                                    } // container service-chaining

                                } // container nat

                            } // container statistics

                        } // container nat

                    } // list mda

                } // list iom

                list mda {
                    key "mda-id";
                    description "Add a list entry for mda";

                    leaf mda-id {
                        type types-isa:slot-mda;
                        description "MDA slot value";
                    }

                    leaf oper-state {
                        type types-isa:nat-mda-operational-state;
                        description "Operational status of a WLAN-GW group MDA";
                    }

                    container nat {
                        description "NAT resources";

                        leaf peak-values-last-reset {
                            type yang:date-and-time;
                            description "Moment when the peak values were last reset";
                        }

                        container resources {
                            description "Resource consumption per group mda";

                            container flows {

                                leaf value {
                                    type yang:gauge64;
                                    description "Actual consumed value";
                                }

                                leaf max {
                                    type uint64;
                                    description "The max value this resource can have, depending on the configuration";
                                }

                                leaf peak {
                                    type yang:gauge64;
                                    description "The peak value for the resource";
                                }

                                leaf peak-timestamp {
                                    type types-sros:date-time;
                                    description "The timestamp when the peak value was observed";
                                }

                            } // container flows

                            container policies {

                                leaf value {
                                    type yang:gauge64;
                                    description "Actual consumed value";
                                }

                                leaf max {
                                    type uint64;
                                    description "The max value this resource can have, depending on the configuration";
                                }

                                leaf peak {
                                    type yang:gauge64;
                                    description "The peak value for the resource";
                                }

                                leaf peak-timestamp {
                                    type types-sros:date-time;
                                    description "The timestamp when the peak value was observed";
                                }

                            } // container policies

                            container subscriber-cache-entries {

                                leaf value {
                                    type yang:gauge64;
                                    description "Actual consumed value";
                                }

                                leaf max {
                                    type uint64;
                                    description "The max value this resource can have, depending on the configuration";
                                }

                                leaf peak {
                                    type yang:gauge64;
                                    description "The peak value for the resource";
                                }

                                leaf peak-timestamp {
                                    type types-sros:date-time;
                                    description "The timestamp when the peak value was observed";
                                }

                            } // container subscriber-cache-entries

                            container delayed-icmps {

                                leaf value {
                                    type yang:gauge64;
                                    description "Actual consumed value";
                                }

                                leaf max {
                                    type uint64;
                                    description "The max value this resource can have, depending on the configuration";
                                }

                                leaf peak {
                                    type yang:gauge64;
                                    description "The peak value for the resource";
                                }

                                leaf peak-timestamp {
                                    type types-sros:date-time;
                                    description "The timestamp when the peak value was observed";
                                }

                            } // container delayed-icmps

                            container alg-session {

                                leaf value {
                                    type yang:gauge64;
                                    description "Actual consumed value";
                                }

                                leaf max {
                                    type uint64;
                                    description "The max value this resource can have, depending on the configuration";
                                }

                                leaf peak {
                                    type yang:gauge64;
                                    description "The peak value for the resource";
                                }

                                leaf peak-timestamp {
                                    type types-sros:date-time;
                                    description "The timestamp when the peak value was observed";
                                }

                            } // container alg-session

                            container fragment-lists {

                                container upstream {

                                    leaf value {
                                        type yang:gauge64;
                                        description "Actual consumed value";
                                    }

                                    leaf max {
                                        type uint64;
                                        description "The max value this resource can have, depending on the configuration";
                                    }

                                    leaf peak {
                                        type yang:gauge64;
                                        description "The peak value for the resource";
                                    }

                                    leaf peak-timestamp {
                                        type types-sros:date-time;
                                        description "The timestamp when the peak value was observed";
                                    }

                                } // container upstream

                                container downstream {

                                    leaf value {
                                        type yang:gauge64;
                                        description "Actual consumed value";
                                    }

                                    leaf max {
                                        type uint64;
                                        description "The max value this resource can have, depending on the configuration";
                                    }

                                    leaf peak {
                                        type yang:gauge64;
                                        description "The peak value for the resource";
                                    }

                                    leaf peak-timestamp {
                                        type types-sros:date-time;
                                        description "The timestamp when the peak value was observed";
                                    }

                                } // container downstream

                            } // container fragment-lists

                            container fragment-holes {

                                container upstream {

                                    leaf value {
                                        type yang:gauge64;
                                        description "Actual consumed value";
                                    }

                                    leaf max {
                                        type uint64;
                                        description "The max value this resource can have, depending on the configuration";
                                    }

                                    leaf peak {
                                        type yang:gauge64;
                                        description "The peak value for the resource";
                                    }

                                    leaf peak-timestamp {
                                        type types-sros:date-time;
                                        description "The timestamp when the peak value was observed";
                                    }

                                } // container upstream

                                container downstream {

                                    leaf value {
                                        type yang:gauge64;
                                        description "Actual consumed value";
                                    }

                                    leaf max {
                                        type uint64;
                                        description "The max value this resource can have, depending on the configuration";
                                    }

                                    leaf peak {
                                        type yang:gauge64;
                                        description "The peak value for the resource";
                                    }

                                    leaf peak-timestamp {
                                        type types-sros:date-time;
                                        description "The timestamp when the peak value was observed";
                                    }

                                } // container downstream

                            } // container fragment-holes

                            container fragment-bufs {

                                container upstream {

                                    leaf value {
                                        type yang:gauge64;
                                        description "Actual consumed value";
                                    }

                                    leaf max {
                                        type uint64;
                                        description "The max value this resource can have, depending on the configuration";
                                    }

                                    leaf peak {
                                        type yang:gauge64;
                                        description "The peak value for the resource";
                                    }

                                    leaf peak-timestamp {
                                        type types-sros:date-time;
                                        description "The timestamp when the peak value was observed";
                                    }

                                } // container upstream

                                container downstream {

                                    leaf value {
                                        type yang:gauge64;
                                        description "Actual consumed value";
                                    }

                                    leaf max {
                                        type uint64;
                                        description "The max value this resource can have, depending on the configuration";
                                    }

                                    leaf peak {
                                        type yang:gauge64;
                                        description "The peak value for the resource";
                                    }

                                    leaf peak-timestamp {
                                        type types-sros:date-time;
                                        description "The timestamp when the peak value was observed";
                                    }

                                } // container downstream

                            } // container fragment-bufs

                            container dormant-subscribers {

                                leaf value {
                                    type yang:gauge64;
                                    description "Actual consumed value";
                                }

                                leaf max {
                                    type uint64;
                                    description "The max value this resource can have, depending on the configuration";
                                }

                                leaf peak {
                                    type yang:gauge64;
                                    description "The peak value for the resource";
                                }

                                leaf peak-timestamp {
                                    type types-sros:date-time;
                                    description "The timestamp when the peak value was observed";
                                }

                            } // container dormant-subscribers

                            container upnp {

                                container mappings {

                                    leaf value {
                                        type yang:gauge64;
                                        description "Actual consumed value";
                                    }

                                    leaf max {
                                        type uint64;
                                        description "The max value this resource can have, depending on the configuration";
                                    }

                                    leaf peak {
                                        type yang:gauge64;
                                        description "The peak value for the resource";
                                    }

                                    leaf peak-timestamp {
                                        type types-sros:date-time;
                                        description "The timestamp when the peak value was observed";
                                    }

                                } // container mappings

                                container sessions {

                                    leaf value {
                                        type yang:gauge64;
                                        description "Actual consumed value";
                                    }

                                    leaf max {
                                        type uint64;
                                        description "The max value this resource can have, depending on the configuration";
                                    }

                                    leaf peak {
                                        type yang:gauge64;
                                        description "The peak value for the resource";
                                    }

                                    leaf peak-timestamp {
                                        type types-sros:date-time;
                                        description "The timestamp when the peak value was observed";
                                    }

                                } // container sessions

                            } // container upnp

                            container pppoe-sessions {

                                leaf value {
                                    type yang:gauge64;
                                    description "Actual consumed value";
                                }

                                leaf max {
                                    type uint64;
                                    description "The max value this resource can have, depending on the configuration";
                                }

                                leaf peak {
                                    type yang:gauge64;
                                    description "The peak value for the resource";
                                }

                                leaf peak-timestamp {
                                    type types-sros:date-time;
                                    description "The timestamp when the peak value was observed";
                                }

                            } // container pppoe-sessions

                        } // container resources

                        container statistics {
                            description "ISA statistics";

                            container ip-forwarding {
                                description "IP forwarding statistics per MDA";

                                leaf fragments {
                                    type yang:counter64;
                                    description "Fragments handled";
                                }

                                leaf reassembled-packets {
                                    type yang:counter64;
                                    description "Frames reassembled";
                                }

                                leaf forwarded-packets {
                                    type yang:counter64;
                                    description "Frames forwarded";
                                }

                                container receive-errors {
                                    description "Receive errors";

                                    leaf l2-error {
                                        type yang:counter64;
                                        description "L2 parse error";
                                    }

                                    leaf l3-not-ip {
                                        type yang:counter64;
                                        description "L3 is not IPv4 or IPv6";
                                    }

                                    leaf ip-invalid-checksum {
                                        type yang:counter64;
                                        description "IPv4 invalid checksum";
                                    }

                                    leaf ip-malformed-header {
                                        type yang:counter64;
                                        description "IP malformed header";
                                    }

                                    leaf ip-malformed-packet {
                                        type yang:counter64;
                                        description "IP malformed packet";
                                    }

                                    leaf ip-zero-ttl {
                                        type yang:counter64;
                                        description "IP zero ttl";
                                    }

                                    leaf ip-opts-or-ext-headers {
                                        type yang:counter64;
                                        description "IPv4 options or IPv6 extension headers";
                                    }

                                    leaf ip-fragment-unsupported {
                                        type yang:counter64;
                                        description "IP fragment unsupported";
                                    }

                                    leaf ip-error {
                                        type yang:counter64;
                                        description "IP parse error";
                                    }

                                    leaf tcp-udp-malformed-header {
                                        type yang:counter64;
                                        description "TCP/UDP malformed header";
                                    }

                                    leaf tcp-udp-invalid-checksum {
                                        type yang:counter64;
                                        description "TCP/UDP invalid checksum";
                                    }

                                    leaf other {
                                        type yang:counter64;
                                        description "Other parse error";
                                    }

                                } // container receive-errors

                                container reassembly-errors {
                                    description "Reassembly errors";

                                    leaf too-many-fragmented-packets {
                                        type yang:counter64;
                                        description "Too many fragmented packets";
                                    }

                                    leaf too-many-fragment-buffers {
                                        type yang:counter64;
                                        description "Too many fragment buffers";
                                    }

                                    leaf too-many-fragment-holes {
                                        type yang:counter64;
                                        description "Too many fragment holes";
                                    }

                                    leaf fragment-filtered {
                                        type yang:counter64;
                                        description "Fragments filtered";
                                    }

                                    leaf fragment-not-supported {
                                        type yang:counter64;
                                        description "Fragment not supported";
                                    }

                                    leaf fragment-list-expired {
                                        type yang:counter64;
                                        description "Fragment list expired";
                                    }

                                    leaf fragment-list-cleanup-in-progress {
                                        type yang:counter64;
                                        description "Fragment list cleanup in progress";
                                    }

                                    leaf reassembly-failed {
                                        type yang:counter64;
                                        description "Reassembly failed";
                                    }

                                } // container reassembly-errors

                            } // container ip-forwarding

                            container pppoe-client {
                                description "PPPoE-client statistics per MDA";

                                leaf rx-error-l2 {
                                    type yang:counter64;
                                    description "Number of packets received with layer 2 parse errors";
                                }

                                leaf rx-error-invalid-headers {
                                    type yang:counter64;
                                    description "Number of packets received with invalid PPPoE headers";
                                }

                                leaf rx-error-invalid-magic {
                                    type yang:counter64;
                                    description "Number of LCP echo-request or echo-reply packets received with an invalid magic number";
                                }

                                leaf rx-error-no-session {
                                    type yang:counter64;
                                    description "Number of LCP echo or data packets received without an associated session";
                                }

                                leaf rx-discovery {
                                    type yang:counter64;
                                    description "Number of PPPoE discovery packets received";
                                }

                                leaf rx-ppp-control {
                                    type yang:counter64;
                                    description "Number of PPP control packets received";
                                }

                                leaf rx-lcp-echo-request {
                                    type yang:counter64;
                                    description "Number of LCP echo-request packets received";
                                }

                                leaf rx-lcp-echo-reply {
                                    type yang:counter64;
                                    description "Number of LCP echo-reply packets received";
                                }

                                leaf tx-lcp-echo-request {
                                    type yang:counter64;
                                    description "Number of LCP echo-request packets transmitted";
                                }

                                leaf tx-lcp-echo-reply {
                                    type yang:counter64;
                                    description "Number of LCP echo-reply packets transmitted";
                                }

                            } // container pppoe-client

                            container nat {
                                description "NAT statistics per MDA";

                                container dropped {
                                    description "NAT related drop counters";

                                    container general {
                                        description "General drop reasons";

                                        leaf arp {
                                            type yang:counter64;
                                            description "ARP frames are ignored";
                                        }

                                        leaf checksum-calculation-error {
                                            type yang:counter64;
                                            description "Error while calculating L4 checksum before transmitting";
                                        }

                                        leaf send-error {
                                            type yang:counter64;
                                            description "Packet send error";
                                        }

                                        leaf no-copy-buffer {
                                            type yang:counter64;
                                            description "No buffer to copy frame";
                                        }

                                        leaf mtu-exceeded {
                                            type yang:counter64;
                                            description "Egress MTU exceeded";
                                        }

                                        leaf multicast {
                                            type yang:counter64;
                                            description "Multicast dropped";
                                        }

                                    } // container general

                                    container receive-errors {
                                        description "Errors in incoming frame format";

                                        leaf l2-error {
                                            type yang:counter64;
                                            description "L2 parse error";
                                        }

                                        leaf l3-not-ip {
                                            type yang:counter64;
                                            description "L3 is not IPv4 or IPv6";
                                        }

                                        leaf ip-invalid-checksum {
                                            type yang:counter64;
                                            description "IPv4 invalid checksum";
                                        }

                                        leaf ip-malformed-header {
                                            type yang:counter64;
                                            description "IP malformed header";
                                        }

                                        leaf ip-malformed-packet {
                                            type yang:counter64;
                                            description "IP malformed packet";
                                        }

                                        leaf ip-zero-ttl {
                                            type yang:counter64;
                                            description "IP zero ttl";
                                        }

                                        leaf ip-opts-or-ext-headers {
                                            type yang:counter64;
                                            description "IPv4 options or IPv6 extension headers";
                                        }

                                        leaf ip-parse-error {
                                            type yang:counter64;
                                            description "IP parse error";
                                        }

                                        leaf ipv6-fragments-unsupported {
                                            type yang:counter64;
                                            description "IPv6 fragments unsupported";
                                        }

                                        leaf ipv6-extension-header-parse-error {
                                            type yang:counter64;
                                            description "IPv6 extension headers parse error";
                                        }

                                        leaf dslite-unsupported-next-header {
                                            type yang:counter64;
                                            description "Dual-stack-lite next header unsupported";
                                        }

                                        leaf l4-unsupported-protocol {
                                            type yang:counter64;
                                            description "Unsupported L4 protocol";
                                        }

                                        leaf tcp-udp-malformed-header {
                                            type yang:counter64;
                                            description "TCP/UDP malformed header";
                                        }

                                        leaf tcp-udp-invalid-checksum {
                                            type yang:counter64;
                                            description "TCP/UDP invalid checksum";
                                        }

                                        leaf icmp-embedded-ipv6-extension-header-parse-error {
                                            type yang:counter64;
                                            description "ICMP embedded IPv6 extension header parse error";
                                        }

                                        leaf other-parse-error {
                                            type yang:counter64;
                                            description "Other parse error";
                                        }

                                    } // container receive-errors

                                    container flow {
                                        description "NAT flow drop reasons";

                                        leaf no-matching-flow {
                                            type yang:counter64;
                                            description "No matching flow";
                                        }

                                        leaf forwarding-blocked {
                                            type yang:counter64;
                                            description
                                                "Management core has blocked new flow creation or forwarding.
                                                 Reasons include policies or port-blocks being released.";
                                        }

                                        leaf tcp-resetting {
                                            type yang:counter64;
                                            description "TCP flow is in reset state but not yet cleaned up";
                                        }

                                    } // container flow

                                    container flow-creation-failed {
                                        description "NAT flow could not be created";

                                        leaf no-resources {
                                            type yang:counter64;
                                            description "No resources";
                                        }

                                        leaf no-host-resources {
                                            type yang:counter64;
                                            description "Could not create host";
                                        }

                                        leaf no-ip-or-port-resources {
                                            type yang:counter64;
                                            description "Could not allocate ip or port-range";
                                        }

                                        leaf max-flows-exceeded {
                                            type yang:counter64;
                                            description "Max number of flows exceeded";
                                        }

                                        leaf ipv6-downstream-prohibited {
                                            type yang:counter64;
                                            description "IPv6 downstream traffic prohibited";
                                        }

                                        leaf address-dependent-filtering {
                                            type yang:counter64;
                                            description "Address dependent filtering";
                                        }

                                        leaf firewall-address-dependent-filtering {
                                            type yang:counter64;
                                            description "Firewall address dependent filtering";
                                        }

                                        leaf transient-no-policy {
                                            type yang:counter64;
                                            description "Policy could temporarily not be used";
                                        }

                                        leaf unmatched-policy {
                                            type yang:counter64;
                                            description "Matched policy not in use by subscriber";
                                        }

                                        leaf conflicting-policies {
                                            type yang:counter64;
                                            description "Conflicting policies";
                                        }

                                        leaf port-range-log-failed {
                                            type yang:counter64;
                                            description "Logging of port range allocation failed";
                                        }

                                        leaf flow-log-failed {
                                            type yang:counter64;
                                            description "Logging of flow creation failed";
                                        }

                                        leaf multiple-host-or-subscriber-ip {
                                            type yang:counter64;
                                            description "No multiple host or subscriber IPs allowed";
                                        }

                                        leaf destination-nat-destination-mismatch {
                                            type yang:counter64;
                                            description "Destination NAT destination IP mismatch";
                                        }

                                        leaf destination-nat-foreign-mismatch {
                                            type yang:counter64;
                                            description "Destination NAT foreign IP mismatch";
                                        }

                                        leaf ambiguous-flow-key {
                                            type yang:counter64;
                                            description "Ambiguous flow key";
                                        }

                                        leaf requested-port-not-in-host-range {
                                            type yang:counter64;
                                            description "Requested port not in host port range";
                                        }

                                        leaf destination-not-routable {
                                            type yang:counter64;
                                            description "Destination IP is not routable";
                                        }

                                        leaf dslite-unknown-aftr {
                                            type yang:counter64;
                                            description "Dual-stack-lite unknown AFTR address";
                                        }

                                        leaf pppoe-uplink-down {
                                            type yang:counter64;
                                            description "PPPoE uplink down";
                                        }

                                        leaf subscriber-id-unknown {
                                            type yang:counter64;
                                            description "Subscriber-id unknown";
                                        }

                                        leaf tcp-unexpected-rst {
                                            type yang:counter64;
                                            description "No flow creation on TCP RST";
                                        }

                                        leaf tcp-unexpected-fin {
                                            type yang:counter64;
                                            description "No flow creation on TCP FIN";
                                        }

                                        leaf tcp-unexpected-flags {
                                            type yang:counter64;
                                            description "No flow creation for invalid flags combinations";
                                        }

                                        leaf portrange-outside-ip-conflict {
                                            type yang:counter64;
                                            description "conflict between forced port range and outside IP of existing flow";
                                        }

                                        leaf requested-outside-port-conflict {
                                            type yang:counter64;
                                            description "conflict between requested outside port and outside port of existing flow";
                                        }

                                    } // container flow-creation-failed

                                    container icmp {
                                        description "ICMP";

                                        leaf unsupported-type-v4 {
                                            type yang:counter64;
                                            description "ICMP type unsupported";
                                        }

                                        leaf unsupported-type-v6 {
                                            type yang:counter64;
                                            description "ICMPv6 type unsupported";
                                        }

                                        leaf unsupported-type-for-translation {
                                            type yang:counter64;
                                            description "ICMP type unsupported for 4 to 6 translation";
                                        }

                                        leaf unsupported-length-for-translation {
                                            type yang:counter64;
                                            description "ICMP length error for 4 to 6 translation";
                                        }

                                        leaf unsupported-local {
                                            type yang:counter64;
                                            description "ICMP to l2aware-host gateway address unsupported";
                                        }

                                        leaf invalid-checksum {
                                            type yang:counter64;
                                            description "ICMP/ICMPv6 invalid checksum";
                                        }

                                        leaf embedded-invalid-checksum {
                                            type yang:counter64;
                                            description "ICMP invalid embedded IP checksum";
                                        }

                                        leaf unsupported-embedded-l3 {
                                            type yang:counter64;
                                            description "ICMP/ICMPv6 invalid embedded IP";
                                        }

                                        leaf unsupported-embedded-l4 {
                                            type yang:counter64;
                                            description "ICMP/ICMPv6 invalid embedded L4";
                                        }

                                        leaf too-short {
                                            type yang:counter64;
                                            description "ICMP/ICMPv6 too short";
                                        }

                                        leaf invalid-length {
                                            type yang:counter64;
                                            description "ICMP/ICMPv6 invalid length";
                                        }

                                        leaf fragmented {
                                            type yang:counter64;
                                            description "ICMP/ICMPv6 fragmentation";
                                        }

                                        leaf icmp6-packet-too-big {
                                            type yang:counter64;
                                            description "ICMP6 Packet-Too-Big with mtu < 1280";
                                        }

                                    } // container icmp

                                    container nat64 {
                                        description "NAT64";

                                        leaf disabled {
                                            type yang:counter64;
                                            description "NAT64 disabled";
                                        }

                                        leaf invalid-source-address {
                                            type yang:counter64;
                                            description "NAT64 invalid source address";
                                        }

                                        leaf fragment-zero-checksum {
                                            type yang:counter64;
                                            description "NAT64 fragment has zero checksum";
                                        }

                                        leaf ipv4-zero-checksum {
                                            type yang:counter64;
                                            description "NAT64 IPv4 zero checksum";
                                        }

                                        leaf icmp-fragment-unsupported {
                                            type yang:counter64;
                                            description "NAT64 ICMP fragments unsupported";
                                        }

                                        leaf unknown-next-header {
                                            type yang:counter64;
                                            description "NAT64 unknown next header";
                                        }

                                        leaf embedded-ipv4-options {
                                            type yang:counter64;
                                            description "NAT64 ICMP embedded IPv4 options";
                                        }

                                    } // container nat64

                                    container fragments {
                                        description "Fragments";

                                        leaf too-many-fragmented-packets {
                                            type yang:counter64;
                                            description "Too many fragmented packets";
                                        }

                                        leaf too-many-fragment-buffers {
                                            type yang:counter64;
                                            description "Fragmentation buffers exhausted";
                                        }

                                        leaf too-many-fragment-holes {
                                            type yang:counter64;
                                            description "Too many fragment holes";
                                        }

                                        leaf too-many-fragments-per-packet {
                                            type yang:counter64;
                                            description "Too many fragments for IP packet";
                                        }

                                        leaf too-many-fragment-lists-for-flow {
                                            type yang:counter64;
                                            description "Too many fragment lists for flow";
                                        }

                                        leaf fragment-list-expired {
                                            type yang:counter64;
                                            description "Fragment list expired";
                                        }

                                        leaf fragment-list-cleanup-in-progress {
                                            type yang:counter64;
                                            description "Fragment list cleanup in progress";
                                        }

                                        leaf reassembly-failed {
                                            type yang:counter64;
                                            description "Reassembly failed";
                                        }

                                    } // container fragments

                                    container radius {
                                        description "RADIUS";

                                        leaf error {
                                            type yang:counter64;
                                            description "Error while processing RADIUS packet";
                                        }

                                        leaf no-send-resources {
                                            type yang:counter64;
                                            description "No resources to send RADIUS packet";
                                        }

                                    } // container radius

                                    container upnp {
                                        description "UPnP";

                                        leaf ssdp {
                                            type yang:counter64;
                                            description "SSDP dropped";
                                        }

                                        leaf control {
                                            type yang:counter64;
                                            description "UPnP control dropped";
                                        }

                                    } // container upnp

                                    container service-chaining {
                                        description "Service-Chaining";

                                        leaf tx-error {
                                            type yang:counter64;
                                            description "Transmit error";
                                        }

                                        leaf rx-error {
                                            type yang:counter64;
                                            description "Receive error";
                                        }

                                        leaf rx-unsupported {
                                            type yang:counter64;
                                            description "Unhandled frames";
                                        }

                                        leaf filter-action-drop {
                                            type yang:counter64;
                                            description "Frames dropped by vas-filter";
                                        }

                                    } // container service-chaining

                                    container inter-chassis-sync {
                                        description "Inter-Chassis Synchronisation";

                                        leaf standby-drop {
                                            type yang:counter64;
                                            description "Standby drop";
                                        }

                                    } // container inter-chassis-sync

                                } // container dropped

                                container flow {
                                    description "NAT flow statistics";

                                    leaf new-flow {
                                        type yang:counter64;
                                        description "New flow created";
                                    }

                                    leaf found-flow {
                                        type yang:counter64;
                                        description "Frame matched existing flow";
                                    }

                                    leaf tcp-closed {
                                        type yang:counter64;
                                        description "Flow terminated by TCP session close";
                                    }

                                    container timeouts {
                                        description "NAT flow timeouts";

                                        leaf tcp-expired {
                                            type yang:counter64;
                                            description "TCP flow expired";
                                        }

                                        leaf udp-expired {
                                            type yang:counter64;
                                            description "UDP flow expired";
                                        }

                                        leaf icmp-expired {
                                            type yang:counter64;
                                            description "ICMP/ICMPv6 flow expired";
                                        }

                                        leaf gre-expired {
                                            type yang:counter64;
                                            description "GRE flow expired";
                                        }

                                        leaf ipv6-any-l4-expired {
                                            type yang:counter64;
                                            description "Any IPv6 L4 flow expired";
                                        }

                                    } // container timeouts

                                } // container flow

                                container icmp {
                                    description "ICMP";

                                    leaf to-local {
                                        type yang:counter64;
                                        description "ICMP to local address";
                                    }

                                } // container icmp

                                container dslite {
                                    description "Dual-Stack Lite";

                                    leaf forward {
                                        type yang:counter64;
                                        description "IPv6 dual-stack-lite frame forwarded";
                                    }

                                } // container dslite

                                container fragmentation {
                                    description "Fragmentation";

                                    leaf ipv6 {
                                        type yang:counter64;
                                        description "IPv6 frame was fragmented";
                                    }

                                } // container fragmentation

                                container reassembly {
                                    description "Reassembly";

                                    leaf packets {
                                        type yang:counter64;
                                        description "Reassembled frames";
                                    }

                                } // container reassembly

                                container flow-log {
                                    description "Flow logging";

                                    leaf logged-flow-create {
                                        type yang:counter64;
                                        description "Flow create logged";
                                    }

                                    leaf logged-flow-delete {
                                        type yang:counter64;
                                        description "Flow delete logged";
                                    }

                                    leaf tx-packet {
                                        type yang:counter64;
                                        description "Transmitted flow log frames";
                                    }

                                    leaf rate-limit-drop {
                                        type yang:counter64;
                                        description "Flow log frames dropped by rate limiting";
                                    }

                                } // container flow-log

                                container radius {
                                    description "RADIUS";

                                    leaf to-local {
                                        type yang:counter64;
                                        description "Frame handled by local radius client";
                                    }

                                } // container radius

                                container subscriber-id-cache {
                                    description "Subscriber id cache";

                                    leaf cached {
                                        type yang:counter64;
                                        description "Subscriber-id cached";
                                    }

                                    leaf delayed {
                                        type yang:counter64;
                                        description "Subscriber-id delayed";
                                    }

                                    leaf cache-timeout {
                                        type yang:counter64;
                                        description "Subscriber-id timeout";
                                    }

                                } // container subscriber-id-cache

                                container fragments {
                                    description "Fragments";

                                    leaf rx-large-scale {
                                        type yang:counter64;
                                        description "Fragments received on large-scale nat interface";
                                    }

                                    leaf rx-dual-stack-lite {
                                        type yang:counter64;
                                        description "Fragments received on dual-stack-lite interface";
                                    }

                                    leaf rx-dormant {
                                        type yang:counter64;
                                        description "Fragments received on dormant interface";
                                    }

                                    leaf rx-l2aware {
                                        type yang:counter64;
                                        description "Fragments received on l2aware interface";
                                    }

                                    leaf rx-outside {
                                        type yang:counter64;
                                        description "Fragments received on outside interface";
                                    }

                                    leaf tx-large-scale {
                                        type yang:counter64;
                                        description "Fragments transmitted on large-scale nat interface";
                                    }

                                    leaf tx-dual-stack-lite {
                                        type yang:counter64;
                                        description "Fragments transmitted on dual-stack-lite interface";
                                    }

                                    leaf tx-dormant {
                                        type yang:counter64;
                                        description "Fragments transmitted on dormant interface";
                                    }

                                    leaf tx-l2aware {
                                        type yang:counter64;
                                        description "Fragments transmitted on l2aware interface";
                                    }

                                    leaf tx-nat64 {
                                        type yang:counter64;
                                        description "Fragments transmitted on nat64 interface";
                                    }

                                    leaf tx-outside {
                                        type yang:counter64;
                                        description "Fragments transmitted on outside interface";
                                    }

                                } // container fragments

                                container upnp {
                                    description "UPnP";

                                    leaf ssdp-rx {
                                        type yang:counter64;
                                        description "SSDP frames received";
                                    }

                                    leaf ssdp-tx {
                                        type yang:counter64;
                                        description "SSDP frames transmitted";
                                    }

                                    leaf control-rx {
                                        type yang:counter64;
                                        description "UPnP control frames received";
                                    }

                                    leaf control-tx {
                                        type yang:counter64;
                                        description "UPnP control frames transmitted";
                                    }

                                    leaf rate-limited-request {
                                        type yang:counter64;
                                        description "UPnP query rate limited";
                                    }

                                    leaf pinhole-without-default-policy {
                                        type yang:counter64;
                                        description "Attempt to create pinhole without default policy";
                                    }

                                    leaf pinhole-without-source-nat {
                                        type yang:counter64;
                                        description "Attempt to create pinhole with source-nat disabled";
                                    }

                                } // container upnp

                                container service-chaining {
                                    description "Service-Chaining";

                                    leaf rx {
                                        type yang:counter64;
                                        description "Service-chaining frames received";
                                    }

                                    leaf tx {
                                        type yang:counter64;
                                        description "Service-chaining frames transmitted";
                                    }

                                } // container service-chaining

                            } // container nat

                        } // container statistics

                    } // container nat

                } // list mda

                list member {
                    key "id";
                    description "Statistics about a member of a WLAN-Gateway ISA Group";

                    leaf id {
                        type uint32;
                        description "Unique value which identifies the member within a WLAN-GW group";
                    }

                    leaf mda {
                        type types-isa:slot-mda;
                        description "Indicate the MDA associated with this member";
                    }

                    leaf num-tunnels {
                        type uint32;
                        description
                            "Number of tunnels processed by the MDA associated with this
                             member";
                    }

                    leaf num-ues {
                        type uint32;
                        description
                            "Number of UEs processed by the MDA associated with this
                             member";
                    }

                    leaf num-active-tunnel-shapers {
                        type uint32;
                        description
                            "Number of activated Tunnel Shapers associated with this ISA
                             group member";
                    }

                    leaf num-pending-tunnel-shapers {
                        type uint32;
                        description
                            "Number of pending Tunnel Shapers associated with this ISA group
                             member";
                    }

                    leaf num-failed-tunnel-shapers {
                        type uint32;
                        description
                            "Number of tunnel Qos infrastructure configuration instances on
                             the MDA associated with this ISA group member that have a
                             resource issue";
                    }

                    leaf state {
                        type enumeration {
                            enum "inactive"                     { value 1; }
                            enum "active"                       { value 2; }
                            enum "needs-reset"                  { value 3; }
                            enum "resetting"                    { value 4; }
                            enum "needs-reconcile"              { value 5; }
                            enum "reconciling"                  { value 6; }
                            enum "needs-audit"                  { value 7; }
                            enum "auditing"                     { value 8; }
                            enum "failed-bypass"                { value 9; }
                            enum "active-bypass"                { value 10; }
                        }
                        description "The state of the MDA associated with this member";
                    }

                    container nat {
                        description "NAT resources";

                        leaf reserved-outside-ip-addresses {
                            type yang:gauge32;
                            description "The number of outside IP addresses reserved for the MDA associated with this member";
                        }

                        leaf outside-port-blocks {
                            type yang:gauge32;
                            description "The number of outside port blocks reserved for the MDA associated with this member";
                        }

                        leaf session-usage {
                            type types-isa:nat-usage-level;
                            description "The session usage of the MDA associated with this member";
                        }

                        leaf high-session-usage {
                            type boolean;
                            description
                                "Indicates if the session usage of the MDA associated with this member is high
                                 according to the values of watermark definitions";
                        }

                        leaf prioritized-sessions {
                            type yang:gauge32;
                            description "The current number of active prioritized sessions of the MDA associated with this member";
                        }

                        container resources {
                            description "Resource consumption per member";

                            container port-ranges {

                                container configured {

                                    leaf value {
                                        type yang:gauge64;
                                        description "Actual consumed value";
                                    }

                                    leaf max {
                                        type uint64;
                                        description "The max value this resource can have, depending on the configuration";
                                    }

                                    leaf peak {
                                        type yang:gauge64;
                                        description "The peak value for the resource";
                                    }

                                    leaf peak-timestamp {
                                        type types-sros:date-time;
                                        description "The timestamp when the peak value was observed";
                                    }

                                } // container configured

                                container used {

                                    leaf value {
                                        type yang:gauge64;
                                        description "Actual consumed value";
                                    }

                                    leaf max {
                                        type uint64;
                                        description "The max value this resource can have, depending on the configuration";
                                    }

                                    leaf peak {
                                        type yang:gauge64;
                                        description "The peak value for the resource";
                                    }

                                    leaf peak-timestamp {
                                        type types-sros:date-time;
                                        description "The timestamp when the peak value was observed";
                                    }

                                } // container used

                                container retained {

                                    leaf value {
                                        type yang:gauge64;
                                        description "Actual consumed value";
                                    }

                                    leaf max {
                                        type uint64;
                                        description "The max value this resource can have, depending on the configuration";
                                    }

                                    leaf peak {
                                        type yang:gauge64;
                                        description "The peak value for the resource";
                                    }

                                    leaf peak-timestamp {
                                        type types-sros:date-time;
                                        description "The timestamp when the peak value was observed";
                                    }

                                } // container retained

                            } // container port-ranges

                            container ports {

                                leaf value {
                                    type yang:gauge64;
                                    description "Actual consumed value";
                                }

                                leaf max {
                                    type uint64;
                                    description "The max value this resource can have, depending on the configuration";
                                }

                                leaf peak {
                                    type yang:gauge64;
                                    description "The peak value for the resource";
                                }

                                leaf peak-timestamp {
                                    type types-sros:date-time;
                                    description "The timestamp when the peak value was observed";
                                }

                            } // container ports

                            container ip-addresses {

                                leaf value {
                                    type yang:gauge64;
                                    description "Actual consumed value";
                                }

                                leaf max {
                                    type uint64;
                                    description "The max value this resource can have, depending on the configuration";
                                }

                                leaf peak {
                                    type yang:gauge64;
                                    description "The peak value for the resource";
                                }

                                leaf peak-timestamp {
                                    type types-sros:date-time;
                                    description "The timestamp when the peak value was observed";
                                }

                            } // container ip-addresses

                            container one-to-one-ip-addresses {

                                leaf value {
                                    type yang:gauge64;
                                    description "Actual consumed value";
                                }

                                leaf max {
                                    type uint64;
                                    description "The max value this resource can have, depending on the configuration";
                                }

                                leaf peak {
                                    type yang:gauge64;
                                    description "The peak value for the resource";
                                }

                                leaf peak-timestamp {
                                    type types-sros:date-time;
                                    description "The timestamp when the peak value was observed";
                                }

                            } // container one-to-one-ip-addresses

                            container large-scale-hosts {

                                leaf value {
                                    type yang:gauge64;
                                    description "Actual consumed value";
                                }

                                leaf max {
                                    type uint64;
                                    description "The max value this resource can have, depending on the configuration";
                                }

                                leaf peak {
                                    type yang:gauge64;
                                    description "The peak value for the resource";
                                }

                                leaf peak-timestamp {
                                    type types-sros:date-time;
                                    description "The timestamp when the peak value was observed";
                                }

                            } // container large-scale-hosts

                            container l2-aware {

                                container subscribers {

                                    leaf value {
                                        type yang:gauge64;
                                        description "Actual consumed value";
                                    }

                                    leaf max {
                                        type uint64;
                                        description "The max value this resource can have, depending on the configuration";
                                    }

                                    leaf peak {
                                        type yang:gauge64;
                                        description "The peak value for the resource";
                                    }

                                    leaf peak-timestamp {
                                        type types-sros:date-time;
                                        description "The timestamp when the peak value was observed";
                                    }

                                } // container subscribers

                                container hosts {

                                    leaf value {
                                        type yang:gauge64;
                                        description "Actual consumed value";
                                    }

                                    leaf max {
                                        type uint64;
                                        description "The max value this resource can have, depending on the configuration";
                                    }

                                    leaf peak {
                                        type yang:gauge64;
                                        description "The peak value for the resource";
                                    }

                                    leaf peak-timestamp {
                                        type types-sros:date-time;
                                        description "The timestamp when the peak value was observed";
                                    }

                                } // container hosts

                            } // container l2-aware

                        } // container resources

                    } // container nat

                    container statistics {

                        container packet-errors {
                            description "Packet related errors";

                            leaf malformed-packet {
                                type yang:counter64;
                                description "The received packet isn't valid according to the specification for the protocol";
                            }

                            leaf nge-dropped-packets {
                                type yang:counter64;
                                description "Number of packets dropped by Network Group Encryption";
                            }

                        } // container packet-errors

                        container ue-errors {
                            description "User Equipment related errors";

                            leaf out-of-ues {
                                type yang:counter64;
                                description "Out of UE records";
                            }

                            leaf ues-purged {
                                type yang:counter64;
                                description "Number of ISA-only UEs (e.g. DSM or portal) that were removed because an ESM UE was installed";
                            }

                            leaf out-of-resources {
                                type yang:counter64;
                                description "Out of queue or packet resources";
                            }

                            leaf out-of-url-buffer-resources {
                                type yang:counter64;
                                description "Out of URL buffer resources";
                            }

                            leaf source-address-filtered {
                                type yang:counter64;
                                description "Number of UE packets filtered because of unknown source address";
                            }

                            leaf policing-filtered {
                                type yang:counter64;
                                description "Number of UE packets filtered because of policing";
                            }

                            leaf ue-filtered {
                                type yang:counter64;
                                description "Number of UE packets filtered because of various reasons";
                            }

                        } // container ue-errors

                        container bd-errors {
                            description "Bridge domain related errors";

                            leaf flooding-failed {
                                type yang:counter64;
                                description "Flooding failed because of packet resources";
                            }

                            leaf unknown-vni {
                                type yang:counter64;
                                description "Unknown VNI to access the bridge domain";
                            }

                        } // container bd-errors

                        container forwarded-packets {
                            description "Number of forwarded packets";

                            leaf tunnel-mobility-auto-relearn {
                                type yang:counter64;
                                description "Number of auto-relearn tunnel mobility events";
                            }

                            leaf tx-upstream-tunnel {
                                type yang:counter64;
                                description "Number of tunnel packets transmitted upstream";
                            }

                            leaf tx-downstream-tunnel {
                                type yang:counter64;
                                description "Number of tunnel packets transmitted downstream";
                            }

                            leaf tx-upstream-ue {
                                type yang:counter64;
                                description "Number of UE packets transmitted upstream";
                            }

                            leaf tx-downstream-ue {
                                type yang:counter64;
                                description "Number of UE packets transmitted downstream";
                            }

                            leaf tx-upstream-portal-redirect {
                                type yang:counter64;
                                description "Number of portal packets redirected upstream";
                            }

                            leaf tx-upstream-aa {
                                type yang:counter64;
                                description "Number of packets transmitted upstream to AA";
                            }

                            leaf tx-downstream-aa {
                                type yang:counter64;
                                description "Number of packets transmitted downstream to AA";
                            }

                            leaf tx-upstream-radius-proxy {
                                type yang:counter64;
                                description "Number of RADIUS proxy packets transmitted upstream";
                            }

                        } // container forwarded-packets

                        container reassembly {
                            description "Reassembly related statistics";

                            leaf out-of-fragment-list-resources {
                                type yang:counter64;
                                description "Out of fragment list resources used for incomplete packets with unreceived fragments";
                            }

                            leaf out-of-fragment-buffer-resources {
                                type yang:counter64;
                                description "Out of fragment buffer resources used for received fragments of incomplete packets";
                            }

                            leaf out-of-fragment-hole-resources {
                                type yang:counter64;
                                description "Out of fragment hole resources used for unreceived segments in incomplete packets";
                            }

                            leaf reassembly-failed {
                                type yang:counter64;
                                description "Reassembly failed because of various reasons";
                            }

                            leaf reassembled-packets {
                                type yang:counter64;
                                description "Number of reassembled packets";
                            }

                        } // container reassembly

                        container aa {
                            description "AA related statistics";

                            leaf out-of-resources {
                                type yang:counter64;
                                description "Out of resources because too many AA enabled UEs for an oversubscribed AA";
                            }

                            leaf out-of-url-buffer-resources {
                                type yang:counter64;
                                description "Out of URL buffer resources used for the AA subscriber URL parameter";
                            }

                        } // container aa

                        container radius {
                            description "RADIUS related statistics";

                            leaf tx-authentication-request {
                                type yang:counter64;
                                description "Number of transmitted authentication requests";
                            }

                            leaf rx-authentication-response {
                                type yang:counter64;
                                description "Number of received authentication responses";
                            }

                            leaf rx-authentication-reject {
                                type yang:counter64;
                                description "Number of received authentication rejects";
                            }

                            leaf rx-coa-request {
                                type yang:counter64;
                                description "Number of received CoA requests";
                            }

                            leaf tx-coa-ack {
                                type yang:counter64;
                                description "Number of transmitted CoA acknowledgements";
                            }

                            leaf rx-disconnect-request {
                                type yang:counter64;
                                description "Number of received disconnect requests";
                            }

                            leaf authentication-portal-failed {
                                type yang:counter64;
                                description "Authentication request to install portal user failed";
                            }

                            leaf authentication-dsm-failed {
                                type yang:counter64;
                                description "Authentication request to install DSM user failed";
                            }

                            leaf authentication-xconnect-failed {
                                type yang:counter64;
                                description "Authentication request to install xconnect user failed";
                            }

                            leaf out-of-authentication-transaction-resources {
                                type yang:counter64;
                                description "Out of transaction resources used to transmit authentication requests, can also be caused by misconfiguration";
                            }

                            leaf out-of-accounting-transaction-resources {
                                type yang:counter64;
                                description "Out of transaction resources used to transmit accounting requests, can also be caused by misconfiguration";
                            }

                            leaf out-of-accounting-queue-resources {
                                type yang:counter64;
                                description "Out of queue resources used to transmit accounting requests";
                            }

                            leaf out-of-packet-resources {
                                type yang:counter64;
                                description "Out of packet resources";
                            }

                            leaf proxy-dropped-packets {
                                type yang:counter64;
                                description "Number of packets dropped by RADIUS proxy";
                            }

                            leaf proxy-vlan-mismatch {
                                type yang:counter64;
                                description "RADIUS proxy VLAN mismatch with UE record";
                            }

                            leaf python-dropped-packets {
                                type yang:counter64;
                                description "Number of packets dropped by Python";
                            }

                        } // container radius

                        container arp {
                            description "ARP related statistics";

                            leaf tx-gre-request {
                                type yang:counter64;
                                description "Number of transmitted GRE ARP requests";
                            }

                            leaf rx-gre-reply {
                                type yang:counter64;
                                description "Number of received GRE ARP replies";
                            }

                            leaf gre-out-of-packet-resources {
                                type yang:counter64;
                                description "Out of packet resources for GRE ARP requests";
                            }

                            leaf tx-ue-arp-reply {
                                type yang:counter64;
                                description "Number of transmitted UE ARP replies";
                            }

                            leaf rx-shcv-arp-reply {
                                type yang:counter64;
                                description "Number of received SHCV ARP replies";
                            }

                        } // container arp

                        container dhcp4 {
                            description "DHCP related statistics";

                            leaf out-of-resources {
                                type yang:counter64;
                                description "Out of queue or packet resources";
                            }

                            leaf tx-offer {
                                type yang:counter64;
                                description "Number of transmitted DHCP offers";
                            }

                            leaf tx-ack {
                                type yang:counter64;
                                description "Number of transmitted DHCP acks";
                            }

                            leaf tx-nak {
                                type yang:counter64;
                                description "Number of transmitted DHCP naks";
                            }

                            leaf rx-decline {
                                type yang:counter64;
                                description "Number of received DHCP declines";
                            }

                            leaf rx-release {
                                type yang:counter64;
                                description "Number of received DHCP releases";
                            }

                            leaf l2-wholesale-option-insert-failed {
                                type yang:counter64;
                                description "DHCP option insert failed for L2 wholesale";
                            }

                        } // container dhcp4

                        container dhcp6 {
                            description "DHCPv6 related statistics";

                            leaf out-of-resources {
                                type yang:counter64;
                                description "Out of queue or packet resources";
                            }

                            leaf tx-advertise {
                                type yang:counter64;
                                description "Number of transmitted DHCPv6 advertises";
                            }

                            leaf tx-reply {
                                type yang:counter64;
                                description "Number of transmitted DHCPv6 replies";
                            }

                            leaf rx-decline {
                                type yang:counter64;
                                description "Number of received DHCPv6 declines";
                            }

                            leaf rx-release {
                                type yang:counter64;
                                description "Number of received DHCPv6 releases";
                            }

                            leaf rx-confirm {
                                type yang:counter64;
                                description "Number of received DHCPv6 confirms";
                            }

                            leaf rx-info-request {
                                type yang:counter64;
                                description "Number of received DHCPv6 information requests";
                            }

                            leaf ipv6-unavailable {
                                type yang:counter64;
                                description "No IPv6 address available for DHCPv6";
                            }

                        } // container dhcp6

                        container icmp4 {
                            description "ICMP related statistics";

                            leaf tx-tunnel-echo-reply {
                                type yang:counter64;
                                description "Number of transmitted tunnel ICMP echo replies";
                            }

                            leaf tx-ue-echo-reply {
                                type yang:counter64;
                                description "Number of transmitted UE ICMP echo replies";
                            }

                        } // container icmp4

                        container icmp6 {
                            description "ICMPv6 related statistics";

                            leaf tx-gre-neighbor-solicitation {
                                type yang:counter64;
                                description "Number of transmitted GRE ICMPv6 neighbor solicitations";
                            }

                            leaf rx-gre-neighbor-advertisement {
                                type yang:counter64;
                                description "Number of received GRE ICMPv6 neighbor advertisements";
                            }

                            leaf gre-out-of-packet-resources {
                                type yang:counter64;
                                description "Out of packet resources GRE ICMPv6 neighbor solicitations";
                            }

                            leaf tx-tunnel-echo-reply {
                                type yang:counter64;
                                description "Number of transmitted tunnel ICMPv6 echo replies";
                            }

                            leaf tx-ue-echo-reply {
                                type yang:counter64;
                                description "Number of transmitted UE ICMPv6 echo replies";
                            }

                            leaf out-of-resources {
                                type yang:counter64;
                                description "Out of queue or packet resources";
                            }

                            leaf tx-router-advertisement {
                                type yang:counter64;
                                description "Number of transmitted ICMPv6 router advertisements";
                            }

                            leaf tx-neighbor-solicitation {
                                type yang:counter64;
                                description "Number of transmitted UE ICMPv6 neighbor solicitations";
                            }

                            leaf tx-ue-neighbor-advertisement {
                                type yang:counter64;
                                description "Number of transmitted UE ICMPv6 neighbor advertisements";
                            }

                            leaf rx-shcv-neighbor-advertisement {
                                type yang:counter64;
                                description "Number of received SHCV ICMPv6 neighbor advertisement";
                            }

                            leaf prefix-unavailable {
                                type yang:counter64;
                                description "No IPv6 prefix available for SLAAC";
                            }

                        } // container icmp6

                        container resources {
                            description "WLAN-GW resource counters";

                            leaf peak-values-last-reset {
                                type yang:date-and-time;
                                description "Moment when the peak values were last reset";
                            }

                            container destinations {
                                description
                                    "WLAN-GW destinations, or group interfaces. This
                                     resource is shared with 'radius-proxy-servers'";

                                leaf max {
                                    type yang:counter64;
                                    description "Maximum possible value of this resource";
                                }

                                leaf value {
                                    type yang:counter64;
                                    description "Actual value of this resource";
                                }

                                leaf peak {
                                    type yang:counter64;
                                    description "Peak value of this resource";
                                }

                                leaf peak-timestamp {
                                    type types-sros:date-time;
                                    description "The time the system reached the peak value of this resource";
                                }

                            } // container destinations

                            container vlan-ranges {
                                description "Number of VLAN ranges";

                                leaf max {
                                    type yang:counter64;
                                    description "Maximum possible value of this resource";
                                }

                                leaf value {
                                    type yang:counter64;
                                    description "Actual value of this resource";
                                }

                                leaf peak {
                                    type yang:counter64;
                                    description "Peak value of this resource";
                                }

                                leaf peak-timestamp {
                                    type types-sros:date-time;
                                    description "The time the system reached the peak value of this resource";
                                }

                            } // container vlan-ranges

                            container ues {
                                description "Number of UEs";

                                leaf max {
                                    type yang:counter64;
                                    description "Maximum possible value of this resource";
                                }

                                leaf value {
                                    type yang:counter64;
                                    description "Actual value of this resource";
                                }

                                leaf peak {
                                    type yang:counter64;
                                    description "Peak value of this resource";
                                }

                                leaf peak-timestamp {
                                    type types-sros:date-time;
                                    description "The time the system reached the peak value of this resource";
                                }

                            } // container ues

                            container http-redirect-policies {
                                description "Number of HTTP redirect policies";

                                leaf max {
                                    type yang:counter64;
                                    description "Maximum possible value of this resource";
                                }

                                leaf value {
                                    type yang:counter64;
                                    description "Actual value of this resource";
                                }

                                leaf peak {
                                    type yang:counter64;
                                    description "Peak value of this resource";
                                }

                                leaf peak-timestamp {
                                    type types-sros:date-time;
                                    description "The time the system reached the peak value of this resource";
                                }

                            } // container http-redirect-policies

                            container filters {
                                description "Number of ISA filters";

                                leaf max {
                                    type yang:counter64;
                                    description "Maximum possible value of this resource";
                                }

                                leaf value {
                                    type yang:counter64;
                                    description "Actual value of this resource";
                                }

                                leaf peak {
                                    type yang:counter64;
                                    description "Peak value of this resource";
                                }

                                leaf peak-timestamp {
                                    type types-sros:date-time;
                                    description "The time the system reached the peak value of this resource";
                                }

                            } // container filters

                            container policers {
                                description "Number of ISA policers";

                                leaf max {
                                    type yang:counter64;
                                    description "Maximum possible value of this resource";
                                }

                                leaf value {
                                    type yang:counter64;
                                    description "Actual value of this resource";
                                }

                                leaf peak {
                                    type yang:counter64;
                                    description "Peak value of this resource";
                                }

                                leaf peak-timestamp {
                                    type types-sros:date-time;
                                    description "The time the system reached the peak value of this resource";
                                }

                            } // container policers

                            container mirrors {
                                description "Number of mirror destinations";

                                leaf max {
                                    type yang:counter64;
                                    description "Maximum possible value of this resource";
                                }

                                leaf value {
                                    type yang:counter64;
                                    description "Actual value of this resource";
                                }

                                leaf peak {
                                    type yang:counter64;
                                    description "Peak value of this resource";
                                }

                                leaf peak-timestamp {
                                    type types-sros:date-time;
                                    description "The time the system reached the peak value of this resource";
                                }

                            } // container mirrors

                            container slaac-subnets {
                                description "Number of SLAAC subnets for local address assignment";

                                leaf max {
                                    type yang:counter64;
                                    description "Maximum possible value of this resource";
                                }

                                leaf value {
                                    type yang:counter64;
                                    description "Actual value of this resource";
                                }

                                leaf peak {
                                    type yang:counter64;
                                    description "Peak value of this resource";
                                }

                                leaf peak-timestamp {
                                    type types-sros:date-time;
                                    description "The time the system reached the peak value of this resource";
                                }

                            } // container slaac-subnets

                            container dhcp6-subnets {
                                description "Number of DHCPv6 NA subnets for local address assignment";

                                leaf max {
                                    type yang:counter64;
                                    description "Maximum possible value of this resource";
                                }

                                leaf value {
                                    type yang:counter64;
                                    description "Actual value of this resource";
                                }

                                leaf peak {
                                    type yang:counter64;
                                    description "Peak value of this resource";
                                }

                                leaf peak-timestamp {
                                    type types-sros:date-time;
                                    description "The time the system reached the peak value of this resource";
                                }

                            } // container dhcp6-subnets

                            container dhcp-subnets {
                                description "Number of IPv4 subnets for local address assignment";

                                leaf max {
                                    type yang:counter64;
                                    description "Maximum possible value of this resource";
                                }

                                leaf value {
                                    type yang:counter64;
                                    description "Actual value of this resource";
                                }

                                leaf peak {
                                    type yang:counter64;
                                    description "Peak value of this resource";
                                }

                                leaf peak-timestamp {
                                    type types-sros:date-time;
                                    description "The time the system reached the peak value of this resource";
                                }

                            } // container dhcp-subnets

                            container xconnect-router-instances {
                                description "Number of router instances available to terminate cross-connect tunnels";

                                leaf max {
                                    type yang:counter64;
                                    description "Maximum possible value of this resource";
                                }

                                leaf value {
                                    type yang:counter64;
                                    description "Actual value of this resource";
                                }

                                leaf peak {
                                    type yang:counter64;
                                    description "Peak value of this resource";
                                }

                                leaf peak-timestamp {
                                    type types-sros:date-time;
                                    description "The time the system reached the peak value of this resource";
                                }

                            } // container xconnect-router-instances

                            container bridge-domains {
                                description "Number of vRGW bridged domains (BDs)";

                                leaf max {
                                    type yang:counter64;
                                    description "Maximum possible value of this resource";
                                }

                                leaf value {
                                    type yang:counter64;
                                    description "Actual value of this resource";
                                }

                                leaf peak {
                                    type yang:counter64;
                                    description "Peak value of this resource";
                                }

                                leaf peak-timestamp {
                                    type types-sros:date-time;
                                    description "The time the system reached the peak value of this resource";
                                }

                            } // container bridge-domains

                            container virtual-network-identifier {
                                description "Number of VNIs";

                                leaf max {
                                    type yang:counter64;
                                    description "Maximum possible value of this resource";
                                }

                                leaf value {
                                    type yang:counter64;
                                    description "Actual value of this resource";
                                }

                                leaf peak {
                                    type yang:counter64;
                                    description "Peak value of this resource";
                                }

                                leaf peak-timestamp {
                                    type types-sros:date-time;
                                    description "The time the system reached the peak value of this resource";
                                }

                            } // container virtual-network-identifier

                            container bridge-domain-filters {
                                description "Number of BD filters";

                                leaf max {
                                    type yang:counter64;
                                    description "Maximum possible value of this resource";
                                }

                                leaf value {
                                    type yang:counter64;
                                    description "Actual value of this resource";
                                }

                                leaf peak {
                                    type yang:counter64;
                                    description "Peak value of this resource";
                                }

                                leaf peak-timestamp {
                                    type types-sros:date-time;
                                    description "The time the system reached the peak value of this resource";
                                }

                            } // container bridge-domain-filters

                            container radius-proxy-servers {
                                description
                                    "Number of RADIUS Proxy Servers. This resource is
                                     shared with 'destinations'";

                                leaf max {
                                    type yang:counter64;
                                    description "Maximum possible value of this resource";
                                }

                                leaf value {
                                    type yang:counter64;
                                    description "Actual value of this resource";
                                }

                                leaf peak {
                                    type yang:counter64;
                                    description "Peak value of this resource";
                                }

                                leaf peak-timestamp {
                                    type types-sros:date-time;
                                    description "The time the system reached the peak value of this resource";
                                }

                            } // container radius-proxy-servers

                            container radius-proxy-contexts {
                                description "Number of in-progress radius proxy transactions";

                                leaf max {
                                    type yang:counter64;
                                    description "Maximum possible value of this resource";
                                }

                                leaf value {
                                    type yang:counter64;
                                    description "Actual value of this resource";
                                }

                                leaf peak {
                                    type yang:counter64;
                                    description "Peak value of this resource";
                                }

                                leaf peak-timestamp {
                                    type types-sros:date-time;
                                    description "The time the system reached the peak value of this resource";
                                }

                            } // container radius-proxy-contexts

                            container application-profiles {
                                description "Number of application profiles used for application assurance";

                                leaf max {
                                    type yang:counter64;
                                    description "Maximum possible value of this resource";
                                }

                                leaf value {
                                    type yang:counter64;
                                    description "Actual value of this resource";
                                }

                                leaf peak {
                                    type yang:counter64;
                                    description "Peak value of this resource";
                                }

                                leaf peak-timestamp {
                                    type types-sros:date-time;
                                    description "The time the system reached the peak value of this resource";
                                }

                            } // container application-profiles

                            container aa-ues {
                                description "Number of UEs with application assurance enabled";

                                leaf max {
                                    type yang:counter64;
                                    description "Maximum possible value of this resource";
                                }

                                leaf value {
                                    type yang:counter64;
                                    description "Actual value of this resource";
                                }

                                leaf peak {
                                    type yang:counter64;
                                    description "Peak value of this resource";
                                }

                                leaf peak-timestamp {
                                    type types-sros:date-time;
                                    description "The time the system reached the peak value of this resource";
                                }

                            } // container aa-ues

                            container fragment-lists {
                                description "Number of incomplete packets with unreceived fragments";

                                leaf max {
                                    type yang:counter64;
                                    description "Maximum possible value of this resource";
                                }

                                leaf value {
                                    type yang:counter64;
                                    description "Actual value of this resource";
                                }

                                leaf peak {
                                    type yang:counter64;
                                    description "Peak value of this resource";
                                }

                                leaf peak-timestamp {
                                    type types-sros:date-time;
                                    description "The time the system reached the peak value of this resource";
                                }

                            } // container fragment-lists

                            container fragment-holes {
                                description "Number of unreceived segments in incomplete packets";

                                leaf max {
                                    type yang:counter64;
                                    description "Maximum possible value of this resource";
                                }

                                leaf value {
                                    type yang:counter64;
                                    description "Actual value of this resource";
                                }

                                leaf peak {
                                    type yang:counter64;
                                    description "Peak value of this resource";
                                }

                                leaf peak-timestamp {
                                    type types-sros:date-time;
                                    description "The time the system reached the peak value of this resource";
                                }

                            } // container fragment-holes

                            container fragment-buffers {
                                description "Number of received fragments of incomplete packets";

                                leaf max {
                                    type yang:counter64;
                                    description "Maximum possible value of this resource";
                                }

                                leaf value {
                                    type yang:counter64;
                                    description "Actual value of this resource";
                                }

                                leaf peak {
                                    type yang:counter64;
                                    description "Peak value of this resource";
                                }

                                leaf peak-timestamp {
                                    type types-sros:date-time;
                                    description "The time the system reached the peak value of this resource";
                                }

                            } // container fragment-buffers

                        } // container resources

                    } // container statistics

                } // list member

            } // list wlan-gw-group

            list lns-group {
                key "id";
                description "Enter the lns-group list instance";

                leaf id {
                    type types-l2tp:lns-group-id;
                    description "Tunnel group ID";
                }

                leaf oper-state {
                    type types-sros:oper-state;
                    description "Operational state.";
                }

                list mda {
                    key "mda-id";
                    description "Enter the mda list instance";

                    leaf mda-id {
                        type types-isa:slot-mda;
                        description "MDA ID for the ISA LNS group";
                    }

                    leaf oper-state {
                        type types-l2tp:isa-mda-oper-state;
                        description "The operation state of the ISA MDA";
                    }

                    leaf sessions {
                        type yang:gauge32;
                        description "The number of sessions handled by the ISA MDA";
                    }

                    list statistics {
                        key "counter";
                        description "The statistics of an ISA LNS group MDA";

                        leaf counter {
                            type uint32 {
                                range "0..70";
                            }
                            description "The counter";
                        }

                        leaf description {
                            type string {
                                length "0..70";
                            }
                            description "The human-readable identifier of the statistic.";
                        }

                        leaf value {
                            type yang:counter64;
                            description "The counter value";
                        }

                    } // list statistics

                } // list mda

            } // list lns-group

            uses state-isa-video-group;
        } // container isa

    } // grouping state-isa

}
