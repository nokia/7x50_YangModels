module alu-conf-router-r13 {
  yang-version "1";

  namespace "urn:alcatel-lucent.com:sros:ns:yang:conf-router-r13";

  prefix "conf-router-r13";

  import alu-conf-router-bgp-r13 {
    prefix "conf-router-bgp-r13";
  }
  import alu-conf-router-bier-r13 {
    prefix "conf-router-bier-r13";
  }
  import alu-conf-router-dhcp6-r13 {
    prefix "conf-router-dhcp6-r13";
  }
  import alu-conf-router-dhcps-r13 {
    prefix "conf-router-dhcps-r13";
  }
  import alu-conf-router-fspec-r13 {
    prefix "conf-router-fspec-r13";
  }
  import alu-conf-router-gmpls-r13 {
    prefix "conf-router-gmpls-r13";
  }
  import alu-conf-router-if-r13 {
    prefix "conf-router-if-r13";
  }
  import alu-conf-router-igmp-r13 {
    prefix "conf-router-igmp-r13";
  }
  import alu-conf-router-isis-r13 {
    prefix "conf-router-isis-r13";
  }
  import alu-conf-router-l2tp-r13 {
    prefix "conf-router-l2tp-r13";
  }
  import alu-conf-router-ldp-r13 {
    prefix "conf-router-ldp-r13";
  }
  import alu-conf-router-lmp-r13 {
    prefix "conf-router-lmp-r13";
  }
  import alu-conf-router-mccacpl-r13 {
    prefix "conf-router-mccacpl-r13";
  }
  import alu-conf-router-mld-r13 {
    prefix "conf-router-mld-r13";
  }
  import alu-conf-router-mpls-r13 {
    prefix "conf-router-mpls-r13";
  }
  import alu-conf-router-nat-r13 {
    prefix "conf-router-nat-r13";
  }
  import alu-conf-router-nhroute-r13 {
    prefix "conf-router-nhroute-r13";
  }
  import alu-conf-router-ogvalid-r13 {
    prefix "conf-router-ogvalid-r13";
  }
  import alu-conf-router-ospf-r13 {
    prefix "conf-router-ospf-r13";
  }
  import alu-conf-router-ospf3-r13 {
    prefix "conf-router-ospf3-r13";
  }
  import alu-conf-router-pcep-r13 {
    prefix "conf-router-pcep-r13";
  }
  import alu-conf-router-pim-r13 {
    prefix "conf-router-pim-r13";
  }
  import alu-conf-router-policy-r13 {
    prefix "conf-router-policy-r13";
  }
  import alu-conf-router-radprox-r13 {
    prefix "conf-router-radprox-r13";
  }
  import alu-conf-router-radvert-r13 {
    prefix "conf-router-radvert-r13";
  }
  import alu-conf-router-rip-r13 {
    prefix "conf-router-rip-r13";
  }
  import alu-conf-router-rsvp-r13 {
    prefix "conf-router-rsvp-r13";
  }
  import alu-conf-router-sc-r13 {
    prefix "conf-router-sc-r13";
  }
  import alu-conf-router-treesid-r13 {
    prefix "conf-router-treesid-r13";
  }
  import alu-conf-router-wlan-r13 {
    prefix "conf-router-wlan-r13";
  }
  import alu-conf-router-wpp-r13 {
    prefix "conf-router-wpp-r13";
  }
  import alu-types {
    prefix "alu";
  }
  import ietf-inet-types {
    prefix "inet";
  }

  alu:alu-major-release "rel20";

  organization "Alcatel-Lucent";

  contact
      "Alcatel-Lucent SR OS Support 
       Web: <http://www.alcatel-lucent.com>";

  description
      "Alcatel-Lucent YANG Data model to configure routing protocols in the base 
       routing instance on SR OS based routers. 
       
       Copyright 2014-2015 Alcatel-Lucent, 2016 Nokia. All rights reserved. 
       Reproduction of this document is authorized on the condition that the 
       foregoing copyright notice is included. 
       
       This alu-conf-router-r13 YANG module embodies Alcatel-Lucent's proprietary 
       intellectual property. Alcatel-Lucent retains all title and ownership in the 
       Specification, including any revisions. 
       
       Alcatel-Lucent grants all interested parties a non-exclusive license to use 
       and distribute an unmodified copy of this Specification in connection with 
       management of Alcatel-Lucent products, and without fee, provided this 
       copyright notice and license appear on all copies. 
       
       This Specification is supplied `as is', and Alcatel-Lucent makes no warranty, 
       either express or implied, as to the use, operation, condition, or performance 
       of the Specification.";

  revision  "2020-03-02";

  grouping alu-conf-router-r13 {
    container router {
      description
          "Configure routing protocols in the base routing instance";
      leaf router-instance {
        type string {
          length "1..32";
        }
        default "Base";
        description
            "Attribute router-instance for router";
      } //router-instance

      list aggregate {
        key "ip-prefix-ip-prefix-length";
        description
            "Create/delete aggregate routes";
        leaf ip-prefix-ip-prefix-length {
          type string;
          description
              "Attribute ip-prefix/ip-prefix-length for aggregate";
        } //ip-prefix-ip-prefix-length

        leaf summary-only {
          type boolean;
        } //summary-only

        leaf as-set {
          type boolean;
        } //as-set

        leaf aggregator {
          type string;
          description
              "as-number - [1..4294967295] 
               ip-address - a.b.c.d";
        } //aggregator

        leaf black-hole {
          type boolean;
        } //black-hole

        leaf-list community {
          type string;
          max-elements 12;
          description
              "Attribute comm-id for aggregate";
        } //community

        leaf indirect {
          type string;
        } //indirect

        leaf generate-icmp {
          type boolean;
        } //generate-icmp

        leaf description {
          type string {
            length "1..80";
          }
        } //description

        leaf local-preference {
          type uint32;
        } //local-preference

        leaf discard-component-communities {
          type boolean;
        } //discard-component-communities

      } //list aggregate

      leaf allow-icmp-redirect {
        type boolean;
        description
            "Allow or drop ICMP Redirects received on the management interface";
      }

      leaf allow-icmp6-redirect {
        type boolean;
        description
            "Allow or drop IPv6 ICMP Redirects received on the management interface";
      }

      container autonomous-system {
        description
            "Configure the Autonomous Systems on the router";
        leaf autonomous-system {
          type uint32 {
            range "1..4294967295";
          }
        } //autonomous-system

      } //container autonomous-system

      leaf class-forwarding {
        type boolean;
        description
            "Enable/Disable class forwarding";
      }

      container confederation {
        description
            "Create/delete confederation autonomous systems within an AS";
        leaf confed-as-num {
          type uint32 {
            range "1..4294967295";
          }
        } //confed-as-num

        leaf-list members {
          type uint32 {
            range "1..4294967295";
          }
          max-elements 15;
        } //members

      } //container confederation

      container description {
        description
            "Configure a description for this router instance";
        leaf description-string {
          type string {
            length "1..80";
          }
        } //description-string

      } //container description

      leaf disable-selective-fib {
        type boolean;
        description
            "Enable/disable selective FIB";
      }

      container ecmp {
        description
            "Enable/disable ECMP and configure max number of routes for path sharing";
        leaf max-ecmp-routes {
          type string;
          description
              "Attribute max-ecmp-routes for ecmp";
        } //max-ecmp-routes

      } //container ecmp

      leaf entropy-label {
        type boolean;
        description
            "Enable/disable use of entropy-label";
      }

      container fib-priority {
        description
            "Specify the FIB Priority";
        leaf high-standard {
          type enumeration {
            enum high;
            enum standard;
          }
        } //high-standard

      } //container fib-priority

      leaf fib-telemetry {
        type boolean;
        description
            "Enable/disable fib-telemetry collection";
      }

      leaf icmp-tunneling {
        type boolean;
        description
            "Enables/disables ICMP tunneling feature globally on the system";
      }

      leaf ip-fast-reroute {
        type boolean;
        description
            "Enable/Disable IP Fast Reroute capability";
      }

      container ipv6-te-router-id {
        description
            "Configure the IPv6 Traffic Engineering router ID";
        leaf interface {
          type string {
            length "1..32";
          }
        } //interface

      } //container ipv6-te-router-id

      container ldp-shortcut {
        description
            "Allow IGP route resolution using LDP LSPs across network interfaces 
             participating in IS-IS and OSPF";
        leaf ipv4 {
          type boolean;
        } //ipv4

        leaf ipv6 {
          type boolean;
        } //ipv6

      } //container ldp-shortcut

      container leak-export {
        description
            "Export route policies used to determine which routes are exported";
        leaf-list policy-name {
          type string;
          max-elements 5;
          description
              "Attribute policy-name for leak-export";
        } //policy-name

        leaf plcy-or-long-expr {
          type string {
            length "1..255";
          }
          description
              "Attribute plcy-or-long-expr for leak-export";
        } //plcy-or-long-expr

        leaf-list plcy-or-expr {
          type string {
            length "1..64";
          }
          max-elements 4;
          description
              "Attribute plcy-or-expr for leak-export";
        } //plcy-or-expr

      } //container leak-export

      list leak-export-limit {
        key "leak-export-limit-id";
        description
            "Configure leak-export-limit";
        leaf leak-export-limit-id {
          type uint32 {
            range "1..10000";
          }
        } //leak-export-limit-id

      } //list leak-export-limit

      container mc-maximum-routes {
        description
            "Configure the max multicast routes";
        leaf number {
          type uint32 {
            range "1..2147483647";
          }
        } //number

        leaf log-only {
          type boolean;
          description
              "keyword - specifies to not disable learning of new routes if maximum is 
               reached only log the event";
        } //log-only

        leaf threshold {
          type int32 {
            range "0..100";
          }
        } //threshold

      } //container mc-maximum-routes

      container mss-adjust-group {
        description
            "Configure the ISA-BB group for TCP Maximum Segment Size adjustment";
        leaf bb-group-id {
          type uint32 {
            range "1..4";
          }
        } //bb-group-id

        leaf segment-size {
          type uint32 {
            range "160..10240";
          }
        } //segment-size

      } //container mss-adjust-group

      container multicast-info-policy {
        description
            "Configure multicast information policy";
        leaf policy-name {
          type string {
            length "1..32";
          }
          description
              "[Max 32 chars]";
        } //policy-name

      } //container multicast-info-policy

      leaf policy-reference-checks {
        type boolean;
        description
            "Enable/disable route policies reference checks";
      }

      container reassembly-group {
        description
            "Configure the ISA-BB group for IP datagram fragment reassembly";
        leaf bb-group-id {
          type uint32 {
            range "1..4";
          }
        } //bb-group-id

        leaf to-base-network {
          type boolean;
          description
              "keyword - send reassembled traffic to network interface on base router";
        } //to-base-network

      } //container reassembly-group

      container router-id {
        description
            "Configure the router-id for the virtual router";
        leaf ip-address {
          type inet:ip-address;
        } //ip-address

      } //container router-id

      list service-prefix {
        key "ip-prefix-ip-prefix-length netmask";
        description
            "Reserve IP address ranges for services";
        leaf ip-prefix-ip-prefix-length {
          type string;
          description
              "Attribute ip-prefix/ip-prefix-length for service-prefix";
        } //ip-prefix-ip-prefix-length

        leaf netmask {
          type string;
          description
              "a.b.c.d (network bits all 1 and host bits all 0)";
        } //netmask

        leaf exclusive {
          type boolean;
        } //exclusive

      } //list service-prefix

      leaf shutdown {
        type boolean;
        description
            "Administratively disable or enable this router instance";
      }

      container single-sfm-overload {
        description
            "Configure IGP single-sfm overload behavior";
        leaf holdoff-time {
          type uint32 {
            range "1..600";
          }
          description
              "[1..600] seconds";
        } //holdoff-time

      } //container single-sfm-overload

      list static-route {
        key "ip-prefix-prefix-length preference metric tag mcast-family community description";
        status "obsolete";
        description
            "Creates/deletes static route entries";
        leaf ip-prefix-prefix-length {
          type string;
          description
              "Attribute ip-prefix/prefix-length for static-route";
        } //ip-prefix-prefix-length

        leaf netmask {
          type string;
          description
              "a.b.c.d (network bits all 1 and host bits all 0)";
        } //netmask

        leaf next-hop {
          type string;
          description
              "Attribute ip-int-name|ip-address|ipv6-address for static-route";
        } //next-hop

        leaf indirect {
          type string;
          description
              "Attribute ip-address for static-route";
        } //indirect

        leaf black-hole {
          type boolean;
        } //black-hole

        leaf preference {
          type uint16 {
            range "1..255";
          }
        } //preference

        leaf metric {
          type uint32 {
            range "0..65535";
          }
        } //metric

        leaf enable-disable {
          type enumeration {
            enum enable;
            enum disable;
          }
          description
              "keywords - specify state of static-route";
        } //enable-disable

        leaf tag {
          type uint32 {
            range "1..4294967295";
          }
        } //tag

        leaf bfd-enable {
          type boolean;
          description
              "keyword - enables BFD sessions on this static route";
        } //bfd-enable

        leaf mcast-family {
          type enumeration {
            enum mcast-ipv4;
            enum mcast-ipv6;
            enum generate-icmp;
          }
          description
              "Attribute mcast-family for static-route";
        } //mcast-family

        leaf cpe-check {
          type string;
          description
              "Attribute cpe-ip-address for static-route";
        } //cpe-check

        leaf interval {
          type uint32 {
            range "1..255";
          }
          default 1;
        } //interval

        leaf drop-count {
          type uint32 {
            range "1..255";
          }
          default 3;
        } //drop-count

        leaf log {
          type boolean;
        } //log

        leaf prefix-list {
          type string {
            length "1..32";
          }
        } //prefix-list

        leaf all-none {
          type enumeration {
            enum all;
            enum none;
          }
          description
              "keyword - specify prefix-list to be considered";
        } //all-none

        leaf ldp-sync {
          type boolean;
        } //ldp-sync

        leaf fc {
          type string;
          description
              "be|l2|af|l1|h2|ef|h1|nc";
        } //fc

        leaf priority {
          type enumeration {
            enum low;
            enum high;
          }
        } //priority

        leaf community {
          type string;
          description
              "[72 chars max] 
               <2 byte-asnumber:comm-val>|<well-known-comm> 
               2 byte-asnumber - [0..65535] 
               comm-val - [0..65535] 
               well-known-comm - no-export|no-export-subconfed| 
               no-advertise";
        } //community

        leaf dynamic-bgp {
          type boolean;
          description
              "enables static route to dynamically derive its next hop from the best bgp 
               route";
        } //dynamic-bgp

        leaf description {
          type string {
            length "1..80";
          }
        } //description

        leaf padding-size {
          type uint32 {
            range "0..16384";
          }
        } //padding-size

        leaf validate-next-hop {
          type boolean;
        } //validate-next-hop

        leaf source-class {
          type uint32 {
            range "1..255";
          }
        } //source-class

        leaf dest-class {
          type uint32 {
            range "1..255";
          }
        } //dest-class

      } //list static-route

      container static-route-hold-down {
        description
            "Enable/Disable hold down time feature globally for the static-routes on the 
             system";
        leaf initial {
          type uint32 {
            range "1..65535";
          }
        } //initial

        leaf multiplier {
          type uint32 {
            range "1..10";
          }
        } //multiplier

        leaf max-value {
          type uint32 {
            range "1..65535";
          }
        } //max-value

      } //container static-route-hold-down

      leaf triggered-policy {
        type boolean;
        description
            "Enable/disable triggered re-evaluation of route policies";
      }

      container weighted-ecmp {
        description
            "Enable/disable weighted ecmp capability";
        leaf strict {
          type boolean;
        } //strict

      } //container weighted-ecmp

      container admin-tags {
        description
            "Configure admin-tags";
        list admin-tag {
          key "tag";
          description
              "Configure an admin-tag.";
          leaf tag {
            type string {
              length "1..32";
            }
          } //tag

        } //list admin-tag

        list route-admin-tag-policy {
          key "policy-name";
          description
              "Configure an admin-tag policy-name";
          leaf policy-name {
            type string {
              length "1..64";
            }
            description
                "Attribute policy-name for route-admin-tag-policy";
          } //policy-name

          list exclude {
            key "tag";
            description
                "Configures an admin-tag to be excluded when matching a route against an LSP";
            leaf tag {
              type string {
                length "1..32";
              }
            } //tag

          } //list exclude

          list include {
            key "tag";
            description
                "Configures an admin-tag to be included when matching a route against an LSP";
            leaf tag {
              type string {
                length "1..32";
              }
            } //tag

          } //list include

        } //list route-admin-tag-policy

      } //container admin-tags

      container bfd {
        description
            "Create/Configure or Delete BFD template";
        leaf abort {
          type boolean;
          description
              "Discard the changes that have been made to bfd template during a session";
        }

        leaf begin {
          type boolean;
          description
              "Switch to edit mode for bfd template - use commit to save or abort to discard 
               the changes made in a session";
        }

        leaf commit {
          type boolean;
          description
              "Save the changes made to bfd template during a session";
        }

        list bfd-template {
          key "bfd-template-string";
          description
              "Configure a bfd template";
          leaf bfd-template-string {
            type string {
              length "1..32";
            }
          } //bfd-template-string

          container echo-receive {
            description
                "Configure echo receive interval";
            leaf milli-seconds {
              type uint32 {
                range "100..100000";
              }
            } //milli-seconds

          } //container echo-receive

          container multiplier {
            description
                "Configure multiplier";
            leaf multiplier {
              type string;
              description
                  "Attribute multiplier for multiplier";
            } //multiplier

          } //container multiplier

          container receive-interval {
            description
                "Configure receive interval";
            leaf milli-seconds {
              type uint32 {
                range "10..100000";
              }
            } //milli-seconds

          } //container receive-interval

          container transmit-interval {
            description
                "Configure transmit interval";
            leaf milli-seconds {
              type uint32 {
                range "10..100000";
              }
            } //milli-seconds

          } //container transmit-interval

          container type {
            description
                "Configure the bfd session endpoint type";
            leaf type-id {
              type enumeration {
                enum cpm-np;
              }
            } //type-id

          } //container type

        } //list bfd-template

        container seamless-bfd {
          description
              "Configure Seamless BFD";
          list peer {
            key "ip-address-ipv6-address";
            description
                "Configure a remote node";
            leaf ip-address-ipv6-address {
              type string;
              description
                  "Attribute ip-address|ipv6-address for peer";
            } //ip-address-ipv6-address

            container discriminator {
              description
                  "Configure the discriminator of the remote node";
              leaf discriminator {
                type uint32 {
                  range "1..4294967295";
                }
                description
                    "Discriminator of remote node [1..4294967295]";
              } //discriminator

            } //container discriminator

          } //list peer

        } //container seamless-bfd

      } //container bfd

      uses "conf-router-bgp-r13:alu-conf-router-bgp-r13";
      uses "conf-router-bier-r13:alu-conf-router-bier-r13";
      uses "conf-router-dhcps-r13:alu-conf-router-dhcps-r13";
      uses "conf-router-dhcp6-r13:alu-conf-router-dhcp6-r13";
      container dns {
        description
            "Configure DNS";
        container redirect-vprn {
          description
              "Configure DNS resolution to be resolve via VPRN";
          list service {
            key "service-id";
            description
                "Configure VPRN redirection";
            leaf service-id {
              type string;
              description
                  "Attribute service-id for service";
            } //service-id

            leaf preference {
              type uint32 {
                range "0..255";
              }
              description
                  "[0..255]";
            } //preference

          } //list service

        } //container redirect-vprn

      } //container dns

      container firewall {
        description
            "Configure the IPv6 firewall";
        list domain {
          key "domain-name";
          description
              "Configure firewall domains";
          leaf domain-name {
            type string;
          } //domain-name

          leaf nat-group {
            type uint32 {
              range "1..4";
            }
          } //nat-group

          container dhcp6-server {
            description
                "Configure the DHCPv6 server";
            leaf router {
              type string {
                length "1..32";
              }
              description
                  "Attribute router-name for dhcp6-server";
            } //router

            leaf name {
              type string;
            } //name

          } //container dhcp6-server

          leaf shutdown {
            type boolean;
            description
                "Administratively disable the domain";
          }

          list prefix {
            key "prefix-prefix-length";
            description
                "Configure IPv6 prefixes";
            leaf prefix-prefix-length {
              type string;
              description
                  "Attribute prefix/prefix-length for prefix";
            } //prefix-prefix-length

            container description {
              description
                  "Configure a description";
              leaf description-string {
                type string {
                  length "1..80";
                }
              } //description-string

            } //container description

          } //list prefix

        } //list domain

      } //container firewall

      container flexible-algorithm-definitions {
        description
            "Configure Flexible Algorithm definitions";
        list flex-algo {
          key "flex-algo-id";
          description
              "Configure Flexible Algorithm";
          leaf flex-algo-id {
            type uint32 {
              range "128..255";
            }
          } //flex-algo-id

          container description {
            description
                "Configure the description of this Flex Algo";
            leaf description-string {
              type string {
                length "1..80";
              }
            } //description-string

          } //container description

          container metric-type {
            description
                "Configure the metric type to be used in Flex Algo calculation";
            leaf metric-type-id {
              type enumeration {
                enum igp;
                enum te-metric;
                enum delay;
              }
              default "igp";
            } //metric-type-id

          } //container metric-type

          container priority {
            description
                "Configure the priority of this Flex Algo";
            leaf priority-id {
              type uint32 {
                range "0..255";
              }
              default 100;
            } //priority-id

          } //container priority

          leaf shutdown {
            type boolean;
            description
                "Administratively enable/disable the Flex Algo";
          }

          container exclude-groups {
            description
                "Configure the exclude groups";
            list admin-group {
              key "admin-group";
              description
                  "Configure an admin group to exclude";
              leaf admin-group {
                type string {
                  length "1..32";
                }
              } //admin-group

            } //list admin-group

          } //container exclude-groups

          container include-all-groups {
            description
                "Configure the include-all groups";
            list admin-group {
              key "admin-group";
              description
                  "Configure an admin group for include-all rule";
              leaf admin-group {
                type string {
                  length "1..32";
                }
              } //admin-group

            } //list admin-group

          } //container include-all-groups

          container include-any-groups {
            description
                "Configure the include-any groups";
            list admin-group {
              key "admin-group";
              description
                  "Configure an admin group for include-any rule";
              leaf admin-group {
                type string {
                  length "1..32";
                }
              } //admin-group

            } //list admin-group

          } //container include-any-groups

        } //list flex-algo

      } //container flexible-algorithm-definitions

      uses "conf-router-fspec-r13:alu-conf-router-fspec-r13";
      uses "conf-router-gmpls-r13:alu-conf-router-gmpls-r13";
      container gtm {
        description
            "Configure GTM";
        leaf mvpn {
          type boolean;
          description
              "Configure multicast VPN";
        }

        container provider-tunnel {
          description
              "Configure provider tunnel for the multicast VPN";
          container inclusive {
            description
                "Configure inclusive provider tunnels for the multicast VPN";
            container rsvp {
              presence
                  "Enable/Disable the Context for specifiying RSVP P2MP LSP for the provider 
                   tunnel";
              container lsp-template {
                description
                    "Specify the Lsp Template";
                leaf lsp-template {
                  type string {
                    length "1..32";
                  }
                } //lsp-template

              } //container lsp-template

              leaf shutdown {
                type boolean;
                description
                    "Administratively enable/disable the use of RSVP";
              }

            } //container rsvp

          } //container inclusive

          container selective {
            description
                "Configure selective provider tunnels for the multicast VPN";
            container data-delay-interval {
              description
                  "Configure the data delay interval";
              leaf value {
                type uint32 {
                  range "3..180";
                }
              } //value

            } //container data-delay-interval

            container data-threshold {
              description
                  "Configures threshold for a group prefix";
              leaf c-grp-ip-addr-mask {
                type string;
                description
                    "multicast group address a.b.c.d 
                     mask [4..32]";
              } //c-grp-ip-addr-mask

              leaf netmask {
                type string;
                description
                    "a.b.c.d (network bits all 1 and host bits all 0)";
              } //netmask

              leaf s-pmsi-threshold {
                type uint32 {
                  range "0..4294967294";
                }
                description
                    "[1..4294967294](threshold in kbps)";
              } //s-pmsi-threshold

              leaf c-grp-ipv6-addr-prefix-length {
                type string;
                description
                    "multicast ipv6-address x:x:x:x:x:x:x:x (eight 16-bit pieces) 
                     x:x:x:x:x:x:d.d.d.d 
                     x [0..FFFF]H 
                     d [0..255]D 
                     prefix-length [1..128]";
              } //c-grp-ipv6-addr-prefix-length

              leaf pe-threshold-add {
                type uint32 {
                  range "1..65535";
                }
              } //pe-threshold-add

              leaf pe-threshold-delete {
                type uint32 {
                  range "2..65535";
                }
              } //pe-threshold-delete

            } //container data-threshold

            container maximum-p2mp-spmsi {
              description
                  "Specify the maximum number of p2mp s-pmsi tunnels for the mvpn";
              leaf range {
                type uint32 {
                  range "1..4000";
                }
                description
                    "[1..4000]";
              } //range

            } //container maximum-p2mp-spmsi

            container rsvp {
              presence
                  "Enable/Disable the Context for specifiying RSVP P2MP LSP for the provider 
                   tunnel";
              container lsp-template {
                description
                    "Specify the Lsp Template";
                leaf lsp-template {
                  type string {
                    length "1..32";
                  }
                } //lsp-template

              } //container lsp-template

              leaf shutdown {
                type boolean;
                description
                    "Administratively enable/disable the use of P2MP Auto LSP";
              }

            } //container rsvp

          } //container selective

        } //container provider-tunnel

      } //container gtm

      container gtp {
        description
            "Configure GTP";
        container s11 {
          description
              "Configure the S11 interface for GTP";
          list interface {
            key "interface-name";
            description
                "Configure the S11 interface name";
            leaf interface-name {
              type string {
                length "1..32";
              }
              description
                  "[32 chars max] (must start with a letter)";
            } //interface-name

            container apn-policy {
              description
                  "Configure the APN policy for the S11 interface";
              leaf apn-policy-name {
                type string {
                  length "1..32";
                }
              } //apn-policy-name

            } //container apn-policy

          } //list interface

          container peer-profile-map {
            description
                "Configure a peer profile map";
            list address {
              key "ip-prefix-ip-prefix-length";
              description
                  "Configure a peer profile map address";
              leaf ip-prefix-ip-prefix-length {
                type string;
                description
                    "Attribute ip-prefix/ip-prefix-length for address";
              } //ip-prefix-ip-prefix-length

              leaf peer-profile {
                type string;
              } //peer-profile

            } //list address

          } //container peer-profile-map

        } //container s11

        container uplink {
          presence
              "Configure the uplink for GTP";
          container apn {
            description
                "Configure the Network Identifier part of the APN";
            leaf apn {
              type string {
                length "1..80";
              }
            } //apn

          } //container apn

          container pdn-type {
            description
                "Configure the default 3GPP-PDN type";
            leaf pdn-type-id {
              type enumeration {
                enum ipv4;
                enum ipv6;
                enum ipv4v6;
              }
            } //pdn-type-id

          } //container pdn-type

          container peer-profile-map {
            description
                "Configure a peer profile map";
            list address {
              key "ip-prefix-ip-prefix-length";
              description
                  "Configure a peer profile map address";
              leaf ip-prefix-ip-prefix-length {
                type string;
                description
                    "Attribute ip-prefix/ip-prefix-length for address";
              } //ip-prefix-ip-prefix-length

              leaf peer-profile {
                type string;
              } //peer-profile

            } //list address

          } //container peer-profile-map

        } //container uplink

      } //container gtp

      container if-attribute {
        description
            "Configure interface attributes";
        list admin-group {
          key "group-name";
          description
              "Create/delete an administrative group";
          leaf group-name {
            type string {
              length "1..32";
            }
          } //group-name

          leaf value {
            type uint32 {
              range "0..31";
            }
          } //value

        } //list admin-group

        list srlg-group {
          key "group-name";
          description
              "Create/delete a SRLG group";
          leaf group-name {
            type string {
              length "1..32";
            }
          } //group-name

          leaf value {
            type uint32;
          } //value

          leaf penalty-weight {
            type uint32 {
              range "0..65535";
            }
          } //penalty-weight

        } //list srlg-group

      } //container if-attribute

      uses "conf-router-igmp-r13:alu-conf-router-igmp-r13";
      uses "conf-router-if-r13:alu-conf-router-if-r13";
      container ipsec {
        description
            "Configure IPsec Policies";
        list security-policy {
          key "security-policy-id";
          description
              "Configure IPsec security policy";
          leaf security-policy-id {
            type uint32 {
              range "1..32768";
            }
          } //security-policy-id

          list entry {
            key "entry-id";
            description
                "Configure IPsec security policy params";
            leaf entry-id {
              type uint32 {
                range "1..16";
              }
            } //entry-id

            container local-ip {
              description
                  "Configure local Ip prefix/mask for this policy param entry";
              leaf unicast-ip-prefix-mask {
                type inet:ip-prefix;
              } //unicast-ip-prefix-mask

              leaf any {
                type boolean;
              } //any

            } //container local-ip

            container local-v6-ip {
              description
                  "Configure local IPv6 prefix/mask for this policy param entry";
              leaf ipv6-address--x-x-x-x-x-x-x-x---eight-16-bit-pieces {
                type string;
              } //ipv6-address--x-x-x-x-x-x-x-x---eight-16-bit-pieces

              leaf any {
                type boolean;
              } //any

            } //container local-v6-ip

            container remote-ip {
              description
                  "Configure remote Ip prefix/mask for this policy param entry";
              leaf ip-prefix-ip-prefix-length {
                type string;
              } //ip-prefix-ip-prefix-length

              leaf any {
                type boolean;
              } //any

            } //container remote-ip

            container remote-v6-ip {
              description
                  "Configure remote Ip prefix/mask for this policy param entry";
              leaf ipv6-address--x-x-x-x-x-x-x-x---eight-16-bit-pieces {
                type string;
              } //ipv6-address--x-x-x-x-x-x-x-x---eight-16-bit-pieces

              leaf any {
                type boolean;
              } //any

            } //container remote-v6-ip

          } //list entry

        } //list security-policy

      } //container ipsec

      container ipv6 {
        description
            "Configure IPv6";
        container reachable-time {
          description
              "Configure neighbor reachability detection timer";
          leaf seconds {
            type uint32 {
              range "30..3600";
            }
          } //seconds

        } //container reachable-time

        container stale-time {
          description
              "Configure the time a neighbor discovery cache entry can remain stale before 
               being removed";
          leaf seconds {
            type uint32 {
              range "60..65535";
            }
          } //seconds

        } //container stale-time

      } //container ipv6

      uses "conf-router-sc-r13:alu-conf-router-sc-r13";
      uses "conf-router-isis-r13:alu-conf-router-isis-r13";
      uses "conf-router-l2tp-r13:alu-conf-router-l2tp-r13";
      uses "conf-router-ldp-r13:alu-conf-router-ldp-r13";
      uses "conf-router-lmp-r13:alu-conf-router-lmp-r13";
      container lsp-bfd {
        description
            "LSP BFD configuration";
        container bfd-sessions {
          description
              "Enable/disable or configure the maximum number of dynamically created LSP BFD 
               session tail-ends";
          leaf max-limit {
            type uint32 {
              range "1..4294967295";
            }
            description
                "Attribute max-limit for bfd-sessions";
          } //max-limit

        } //container bfd-sessions

      } //container lsp-bfd

      uses "conf-router-mccacpl-r13:alu-conf-router-mccacpl-r13";
      list mh-primary-interface {
        key "interface-name";
        status "obsolete";
        description
            "Create/delete or configure a multihoming-primary-interface";
        leaf interface-name {
          type string {
            length "1..32";
          }
          description
              "[32 chars max] (must start with a letter)";
        } //interface-name

        container address {
          status "obsolete";
          description
              "Assigns an IP address/IP subnet address to the interface";
          leaf ip-address-mask {
            type string;
            description
                "ip-address a.b.c.d 
                 mask [1..32]";
          } //ip-address-mask

          leaf netmask {
            type string;
            description
                "a.b.c.d (network bits all 1 and host bits all 0)";
          } //netmask

        } //container address

        container description {
          status "obsolete";
          description
              "Description for the multihoming-primary-interface";
          leaf long-description-string {
            type string {
              length "1..160";
            }
          } //long-description-string

        } //container description

        leaf shutdown {
          type boolean;
          status "obsolete";
          description
              "Administratively enable/disable the multihoming-primary-interface";
        }

      } //list mh-primary-interface

      list mh-secondary-interface {
        key "interface-name";
        status "obsolete";
        description
            "Create/delete or configure a multihoming-secondary-interface";
        leaf interface-name {
          type string {
            length "1..32";
          }
          description
              "[32 chars max] (must start with a letter)";
        } //interface-name

        container address {
          status "obsolete";
          description
              "Assigns an IP address/IP subnet address to the interface";
          leaf ip-address-mask {
            type string;
            description
                "ip-address a.b.c.d 
                 mask [1..32]";
          } //ip-address-mask

          leaf netmask {
            type string;
            description
                "a.b.c.d (network bits all 1 and host bits all 0)";
          } //netmask

        } //container address

        container description {
          status "obsolete";
          description
              "Description for the multihoming-secondary-interface";
          leaf long-description-string {
            type string {
              length "1..160";
            }
          } //long-description-string

        } //container description

        container hold-time {
          status "obsolete";
          description
              "Hold-Time for the multihoming-secondary-interface";
          leaf holdover-time {
            type uint32 {
              range "1..65535";
            }
            description
                "[1..65535]";
          } //holdover-time

        } //container hold-time

        leaf shutdown {
          type boolean;
          status "obsolete";
          description
              "Administratively enable/disable the multihoming-secondary-interface";
        }

      } //list mh-secondary-interface

      uses "conf-router-mld-r13:alu-conf-router-mld-r13";
      uses "conf-router-mpls-r13:alu-conf-router-mpls-r13";
      container mpls-labels {
        description
            "Configure Mpls labels on the ingress router";
        container bgp-labels-hold-timer {
          description
              "Configure bgp labels hold timer on the ingress router";
          leaf seconds {
            type uint32 {
              range "0..255";
            }
            default 0;
            description
                "[0..255]";
          } //seconds

        } //container bgp-labels-hold-timer

        container sr-labels {
          description
              "Configure Segment Routing Labels on the ingress router";
          leaf start {
            type string;
            description
                "Attribute start-value for sr-labels";
          } //start

          leaf end {
            type string;
            description
                "Attribute end-value for sr-labels";
          } //end

        } //container sr-labels

        container static-label-range {
          description
              "Configure Static Label Range on the ingress router";
          leaf static-range {
            type string;
            description
                "Attribute static-range for static-label-range";
          } //static-range

        } //container static-label-range

        list reserved-label-block {
          key "name";
          description
              "Configure mpls reserved label blocks.";
          leaf name {
            type string {
              length "1..64";
            }
          } //name

          container start-label {
            description
                "Configures start and end values for reserved label blocks.";
            leaf start-value {
              type string;
              description
                  "Attribute start-value for start-label";
            } //start-value

            leaf end-label {
              type string;
              description
                  "Attribute end-value for start-label";
            } //end-label

          } //container start-label

        } //list reserved-label-block

      } //container mpls-labels

      container msdp {
        presence
            "Create/Configure or delete MSDP instance";
        container active-source-limit {
          description
              "Configure maximum number of active source messages accepted by MSDP";
          leaf number {
            type int32 {
              range "0..1000000";
            }
          } //number

        } //container active-source-limit

        leaf data-encapsulation {
          type boolean;
          description
              "Enable/Disable encapsulation of multicast data used by MSDP";
        }

        container export {
          description
              "Configure policies to export Source Active state from the Source Active list 
               into MSDP";
          leaf-list policy-name {
            type string {
              length "1..32";
            }
            max-elements 5;
          } //policy-name

        } //container export

        container import {
          description
              "Configure policies to import Source Active state from the Source Active list 
               into MSDP";
          leaf-list policy-name {
            type string {
              length "1..32";
            }
            max-elements 5;
          } //policy-name

        } //container import

        container local-address {
          description
              "Configure the local end of an MSDP session";
          leaf ip-address {
            type inet:ip-address;
            description
                "[a.b.c.d]";
          } //ip-address

        } //container local-address

        container receive-msdp-msg-rate {
          description
              "Configure number of messages MSDP can read";
          leaf number {
            type uint32 {
              range "10..10000";
            }
          } //number

          leaf interval {
            type uint32 {
              range "1..600";
            }
          } //interval

          leaf threshold {
            type uint32 {
              range "1..1000000";
            }
          } //threshold

        } //container receive-msdp-msg-rate

        container rpf-table {
          description
              "Configure the route table(s) for RPF lookup";
          leaf rtable-m-rtable-u-both {
            type enumeration {
              enum rtable-m;
              enum rtable-u;
              enum both;
            }
            description
                "keywords";
          } //rtable-m-rtable-u-both

        } //container rpf-table

        container sa-timeout {
          description
              "Configure a MSDP SA-timeout";
          leaf seconds {
            type uint32 {
              range "90..600";
            }
            default 90;
          } //seconds

        } //container sa-timeout

        leaf shutdown {
          type boolean;
          description
              "Administratively enable/disable the MSDP instance";
        }

        list group {
          key "group-name";
          description
              "Configure a MSDP group";
          leaf group-name {
            type string {
              length "1..32";
            }
          } //group-name

          container active-source-limit {
            description
                "Configure maximum number of active source messages accepted by MSDP group";
            leaf number {
              type int32 {
                range "0..1000000";
              }
            } //number

          } //container active-source-limit

          container export {
            description
                "Configure policies to export Source Active state from the Source Active list 
                 into MSDP";
            leaf-list policy-name {
              type string {
                length "1..32";
              }
              max-elements 5;
            } //policy-name

          } //container export

          container import {
            description
                "Configure policies to import Source Active state from the Source Active list 
                 into MSDP";
            leaf-list policy-name {
              type string {
                length "1..32";
              }
              max-elements 5;
            } //policy-name

          } //container import

          container local-address {
            description
                "Configure the local end of an MSDP session";
            leaf ip-address {
              type inet:ip-address;
              description
                  "[a.b.c.d]";
            } //ip-address

          } //container local-address

          container mode {
            description
                "Configure mode of a MSDP group";
            leaf mesh-group-standard {
              type enumeration {
                enum mesh-group;
                enum standard;
              }
              description
                  "keywords";
            } //mesh-group-standard

          } //container mode

          container receive-msdp-msg-rate {
            description
                "Configure number of messages MSDP group can read";
            leaf number {
              type uint32 {
                range "10..10000";
              }
            } //number

            leaf interval {
              type uint32 {
                range "1..600";
              }
            } //interval

            leaf threshold {
              type uint32 {
                range "1..1000000";
              }
            } //threshold

          } //container receive-msdp-msg-rate

          leaf shutdown {
            type boolean;
            description
                "Administratively enable/disable the MSDP group instance";
          }

          list peer {
            key "ip-address";
            description
                "Configure a MSDP group peer";
            leaf ip-address {
              type inet:ip-address;
              description
                  "[a.b.c.d]";
            } //ip-address

            container active-source-limit {
              description
                  "Configure maximum number of active source messages accepted by MSDP peer";
              leaf number {
                type int32 {
                  range "0..1000000";
                }
              } //number

            } //container active-source-limit

            container authentication-key {
              description
                  "Configure the MD5 authentication key for the MSDP peering session";
              leaf authentication-key-hash-key {
                type string {
                  length "1..500";
                }
                description
                    "authentication-key - [255 chars max] 
                     hash-key 
                     hash2-key 
                     custom-key";
              } //authentication-key-hash-key

              leaf hash-hash2-custom {
                type enumeration {
                  enum hash;
                  enum hash2;
                  enum custom;
                }
                description
                    "keywords - specify hashing scheme";
              } //hash-hash2-custom

            } //container authentication-key

            leaf default-peer {
              type boolean;
              description
                  "Enable/Disable default peer as MSDP peer";
            }

            container export {
              description
                  "Configure policies to export Source Active state from the Source Active list 
                   into MSDP group peer";
              leaf-list policy-name {
                type string {
                  length "1..32";
                }
                max-elements 5;
              } //policy-name

            } //container export

            container import {
              description
                  "Configure policies to import Source Active state from the Source Active list 
                   into MSDP group peer";
              leaf-list policy-name {
                type string {
                  length "1..32";
                }
                max-elements 5;
              } //policy-name

            } //container import

            container local-address {
              description
                  "Configure the local end of an MSDP peering session";
              leaf ip-address {
                type inet:ip-address;
                description
                    "[a.b.c.d]";
              } //ip-address

            } //container local-address

            container receive-msdp-msg-rate {
              description
                  "Configure number of messages MSDP group peer can read";
              leaf number {
                type uint32 {
                  range "10..10000";
                }
              } //number

              leaf interval {
                type uint32 {
                  range "1..600";
                }
              } //interval

              leaf threshold {
                type uint32 {
                  range "1..1000000";
                }
              } //threshold

            } //container receive-msdp-msg-rate

            leaf shutdown {
              type boolean;
              description
                  "Administratively enable/disable the MSDP peer group instance";
            }

          } //list peer

        } //list group

        list peer {
          key "ip-address";
          description
              "Configure a MSDP peer";
          leaf ip-address {
            type inet:ip-address;
            description
                "[a.b.c.d]";
          } //ip-address

          container active-source-limit {
            description
                "Configure maximum number of active source messages accepted by MSDP peer";
            leaf number {
              type int32 {
                range "0..1000000";
              }
            } //number

          } //container active-source-limit

          container authentication-key {
            description
                "Configure the MD5 authentication key for the MSDP peering session";
            leaf authentication-key-hash-key {
              type string {
                length "1..500";
              }
              description
                  "authentication-key - [255 chars max] 
                   hash-key 
                   hash2-key 
                   custom-key";
            } //authentication-key-hash-key

            leaf hash-hash2-custom {
              type enumeration {
                enum hash;
                enum hash2;
                enum custom;
              }
              description
                  "keywords - specify hashing scheme";
            } //hash-hash2-custom

          } //container authentication-key

          leaf default-peer {
            type boolean;
            description
                "Enable/Disable default peer as MSDP peer";
          }

          container export {
            description
                "Configure policies to export Source Active state from the Source Active list 
                 into MSDP";
            leaf-list policy-name {
              type string {
                length "1..32";
              }
              max-elements 5;
            } //policy-name

          } //container export

          container import {
            description
                "Configure policies to import Source Active state from the Source Active list 
                 into MSDP";
            leaf-list policy-name {
              type string {
                length "1..32";
              }
              max-elements 5;
            } //policy-name

          } //container import

          container local-address {
            description
                "Configure the local end of an MSDP peering session";
            leaf ip-address {
              type inet:ip-address;
              description
                  "[a.b.c.d]";
            } //ip-address

          } //container local-address

          container receive-msdp-msg-rate {
            description
                "Configure number of messages MSDP peer can read";
            leaf number {
              type uint32 {
                range "10..10000";
              }
            } //number

            leaf interval {
              type uint32 {
                range "1..600";
              }
            } //interval

            leaf threshold {
              type uint32 {
                range "1..1000000";
              }
            } //threshold

          } //container receive-msdp-msg-rate

          leaf shutdown {
            type boolean;
            description
                "Administratively enable/disable the MSDP peer instance";
          }

        } //list peer

        list source {
          key "unicast-ip-prefix-mask";
          description
              "Configure a MSDP source";
          leaf unicast-ip-prefix-mask {
            type inet:ip-prefix;
            description
                "ip-prefix/mask";
          } //unicast-ip-prefix-mask

          container active-source-limit {
            description
                "Configure maximum number of active source messages accepted by MSDP source";
            leaf number {
              type uint32 {
                range "0..1000000";
              }
            } //number

          } //container active-source-limit

        } //list source

      } //container msdp

      container mtrace2 {
        description
            "Configure UDP-based Multicast Traceroute (mstat2 and mtrace2)";
        leaf shutdown {
          type boolean;
          description
              "Administratively enable/disable launching UDP-based Multicast Traceroute 
               (mstat2 or mtrace2) tests, and listening for unsolicited test packets";
        }

        container udp-port {
          description
              "Configure the UDP port used when launching an mstat2 or mtrace2 test, and when 
               listening for unsolicited test packets";
          leaf udp-port-number {
            type uint32 {
              range "1024..49151";
            }
            default 5000;
            description
                "[1024..49151] - Default: 5000";
          } //udp-port-number

        } //container udp-port

      } //container mtrace2

      uses "conf-router-nat-r13:alu-conf-router-nat-r13";
      container network-domains {
        description
            "Configure network-domains";
        list network-domain {
          key "network-domain-name";
          description
              "Provision a network-domain";
          leaf network-domain-name {
            type inet:domain-name;
          } //network-domain-name

          container description {
            description
                "Description for this network domain";
            leaf description-string {
              type string {
                length "1..80";
              }
            } //description-string

          } //container description

        } //list network-domain

      } //container network-domains

      uses "conf-router-ogvalid-r13:alu-conf-router-ogvalid-r13";
      uses "conf-router-ospf-r13:alu-conf-router-ospf-r13";
      uses "conf-router-ospf3-r13:alu-conf-router-ospf3-r13";
      uses "conf-router-treesid-r13:alu-conf-router-treesid-r13";
      uses "conf-router-pcep-r13:alu-conf-router-pcep-r13";
      container pcp-server {
        description
            "Configure Port Control Policy servers";
        list server {
          key "pcp-server-name";
          description
              "Configure a PCP server";
          leaf pcp-server-name {
            type string {
              length "1..32";
            }
          } //pcp-server-name

          container description {
            description
                "Configure a description";
            leaf description-string {
              type string {
                length "1..80";
              }
            } //description-string

          } //container description

          container dual-stack-lite-address {
            description
                "Configure the inside Dual Stack Lite AFTR address (optional)";
            leaf ipv6-address {
              type inet:ipv6-address;
              description
                  "Attribute ipv6-address for dual-stack-lite-address";
            } //ipv6-address

          } //container dual-stack-lite-address

          container fwd-inside-router {
            description
                "Configure the PCP forwarding inside virtual router instance";
            leaf router-instance {
              type string {
                length "1..32";
              }
              description
                  "Attribute router-instance for fwd-inside-router";
            } //router-instance

            leaf service-name {
              type string;
            } //service-name

          } //container fwd-inside-router

          list interface {
            key "interface-name";
            description
                "Associate an interface";
            leaf interface-name {
              type string {
                length "1..32";
              }
              description
                  "[32 chars max] (must start with a letter)";
            } //interface-name

          } //list interface

          container pcp-server-policy {
            description
                "Configure the PCP server policy";
            leaf name {
              type string {
                length "1..32";
              }
            } //name

          } //container pcp-server-policy

          leaf shutdown {
            type boolean;
            description
                "Administratively enable or disable the PCP server";
          }

        } //list server

      } //container pcp-server

      uses "conf-router-pim-r13:alu-conf-router-pim-r13";
      list policy-acct-template {
        key "template-name";
        description
            "Create/Configure or Delete Policy Accounting template";
        leaf template-name {
          type string {
            length "1..32";
          }
        } //template-name

        container dest-class {
          description
              "Create or Delete destination class index";
          leaf-list index {
            type uint32 {
              range "1..255";
            }
            max-elements 255;
          } //index

          leaf dest-class-id {
            type uint32 {
              range "1..255";
            }
            description
                "index";
          } //dest-class-id

          leaf all {
            type boolean;
            description
                "Delete all dest-class index";
          } //all

        } //container dest-class

        container source-class {
          description
              "Create or Delete source class index";
          leaf-list index {
            type uint32 {
              range "1..255";
            }
            max-elements 255;
          } //index

          leaf source-class-id {
            type uint32 {
              range "1..255";
            }
            description
                "index";
          } //source-class-id

          leaf all {
            type boolean;
            description
                "Delete all source-class index";
          } //all

        } //container source-class

      } //list policy-acct-template

      uses "conf-router-policy-r13:alu-conf-router-policy-r13";
      uses "conf-router-radprox-r13:alu-conf-router-radprox-r13";
      container radius-server {
        description
            "Configure RADIUS servers";
        list server {
          key "server-name";
          description
              "Add/remove a RADIUS server";
          leaf server-name {
            type string {
              length "1..32";
            }
          } //server-name

          leaf address {
            type string;
            description
                "Attribute ip-address for server";
          } //address

          leaf secret {
            type string {
              length "1..500";
            }
            description
                "secret-key - [64 chars max] 
                 hash-key 
                 hash2-key 
                 custom-key";
          } //secret

          leaf hash-hash2-custom {
            type enumeration {
              enum hash;
              enum hash2;
              enum custom;
            }
            description
                "keywords - specify hashing scheme";
          } //hash-hash2-custom

          leaf accept-coa {
            type boolean;
            description
                "Configure this server for Change of Authorization messages";
          }

          container acct-port {
            description
                "Configure the ACCT UDP port";
            leaf port {
              type uint16 {
                range "1..65535";
              }
            } //port

          } //container acct-port

          container auth-port {
            description
                "Configure the AUTH UDP port";
            leaf port {
              type uint16 {
                range "1..65535";
              }
            } //port

          } //container auth-port

          container coa-script-policy {
            description
                "Configure a RADIUS script policy to modify Change-of-Authorization messages";
            leaf script-policy-name {
              type string {
                length "1..32";
              }
            } //script-policy-name

          } //container coa-script-policy

          container description {
            description
                "Configure a description";
            leaf description-string {
              type string {
                length "1..80";
              }
            } //description-string

          } //container description

          container pending-requests-limit {
            description
                "Configure the limit of the number of pending RADIUS requests";
            leaf limit {
              type uint32 {
                range "1..4096";
              }
            } //limit

          } //container pending-requests-limit

          container python-policy {
            description
                "Configure a Python script policy to modify Change-of-Authorization messages";
            leaf name {
              type string {
                length "1..32";
              }
            } //name

          } //container python-policy

        } //list server

      } //container radius-server

      container rib-api {
        description
            "Configure RIB-API information";
        container mpls {
          description
              "Configure RIB-API MPLS information";
          container reserved-label-block {
            description
                "Configure reserved label block.";
            leaf name {
              type string {
                length "1..64";
              }
            } //name

          } //container reserved-label-block

          leaf shutdown {
            type boolean;
            description
                "Administratively enable/disable.";
          }

        } //container mpls

      } //container rib-api

      uses "conf-router-rip-r13:alu-conf-router-rip-r13";
      container ripng {
        presence
            "Create/Configure or delete RIP-NG instance";
        leaf bfd-enable {
          type boolean;
          description
              "Enable BFD monitoring of RIPng peers";
        }

        container check-zero {
          description
              "Check for zero values in must-be-zero fields";
          leaf enable-disable {
            type enumeration {
              enum enable;
              enum disable;
            }
            description
                "keywords";
          } //enable-disable

        } //container check-zero

        container description {
          description
              "Create a textual description for the RIP-NG instance";
          leaf description-string {
            type string {
              length "1..80";
            }
          } //description-string

        } //container description

        container export {
          description
              "Apply export policies used to determine routes advertised to all peers";
          leaf-list policy-name {
            type string {
              length "1..32";
            }
            max-elements 5;
          } //policy-name

        } //container export

        container export-limit {
          description
              "Maximum number of routes (prefixes) that can be exported into RIP-NG from the 
               route table.";
          leaf number {
            type uint32 {
              range "1..4294967295";
            }
          } //number

          leaf log {
            type uint16 {
              range "1..100";
            }
          } //log

        } //container export-limit

        container import {
          description
              "Apply import policies used to determine routes accepted from all peers";
          leaf-list policy-name {
            type string {
              length "1..32";
            }
            max-elements 5;
          } //policy-name

        } //container import

        container message-size {
          description
              "Set maximum number of routes in message";
          leaf max-num-of-routes {
            type uint64 {
              range "25..255";
            }
          } //max-num-of-routes

        } //container message-size

        container metric-in {
          description
              "Set metric added to routes from neighbor";
          leaf metric {
            type uint32 {
              range "1..16";
            }
          } //metric

        } //container metric-in

        container metric-out {
          description
              "Set metric added to routes exported into RIP-NG";
          leaf metric {
            type uint32 {
              range "1..16";
            }
          } //metric

        } //container metric-out

        container preference {
          description
              "Set the route preference";
          leaf preference {
            type uint64 {
              range "1..255";
            }
          } //preference

        } //container preference

        container receive {
          description
              "Specify type of updates accepted";
          leaf receive-type {
            type enumeration {
              enum none;
              enum ripng;
            }
            description
                "none | ripng - keywords";
          } //receive-type

        } //container receive

        container send {
          description
              "Specify type of message sent";
          leaf send-type {
            type enumeration {
              enum none;
              enum ripng;
            }
            description
                "none | ripng - keywords";
          } //send-type

        } //container send

        leaf shutdown {
          type boolean;
          description
              "Administratively enable/disable the RIP-NG instance";
        }

        container split-horizon {
          description
              "Enable/disable split-horizon";
          leaf enable-disable {
            type enumeration {
              enum enable;
              enum disable;
            }
            description
                "keywords";
          } //enable-disable

        } //container split-horizon

        container timers {
          description
              "Specify number of seconds for each timer";
          leaf update {
            type uint32 {
              range "1..600";
            }
            description
                "[1..600] seconds";
          } //update

          leaf timeout {
            type uint32 {
              range "1..1200";
            }
            description
                "[1..1200] seconds";
          } //timeout

          leaf flush {
            type uint32 {
              range "1..1200";
            }
            description
                "[1..1200] seconds";
          } //flush

        } //container timers

        list group {
          key "name";
          description
              "Configure or remove a group of interfaces";
          leaf name {
            type string;
          } //name

          leaf bfd-enable {
            type boolean;
            description
                "Enable BFD monitoring of RIPng peers";
          }

          container check-zero {
            description
                "Check for zero values in must-be-zero fields";
            leaf enable-disable {
              type enumeration {
                enum enable;
                enum disable;
              }
              description
                  "keywords";
            } //enable-disable

          } //container check-zero

          container description {
            description
                "Create a textual description for the group";
            leaf description-string {
              type string {
                length "1..80";
              }
            } //description-string

          } //container description

          container export {
            description
                "Apply export policies used to determine routes advertised to group peers";
            leaf-list policy-name {
              type string {
                length "1..32";
              }
              max-elements 5;
            } //policy-name

          } //container export

          container import {
            description
                "Apply import policies used to determine routes accepted from peers of group";
            leaf-list policy-name {
              type string {
                length "1..32";
              }
              max-elements 5;
            } //policy-name

          } //container import

          container message-size {
            description
                "Set maximum number of routes in message";
            leaf max-num-of-routes {
              type uint64 {
                range "25..255";
              }
            } //max-num-of-routes

          } //container message-size

          container metric-in {
            description
                "Set metric added to routes from neighbor";
            leaf metric {
              type uint32 {
                range "1..16";
              }
            } //metric

          } //container metric-in

          container metric-out {
            description
                "Set metric added to routes exported into RIP-NG";
            leaf metric {
              type uint32 {
                range "1..16";
              }
            } //metric

          } //container metric-out

          container preference {
            description
                "Set the route preference";
            leaf preference {
              type uint64 {
                range "1..255";
              }
            } //preference

          } //container preference

          container receive {
            description
                "Specify type of updates accepted";
            leaf receive-type {
              type enumeration {
                enum none;
                enum ripng;
              }
              description
                  "none | ripng - keywords";
            } //receive-type

          } //container receive

          container send {
            description
                "Specify type of message sent";
            leaf send-type {
              type enumeration {
                enum none;
                enum ripng;
              }
              description
                  "none | ripng - keywords";
            } //send-type

          } //container send

          leaf shutdown {
            type boolean;
            description
                "Administratively enable/disable the group";
          }

          container split-horizon {
            description
                "Enable/disable split-horizon";
            leaf enable-disable {
              type enumeration {
                enum enable;
                enum disable;
              }
              description
                  "keywords";
            } //enable-disable

          } //container split-horizon

          container timers {
            description
                "Specify number of seconds for each timer";
            leaf update {
              type uint32 {
                range "1..600";
              }
              description
                  "[1..600] seconds";
            } //update

            leaf timeout {
              type uint32 {
                range "1..1200";
              }
              description
                  "[1..1200] seconds";
            } //timeout

            leaf flush {
              type uint32 {
                range "1..1200";
              }
              description
                  "[1..1200] seconds";
            } //flush

          } //container timers

          list neighbor {
            key "ip-int-name";
            description
                "Configure or remove an interface as a RIP-NG neighbor";
            leaf ip-int-name {
              type string {
                length "1..32";
              }
            } //ip-int-name

            leaf bfd-enable {
              type boolean;
              description
                  "Enable BFD monitoring of RIPng peers";
            }

            container check-zero {
              description
                  "Check for zero values";
              leaf enable-disable {
                type enumeration {
                  enum enable;
                  enum disable;
                }
                description
                    "keywords";
              } //enable-disable

            } //container check-zero

            container description {
              description
                  "Create a textual description for the neighbor";
              leaf description-string {
                type string {
                  length "1..80";
                }
              } //description-string

            } //container description

            container export {
              description
                  "Apply export policies used to determine routes advertised to peers";
              leaf-list policy-name {
                type string {
                  length "1..32";
                }
                max-elements 5;
              } //policy-name

            } //container export

            container import {
              description
                  "Apply import policies used to determine routes accepted from peers";
              leaf-list policy-name {
                type string {
                  length "1..32";
                }
                max-elements 5;
              } //policy-name

            } //container import

            container message-size {
              description
                  "Set number of routes in message";
              leaf max-num-of-routes {
                type uint64 {
                  range "25..255";
                }
              } //max-num-of-routes

            } //container message-size

            container metric-in {
              description
                  "Set metric added to routes from neighbor";
              leaf metric {
                type uint32 {
                  range "1..16";
                }
              } //metric

            } //container metric-in

            container metric-out {
              description
                  "Set metric added to routes exported into RIP-NG";
              leaf metric {
                type uint32 {
                  range "1..16";
                }
              } //metric

            } //container metric-out

            container preference {
              description
                  "Set the route preference";
              leaf preference {
                type uint64 {
                  range "1..255";
                }
              } //preference

            } //container preference

            container receive {
              description
                  "Specify type of updates accepted";
              leaf receive-type {
                type enumeration {
                  enum none;
                  enum ripng;
                }
                description
                    "none | ripng - keywords";
              } //receive-type

            } //container receive

            container send {
              description
                  "Specify type of message sent";
              leaf send-type {
                type enumeration {
                  enum none;
                  enum ripng;
                  enum unicast;
                }
              } //send-type

            } //container send

            leaf shutdown {
              type boolean;
              description
                  "Administratively enable/disable the neighbor";
            }

            container split-horizon {
              description
                  "Enable/disable split-horizon";
              leaf enable-disable {
                type enumeration {
                  enum enable;
                  enum disable;
                }
                description
                    "keywords";
              } //enable-disable

            } //container split-horizon

            container timers {
              description
                  "Specify number of seconds for each timer";
              leaf update {
                type uint32 {
                  range "1..600";
                }
                description
                    "[1..600] seconds";
              } //update

              leaf timeout {
                type uint32 {
                  range "1..1200";
                }
                description
                    "[1..1200] seconds";
              } //timeout

              leaf flush {
                type uint32 {
                  range "1..1200";
                }
                description
                    "[1..1200] seconds";
              } //flush

            } //container timers

            list unicast-address {
              key "ipv6-address";
              description
                  "Create a unicast-address for the neighbor";
              leaf ipv6-address {
                type inet:ipv6-address;
              } //ipv6-address

            } //list unicast-address

          } //list neighbor

        } //list group

      } //container ripng

      uses "conf-router-nhroute-r13:alu-conf-router-nhroute-r13";
      uses "conf-router-radvert-r13:alu-conf-router-radvert-r13";
      uses "conf-router-rsvp-r13:alu-conf-router-rsvp-r13";
      container segment-routing {
        description
            "Segment routing management";
        container sr-policies {
          description
              "Configuration of segment routing static policies";
          container reserved-label-block {
            description
                "Reserved label block name used with the associated segment routing policy 
                 routes";
            leaf name {
              type string;
            } //name

          } //container reserved-label-block

          leaf shutdown {
            type boolean;
            description
                "Administratively disable or enable the segment routing policy";
          }

          container egress-statistics {
            presence
                "Configure Segment Routing Egress Statistics";
            leaf shutdown {
              type boolean;
              description
                  "Administratively disable or enable the egress statistics";
            }

          } //container egress-statistics

          container ingress-statistics {
            presence
                "Static policies' ingress statistics";
            leaf shutdown {
              type boolean;
              description
                  "Administratively disable or enable the ingress statistics";
            }

          } //container ingress-statistics

          list static-policy {
            key "name";
            description
                "Configuration of a segment routing static policy";
            leaf name {
              type string;
            } //name

            container binding-sid {
              description
                  "A Segment ID value that opaquely represents an SR policy to upstream routers";
              leaf number {
                type string;
                description
                    "Attribute number for binding-sid";
              } //number

            } //container binding-sid

            container color {
              description
                  "Determines the set of traffic flows that would be steered by this policy";
              leaf color-id {
                type uint32;
              } //color-id

            } //container color

            container distinguisher {
              description
                  "A unique value to distinguish a policy";
              leaf distinguisher-id {
                type uint32 {
                  range "1..4294967295";
                }
              } //distinguisher-id

            } //container distinguisher

            container endpoint {
              description
                  "Destination IP address of the source-routed path";
              leaf ip-address {
                type string;
                description
                    "Attribute ip-address for endpoint";
              } //ip-address

            } //container endpoint

            container head-end {
              description
                  "The head end address for this static policy";
              leaf ipv4-address {
                type inet:ip-address;
              } //ipv4-address

              leaf local {
                type boolean;
                description
                    "0.0.0.0";
              } //local

            } //container head-end

            container preference {
              description
                  "The preference value of this static policy";
              leaf preference-id {
                type uint32;
              } //preference-id

            } //container preference

            leaf shutdown {
              type boolean;
              description
                  "Administratively disable or enable the static policy";
            }

            list segment-list {
              key "segment-list-id";
              description
                  "The segment list of a static policy";
              leaf segment-list-id {
                type uint32 {
                  range "1..32";
                }
              } //segment-list-id

              leaf shutdown {
                type boolean;
                description
                    "Administratively disable or enable the segment list";
              }

              container weight {
                description
                    "The weight of this segment list";
                leaf weight-id {
                  type uint32 {
                    range "1..4294967295";
                  }
                } //weight-id

              } //container weight

              list segment {
                key "segment-id";
                description
                    "A segment of a static policy";
                leaf segment-id {
                  type uint32 {
                    range "1..11";
                  }
                } //segment-id

                container mpls-label {
                  description
                      "MPLS lable value";
                  leaf mpls-label-id {
                    type uint32 {
                      range "0..1048575";
                    }
                  } //mpls-label-id

                } //container mpls-label

              } //list segment

            } //list segment-list

          } //list static-policy

        } //container sr-policies

      } //container segment-routing

      container sgt-qos {
        description
            "Configure DSCP/Dot1p re-marking for self-generated traffic";
        container application {
          description
              "Configure DSCP/Dot1p re-marking for applications";
          leaf dscp-app-name {
            type enumeration {
              enum bgp;
              enum bmp;
              enum call-trace;
              enum cflowd;
              enum dhcp;
              enum diameter;
              enum dns;
              enum ftp;
              enum grpc;
              enum gtp;
              enum http;
              enum ibcp;
              enum icmp;
              enum igmp;
              enum igmp-reporter;
              enum l2tp;
              enum ldp;
              enum mld;
              enum mpls-udp-return;
              enum msdp;
              enum mtrace2;
              enum ndis;
              enum ntp;
              enum ospf;
              enum pcep;
              enum pfcp;
              enum pim;
              enum ptp;
              enum radius;
              enum rip;
              enum rsvp;
              enum sflow;
              enum snmp;
              enum snmp-notification;
              enum srrp;
              enum ssh;
              enum syslog;
              enum tacplus;
              enum telnet;
              enum tftp;
              enum traceroute;
              enum vrrp;
            }
            description
                "Attribute dscp-app-name for application";
          } //dscp-app-name

          leaf dscp {
            type string {
              length "1..4";
            }
            description
                "Attribute dscp-value for application";
          } //dscp

          leaf dot1p {
            type string {
              length "1..4";
            }
            description
                "[none|0..7]";
          } //dot1p

          leaf dot1p-app-name {
            type enumeration {
              enum arp;
              enum isis;
              enum pppoe;
            }
          } //dot1p-app-name

        } //container application

        list dscp {
          key "dscp-name";
          description
              "Configure DSCP name to FC mapping";
          leaf dscp-name {
            type string {
              length "1..32";
            }
            description
                "Attribute dscp-name for dscp";
          } //dscp-name

          leaf fc {
            type enumeration {
              enum be;
              enum l2;
              enum af;
              enum l1;
              enum h2;
              enum ef;
              enum h1;
              enum nc;
            }
            default "be";
          } //fc

        } //list dscp

      } //container sgt-qos

      container static-route-entry {
        description
            "Create/Configure or Delete/Deconfigure static route entries";
        leaf ip-prefix-prefix-length {
          type string;
          description
              "Attribute ip-prefix/prefix-length for static-route-entry";
        } //ip-prefix-prefix-length

        leaf mcast {
          type boolean;
          description
              "keyword - Indicates that static-route being configured is used for mcast table 
               only";
        } //mcast

        container community {
          description
              "Create/Configure or Delete/Deconfigure community for static-route-entry";
          leaf-list comm-id {
            type string;
            max-elements 12;
            description
                "Attribute comm-id for community";
          } //comm-id

        } //container community

        list tag {
          key "tag";
          description
              "Create/Configure or Delete/Deconfigure tag for static-route-entry";
          leaf tag {
            type uint32 {
              range "1..4294967295";
            }
          } //tag

        } //list tag

        container black-hole {
          presence
              "Create/Configure or Delete/Deconfigure blackhole nexthop for 
               static-route-entry";
          list community {
            key "comm-id";
            description
                "Create/Configure or Delete/Deconfigure";
            leaf comm-id {
              type string;
              description
                  "Attribute comm-id for community";
            } //comm-id

          } //list community

          list description {
            key "description-string";
            description
                "Create/Configure or Delete/Deconfigure description";
            leaf description-string {
              type string {
                length "1..80";
              }
            } //description-string

          } //list description

          leaf dynamic-bgp {
            type boolean;
            description
                "Create/Configure or Delete/Deconfigure dynamic-bgp";
          }

          leaf generate-icmp {
            type boolean;
            description
                "Create/Configure or Delete/Deconfigure generate-icmp";
          }

          list metric {
            key "metric";
            description
                "Create/Configure or Delete/Deconfigure static route metric";
            leaf metric {
              type uint32 {
                range "0..65535";
              }
            } //metric

          } //list metric

          container preference {
            description
                "Create/Configure or Delete/Deconfigure preference";
            leaf preference {
              type uint16 {
                range "1..255";
              }
            } //preference

          } //container preference

          list prefix-list {
            key "prefix-list-name all-none";
            description
                "Create/Configure or Delete/Deconfigure static route prefix-list";
            leaf prefix-list-name {
              type string {
                length "1..32";
              }
            } //prefix-list-name

            leaf all-none {
              type enumeration {
                enum all;
                enum none;
                enum any;
              }
            } //all-none

          } //list prefix-list

          leaf shutdown {
            type boolean;
            description
                "Administratively enable/disable the static route black-hole nexthop";
          }

          list tag {
            key "tag";
            description
                "Create/Configure or Delete/Deconfigure static route tag";
            leaf tag {
              type uint32 {
                range "1..4294967295";
              }
            } //tag

          } //list tag

        } //container black-hole

        list indirect {
          key "ip-address";
          description
              "Create/Configure or Delete/Deconfigure indirect next-hop for 
               static-route-entry";
          leaf ip-address {
            type string;
            description
                "Attribute ip-address for indirect";
          } //ip-address

          list community {
            key "comm-id";
            description
                "Create/Configure or Delete/Deconfigure community";
            leaf comm-id {
              type string;
              description
                  "Attribute comm-id for community";
            } //comm-id

          } //list community

          list description {
            key "description-string";
            description
                "Create/Configure or Delete/Deconfigure description";
            leaf description-string {
              type string {
                length "1..80";
              }
            } //description-string

          } //list description

          list destination-class {
            key "dest-index";
            description
                "Create/Configure or Delete/Deconfigure destination-class";
            leaf dest-index {
              type uint32 {
                range "1..255";
              }
            } //dest-index

          } //list destination-class

          list metric {
            key "metric";
            description
                "Create/Configure or Delete/Deconfigure static route metric";
            leaf metric {
              type uint32 {
                range "0..65535";
              }
            } //metric

          } //list metric

          container preference {
            description
                "Create/Configure or Delete/Deconfigure static route preference";
            leaf preference {
              type uint16 {
                range "1..255";
              }
            } //preference

          } //container preference

          list prefix-list {
            key "prefix-list-name all-none";
            description
                "Create/Configure or Delete/Deconfigure static route prefix-list";
            leaf prefix-list-name {
              type string {
                length "1..32";
              }
            } //prefix-list-name

            leaf all-none {
              type enumeration {
                enum all;
                enum none;
                enum any;
              }
            } //all-none

          } //list prefix-list

          leaf shutdown {
            type boolean;
            description
                "Administratively enable/disable the static route indirect nexthop";
          }

          list source-class {
            key "source-index";
            description
                "Create/Configure or Delete/Deconfigure source-class";
            leaf source-index {
              type uint32 {
                range "1..255";
              }
            } //source-index

          } //list source-class

          list tag {
            key "tag";
            description
                "Create/Configure or Delete/Deconfigure static route tag";
            leaf tag {
              type uint32 {
                range "1..4294967295";
              }
            } //tag

          } //list tag

          list cpe-check {
            key "cpe-ip-address";
            description
                "Create/Configure or Delete/Deconfigure cpe-check Address";
            leaf cpe-ip-address {
              type string;
              description
                  "Attribute cpe-ip-address for cpe-check";
            } //cpe-ip-address

            container drop-count {
              description
                  "Create/Configure or Delete/Deconfigure cpe-check drop-count";
              leaf count {
                type uint64 {
                  range "1..255";
                }
                default 3;
              } //count

            } //container drop-count

            container interval {
              description
                  "Create/Configure or Delete/Deconfigure cpe-check interval";
              leaf seconds {
                type uint32 {
                  range "1..255";
                }
                default 1;
              } //seconds

            } //container interval

            leaf log {
              type boolean;
              description
                  "Create/Configure or Delete/Deconfigure cpe-check log";
            }

            container padding-size {
              description
                  "Create/Configure or Delete/Deconfigure cpe-check padding-size";
              leaf padding-size {
                type uint32 {
                  range "0..16384";
                }
              } //padding-size

            } //container padding-size

          } //list cpe-check

          list forwarding-class {
            key "forwarding-class-string";
            description
                "Create/Configure or Delete/Deconfigure forwarding-class";
            leaf forwarding-class-string {
              type string;
              description
                  "be|l2|af|l1|h2|ef|h1|nc";
            } //forwarding-class-string

            list priority {
              key "low-high";
              description
                  "Create/Configure or Delete/Deconfigure forwarding-class priority";
              leaf low-high {
                type enumeration {
                  enum low;
                  enum high;
                }
              } //low-high

            } //list priority

          } //list forwarding-class

          container tunnel-next-hop {
            description
                "Create/Configure tunnel-next-hop for indirect static-route-entry";
            leaf disallow-igp {
              type boolean;
              description
                  "Allow/Disallow igp to find the route to indirect next-hop";
            }

            container resolution {
              description
                  "Create/Configure or Delete/Deconfigure tunnel-next-hop resolution for 
                   resolving indirect static-route-entry";
              leaf any-disabled-filter {
                type enumeration {
                  enum any;
                  enum disabled;
                  enum filter;
                }
              } //any-disabled-filter

            } //container resolution

            container resolution-filter {
              description
                  "Create/Configure or Delete/Deconfigure tunnel-next-hop filter for resolving 
                   indirect static-route-entry";
              leaf ldp {
                type boolean;
                description
                    "Create/Configure or Delete/Deconfigure LDP to find the route to indirect 
                     next-hop static-route-entry";
              }

              leaf mpls-fwd-policy {
                type boolean;
                description
                    "Create/Configure or Delete/Deconfigure MPLS Forwarding Policy to find the 
                     route to indirect next-hop static-route-entry";
              }

              leaf rib-api {
                type boolean;
                description
                    "Create/Configure or Delete/Deconfigure RIB-API to find the route to indirect 
                     next-hop static-route-entry";
              }

              leaf sr-isis {
                type boolean;
                description
                    "Create/Configure or Delete/Deconfigure SR-ISIS to find the route to indirect 
                     next-hop static-route-entry";
              }

              leaf sr-ospf {
                type boolean;
                description
                    "Create/Configure or Delete/Deconfigure SR-OSPF to find the route to indirect 
                     next-hop static-route-entry";
              }

              leaf sr-ospf3 {
                type boolean;
                description
                    "Use sr-ospf3 for next hop resolution";
              }

              container rsvp-te {
                presence
                    "Create/Configure or Delete/Deconfigure RSVP-TE to find the route to indirect 
                     next-hop static-route-entry";
                list lsp {
                  key "lsp-name";
                  description
                      "Create/Configure or Delete/Deconfigure lsp-name for static-route-entry";
                  leaf lsp-name {
                    type string;
                    description
                        "Attribute lsp-name for lsp";
                  } //lsp-name

                } //list lsp

              } //container rsvp-te

              container sr-te {
                presence
                    "Create/Configure or Delete/Deconfigure SR-TE to find the route to indirect 
                     next-hop static-route-entry";
                list lsp {
                  key "lsp-name";
                  description
                      "Create/Configure or Delete/Deconfigure lsp-name for static-route-entry";
                  leaf lsp-name {
                    type string;
                    description
                        "Attribute lsp-name for lsp";
                  } //lsp-name

                } //list lsp

              } //container sr-te

            } //container resolution-filter

          } //container tunnel-next-hop

        } //list indirect

        list ipsec-tunnel {
          key "ipsec-tunnel-name";
          description
              "Create/Configure or Delete/Deconfigure ipsec-tunnel next-hop for 
               static-route-entry";
          leaf ipsec-tunnel-name {
            type string {
              length "1..32";
            }
          } //ipsec-tunnel-name

          list community {
            key "comm-id";
            description
                "Create/Configure or Delete/Deconfigure community";
            leaf comm-id {
              type string;
              description
                  "Attribute comm-id for community";
            } //comm-id

          } //list community

          list description {
            key "description-string";
            description
                "Create/Configure or Delete/Deconfigure description";
            leaf description-string {
              type string {
                length "1..80";
              }
            } //description-string

          } //list description

          list destination-class {
            key "dest-index";
            description
                "Create/Configure or Delete/Deconfigure destination-class";
            leaf dest-index {
              type uint32 {
                range "1..255";
              }
            } //dest-index

          } //list destination-class

          list metric {
            key "metric";
            description
                "Create/Configure or Delete/Deconfigure static route metric";
            leaf metric {
              type uint32 {
                range "0..65535";
              }
            } //metric

          } //list metric

          container preference {
            description
                "Create/Configure or Delete/Deconfigure static route preference";
            leaf preference {
              type uint16 {
                range "1..255";
              }
            } //preference

          } //container preference

          leaf shutdown {
            type boolean;
            description
                "Administratively enable/disable the static route nexthop";
          }

          list source-class {
            key "source-index";
            description
                "Create/Configure or Delete/Deconfigure source-class";
            leaf source-index {
              type uint32 {
                range "1..255";
              }
            } //source-index

          } //list source-class

          list tag {
            key "tag";
            description
                "Create/Configure or Delete/Deconfigure static route tag";
            leaf tag {
              type uint32 {
                range "1..4294967295";
              }
            } //tag

          } //list tag

          list forwarding-class {
            key "forwarding-class-string";
            description
                "Create/Configure or Delete/Deconfigure forwarding-class";
            leaf forwarding-class-string {
              type string;
              description
                  "be|l2|af|l1|h2|ef|h1|nc";
            } //forwarding-class-string

            list priority {
              key "low-high";
              description
                  "Create/Configure or Delete/Deconfigure forwarding class priority";
              leaf low-high {
                type enumeration {
                  enum low;
                  enum high;
                }
              } //low-high

            } //list priority

          } //list forwarding-class

        } //list ipsec-tunnel

        list next-hop {
          key "ip-int-name-ip-address-ipv6-address";
          description
              "Create/Configure or Delete/Deconfigure next-hop for static-route-entry";
          leaf ip-int-name-ip-address-ipv6-address {
            type string;
            description
                "Attribute ip-int-name|ip-address|ipv6-address for next-hop";
          } //ip-int-name-ip-address-ipv6-address

          leaf bfd-enable {
            type boolean;
            description
                "Create/Configure or Delete/Deconfigure bfd";
          }

          list community {
            key "comm-id";
            description
                "Create/Configure or Delete/Deconfigure community";
            leaf comm-id {
              type string;
              description
                  "Attribute comm-id for community";
            } //comm-id

          } //list community

          list description {
            key "description-string";
            description
                "Create/Configure or Delete/Deconfigure description";
            leaf description-string {
              type string {
                length "1..80";
              }
            } //description-string

          } //list description

          list destination-class {
            key "dest-index";
            description
                "Create/Configure or Delete/Deconfigure destination-class";
            leaf dest-index {
              type uint32 {
                range "1..255";
              }
            } //dest-index

          } //list destination-class

          leaf ldp-sync {
            type boolean;
            description
                "Create/Configure or Delete/Deconfigure ldp-sync";
          }

          list load-balancing-weight {
            key "load-balancing-weight-id";
            description
                "Create/Configure or Delete/Deconfigure load-balancing-weight";
            leaf load-balancing-weight-id {
              type uint32;
            } //load-balancing-weight-id

          } //list load-balancing-weight

          list metric {
            key "metric";
            description
                "Create/Configure or Delete/Deconfigure static route metric";
            leaf metric {
              type uint32 {
                range "0..65535";
              }
            } //metric

          } //list metric

          container preference {
            description
                "Create/Configure or Delete/Deconfigure static route preference";
            leaf preference {
              type uint16 {
                range "1..255";
              }
            } //preference

          } //container preference

          list prefix-list {
            key "prefix-list-name all-none";
            description
                "Create/Configure or Delete/Deconfigure static route prefix-list";
            leaf prefix-list-name {
              type string {
                length "1..32";
              }
            } //prefix-list-name

            leaf all-none {
              type enumeration {
                enum all;
                enum none;
                enum any;
              }
            } //all-none

          } //list prefix-list

          leaf shutdown {
            type boolean;
            description
                "Administratively enable/disable the static route nexthop";
          }

          list source-class {
            key "source-index";
            description
                "Create/Configure or Delete/Deconfigure source-class";
            leaf source-index {
              type uint32 {
                range "1..255";
              }
            } //source-index

          } //list source-class

          list tag {
            key "tag";
            description
                "Create/Configure or Delete/Deconfigure static route tag";
            leaf tag {
              type uint32 {
                range "1..4294967295";
              }
            } //tag

          } //list tag

          leaf validate-next-hop {
            type boolean;
            description
                "Create/Configure or Delete/Deconfigure validate-next-hop";
          }

          list cpe-check {
            key "cpe-ip-address";
            description
                "Create/Configure or Delete/Deconfigure cpe-check address";
            leaf cpe-ip-address {
              type string;
              description
                  "Attribute cpe-ip-address for cpe-check";
            } //cpe-ip-address

            container drop-count {
              description
                  "Create/Configure or Deconfigure cpe-check drop-count";
              leaf count {
                type uint32 {
                  range "1..255";
                }
                default 3;
              } //count

            } //container drop-count

            container interval {
              description
                  "Create/Configure or Deconfigure cpe-check interval";
              leaf seconds {
                type uint32 {
                  range "1..255";
                }
                default 1;
              } //seconds

            } //container interval

            leaf log {
              type boolean;
              description
                  "Create/Configure or Deconfigure cpe-check log";
            }

            container padding-size {
              description
                  "Create/Configure or Deconfigure cpe-check padding-size";
              leaf padding-size {
                type uint32 {
                  range "0..16384";
                }
              } //padding-size

            } //container padding-size

          } //list cpe-check

          list forwarding-class {
            key "forwarding-class-string";
            description
                "Create/Configure or Delete/Deconfigure forwarding-class";
            leaf forwarding-class-string {
              type string;
              description
                  "be|l2|af|l1|h2|ef|h1|nc";
            } //forwarding-class-string

            list priority {
              key "low-high";
              description
                  "Create/Configure or Deconfigure forwarding class priority";
              leaf low-high {
                type enumeration {
                  enum low;
                  enum high;
                }
              } //low-high

            } //list priority

          } //list forwarding-class

        } //list next-hop

      } //container static-route-entry

      list static-route-entry-old {
        key "ip-prefix-prefix-length mcast";
        status "obsolete";
        description
            "Configure static-route-entry";
        leaf ip-prefix-prefix-length {
          type string;
          description
              "Attribute ip-prefix/prefix-length for static-route-entry-old";
        } //ip-prefix-prefix-length

        leaf mcast {
          type boolean;
          description
              "keyword - Indicates that static-route being configured is used for mcast table 
               only";
        } //mcast

        container indirect {
          description
              "Configure indirect next-hop for static-route-entry";
          leaf ip-address {
            type string;
            description
                "Attribute ip-address for indirect";
          } //ip-address

          container tunnel-next-hop {
            presence
                "Configure tunnel-next-hop for indirect static-route-entry";
            leaf disallow-igp {
              type boolean;
              description
                  "Enable/Disable igp to find the route to indirect next-hop";
            }

            container resolution {
              description
                  "Configure tunnel-next-hop resolution for resolving indirect static-route-entry";
              leaf any-disabled-filter {
                type enumeration {
                  enum any;
                  enum disabled;
                  enum filter;
                }
              } //any-disabled-filter

            } //container resolution

            container resolution-filter {
              description
                  "Configure tunnel-next-hop filter for resolving indirect static-route-entry";
              leaf ldp {
                type boolean;
                description
                    "Enable/Disable LDP to find the route to indirect next-hop";
              }

              leaf sr-isis {
                type boolean;
                description
                    "Enable/Disable SR-ISIS to find the route to indirect next-hop";
              }

              leaf sr-ospf {
                type boolean;
                description
                    "Enable/Disable SR-OSPF to find the route to indirect next-hop";
              }

              leaf sr-te {
                type boolean;
                description
                    "Enable/Disable SR-TE to find the route to indirect next-hop";
              }

              container rsvp-te {
                presence
                    "Enable/Disable RSVP-TE to find the route to indirect next-hop";
                list lsp {
                  key "lsp-name";
                  leaf lsp-name {
                    type string;
                    description
                        "Attribute lsp-name for lsp";
                  } //lsp-name

                } //list lsp

              } //container rsvp-te

            } //container resolution-filter

          } //container tunnel-next-hop

        } //container indirect

      } //list static-route-entry-old

      container ttl-propagate {
        description
            "Manage TTL propagation from IP header into label stack";
        container label-route-local {
          description
              "Manage TTL propagation from IP header into label stack for local packets";
          leaf ttl-prop-type {
            type enumeration {
              enum none;
              enum all;
            }
            default "none";
            description
                "none|all - Default: none";
          } //ttl-prop-type

        } //container label-route-local

        container label-route-transit {
          description
              "Manage TTL propagation from IP header into label stack for transit packets";
          leaf ttl-prop-type {
            type enumeration {
              enum none;
              enum all;
            }
            default "none";
            description
                "none|all - Default: none";
          } //ttl-prop-type

        } //container label-route-transit

        container lsr-label-route {
          description
              "Manage TTL propagation from IP header into label stack";
          leaf ttl-prop-type {
            type enumeration {
              enum none;
              enum all;
            }
            default "none";
            description
                "none|all - Default: none";
          } //ttl-prop-type

        } //container lsr-label-route

        container vprn-local {
          description
              "Manage TTL propagation from IP header into label stack for local packets";
          leaf ttl-prop-type {
            type enumeration {
              enum none;
              enum all;
              enum vc-only;
            }
            default "vc-only";
            description
                "none|all|vc-only - Default: vc-only";
          } //ttl-prop-type

        } //container vprn-local

        container vprn-transit {
          description
              "Manage TTL propagation from IP header into label stack for transit packets";
          leaf ttl-prop-type {
            type enumeration {
              enum none;
              enum all;
              enum vc-only;
            }
            default "vc-only";
            description
                "none|all|vc-only - Default: vc-only";
          } //ttl-prop-type

        } //container vprn-transit

      } //container ttl-propagate

      list tunnel-interface {
        key "sender";
        description
            "Configure tunnel interfaces";
        leaf rsvp-p2mp-create {
          type string;
          description
              "Attribute lsp-name for tunnel-interface";
        } //rsvp-p2mp-create

        leaf ldp-p2mp {
          type uint32 {
            range "1..4294967295";
          }
          description
              "[1..8192] for root-node, [1..4294967295] for non root-nodes";
        } //ldp-p2mp

        leaf sender {
          type inet:ip-address;
          description
              "[a.b.c.d]";
        } //sender

        leaf root-node {
          type boolean;
          description
              "keyword";
        } //root-node

        container description {
          description
              "Description for the tunnel-interface";
          leaf description-string {
            type string {
              length "1..80";
            }
          } //description-string

        } //container description

      } //list tunnel-interface

      container twamp-light {
        description
            "Configure TWAMP-Light (Two Way Active Measurement Protocol, Light) parameters 
             for the router";
        container reflector {
          description
              "Configure TWAMP-Light reflector parameters";
          leaf udp-port {
            type string;
            description
                "[862 | 64364..64373] - mandatory when creating a TWAMP-Light reflector";
          } //udp-port

          container description {
            description
                "Configure a description for the TWAMP-Light reflector";
            leaf description-string {
              type string {
                length "1..80";
              }
            } //description-string

          } //container description

          leaf shutdown {
            type boolean;
            description
                "Administratively enable/disable the TWAMP-Light reflector";
          }

          list prefix {
            key "ip-prefix-prefix-length";
            description
                "Create or configure a prefix for the TWAMP-Light reflector";
            leaf ip-prefix-prefix-length {
              type string;
              description
                  "Attribute ip-prefix/prefix-length for prefix";
            } //ip-prefix-prefix-length

            container description {
              description
                  "Configure a description for the TWAMP-Light reflector prefix";
              leaf description-string {
                type string {
                  length "1..80";
                }
              } //description-string

            } //container description

          } //list prefix

        } //container reflector

      } //container twamp-light

      container vrgw {
        presence
            "Configure Virtual Residential Gateway functionality";
        container lanext {
          presence
              "Configure Home LAN Extension functionality";
          leaf shutdown {
            type boolean;
            description
                "Enable/disable the Home LAN Extension functionality";
          }

          container vxlan-port {
            description
                "Configure the remote VXLAN UDP port";
            leaf vxlan-port-id {
              type uint32 {
                range "1..65535";
              }
              description
                  "4789|8472";
            } //vxlan-port-id

          } //container vxlan-port

          container vxlan-vtep-range {
            description
                "Configure a range of VXLAN VTEP addresses";
            leaf start {
              type string;
              description
                  "Attribute ip-address|ipv6-address for vxlan-vtep-range";
            } //start

            leaf end {
              type string;
              description
                  "Attribute ip-address|ipv6-address for vxlan-vtep-range";
            } //end

          } //container vxlan-vtep-range

          container wlan-gw-group {
            description
                "Configure the ISA WLAN Gateway group";
            leaf wlan-gw-group-id {
              type uint32 {
                range "1..4";
              }
            } //wlan-gw-group-id

          } //container wlan-gw-group

        } //container lanext

      } //container vrgw

      uses "conf-router-wlan-r13:alu-conf-router-wlan-r13";
      uses "conf-router-wpp-r13:alu-conf-router-wpp-r13";
    } //container router

  } //grouping alu-conf-router-r13

} //module  alu-conf-router-r13
