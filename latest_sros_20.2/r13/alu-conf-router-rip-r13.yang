module alu-conf-router-rip-r13 {
  yang-version "1";

  namespace "urn:alcatel-lucent.com:sros:ns:yang:conf-router-rip-r13";

  prefix "conf-router-rip-r13";

  import alu-types {
    prefix "alu";
  }
  import ietf-inet-types {
    prefix "inet";
  }

  alu:alu-major-release "rel20";

  organization "Alcatel-Lucent";

  contact
      "Alcatel-Lucent SR OS Support 
       Web: <http://www.alcatel-lucent.com>";

  description
      "Alcatel-Lucent YANG Data model to configure RIP on SR OS based routers. 
       
       Copyright 2014-2015 Alcatel-Lucent, 2016 Nokia. All rights reserved. 
       Reproduction of this document is authorized on the condition that the 
       foregoing copyright notice is included. 
       
       This alu-conf-router-rip-r13 YANG module embodies Alcatel-Lucent's proprietary 
       intellectual property. Alcatel-Lucent retains all title and ownership in the 
       Specification, including any revisions. 
       
       Alcatel-Lucent grants all interested parties a non-exclusive license to use 
       and distribute an unmodified copy of this Specification in connection with 
       management of Alcatel-Lucent products, and without fee, provided this 
       copyright notice and license appear on all copies. 
       
       This Specification is supplied `as is', and Alcatel-Lucent makes no warranty, 
       either express or implied, as to the use, operation, condition, or performance 
       of the Specification.";

  revision  "2019-08-08";

  grouping alu-conf-router-rip-r13 {
    container rip {
      presence
          "Configure RIP";
      container authentication-key {
        description
            "Set authentication key";
        leaf authentication-key-hash-key {
          type string {
            length "1..500";
          }
          description
              "authentication-key - [16 chars max] 
               hash-key 
               hash2-key 
               custom-key";
        } //authentication-key-hash-key

        leaf hash-hash2-custom {
          type enumeration {
            enum hash;
            enum hash2;
            enum custom;
          }
          description
              "keywords - specify hashing scheme";
        } //hash-hash2-custom

      } //container authentication-key

      container authentication-type {
        description
            "Set authentication type";
        leaf authentication-type {
          type enumeration {
            enum none;
            enum password;
            enum message-digest;
            enum message-digest-20;
            enum message-digest-16;
            enum message-digest-20-exact;
          }
          description
              "Attribute authentication-type for authentication-type";
        } //authentication-type

      } //container authentication-type

      leaf bfd-enable {
        type boolean;
        description
            "Enable BFD monitoring of RIP peers";
      }

      container check-zero {
        description
            "Check for zero values in must-be-zero fields";
        leaf enable-disable {
          type enumeration {
            enum enable;
            enum disable;
          }
          description
              "keywords";
        } //enable-disable

      } //container check-zero

      container description {
        description
            "Create a textual description for the RIP instance";
        leaf description-string {
          type string {
            length "1..80";
          }
        } //description-string

      } //container description

      container export {
        description
            "Apply export policies used to determine routes advertised to all peers";
        leaf-list policy-name {
          type string {
            length "1..32";
          }
          max-elements 5;
        } //policy-name

      } //container export

      container export-limit {
        description
            "Maximum number of routes (prefixes) that can be exported into RIP from the 
             route table.";
        leaf number {
          type uint32 {
            range "1..4294967295";
          }
        } //number

        leaf log {
          type uint16 {
            range "1..100";
          }
        } //log

      } //container export-limit

      container import {
        description
            "Apply import policies used to determine routes accepted from all peers";
        leaf-list policy-name {
          type string {
            length "1..32";
          }
          max-elements 5;
        } //policy-name

      } //container import

      container message-size {
        description
            "Set maximum number of routes in message";
        leaf max-num-of-routes {
          type uint64 {
            range "25..255";
          }
        } //max-num-of-routes

      } //container message-size

      container metric-in {
        description
            "Set metric added to routes from neighbor";
        leaf metric {
          type uint32 {
            range "1..16";
          }
        } //metric

      } //container metric-in

      container metric-out {
        description
            "Set metric added to routes exported into RIP";
        leaf metric {
          type uint32 {
            range "1..16";
          }
        } //metric

      } //container metric-out

      container preference {
        description
            "Set the route preference";
        leaf preference {
          type uint64 {
            range "1..255";
          }
        } //preference

      } //container preference

      container receive {
        description
            "Specify type of updates accepted";
        leaf receive-type {
          type enumeration {
            enum none;
            enum both;
            enum version-1;
            enum version-2;
          }
          description
              "both|none|version-1|version-2 - keywords";
        } //receive-type

      } //container receive

      container send {
        description
            "Specify type of message sent";
        leaf send-type {
          type enumeration {
            enum broadcast;
            enum multicast;
            enum none;
            enum version-1;
          }
          description
              "broadcast|multicast|none|version-1 - keywords";
        } //send-type

      } //container send

      leaf shutdown {
        type boolean;
        description
            "Administratively enable/disable the RIP instance";
      }

      container split-horizon {
        description
            "Enable/disable split-horizon";
        leaf enable-disable {
          type enumeration {
            enum enable;
            enum disable;
          }
          description
              "keywords";
        } //enable-disable

      } //container split-horizon

      container timers {
        description
            "Specify number of seconds for each timer";
        leaf update {
          type uint32 {
            range "1..600";
          }
          description
              "[1..600] seconds";
        } //update

        leaf timeout {
          type uint32 {
            range "1..1200";
          }
          description
              "[1..1200] seconds";
        } //timeout

        leaf flush {
          type uint32 {
            range "1..1200";
          }
          description
              "[1..1200] seconds";
        } //flush

      } //container timers

      list group {
        key "name";
        description
            "Configure or remove a group of interfaces";
        leaf name {
          type string {
            length "1..32";
          }
        } //name

        container authentication-key {
          description
              "Set authentication key";
          leaf authentication-key-hash-key {
            type string {
              length "1..500";
            }
            description
                "authentication-key - [16 chars max] 
                 hash-key 
                 hash2-key 
                 custom-key";
          } //authentication-key-hash-key

          leaf hash-hash2-custom {
            type enumeration {
              enum hash;
              enum hash2;
              enum custom;
            }
            description
                "keywords - specify hashing scheme";
          } //hash-hash2-custom

        } //container authentication-key

        container authentication-type {
          description
              "Set authentication type";
          leaf authentication-type {
            type enumeration {
              enum none;
              enum password;
              enum message-digest;
              enum message-digest-20;
              enum message-digest-16;
              enum message-digest-20-exact;
            }
            description
                "Attribute authentication-type for authentication-type";
          } //authentication-type

        } //container authentication-type

        leaf bfd-enable {
          type boolean;
          description
              "Enable BFD monitoring of RIP peers";
        }

        container check-zero {
          description
              "Check for zero values in must-be-zero fields";
          leaf enable-disable {
            type enumeration {
              enum enable;
              enum disable;
            }
            description
                "keywords";
          } //enable-disable

        } //container check-zero

        container description {
          description
              "Create a textual description for the group";
          leaf description-string {
            type string {
              length "1..80";
            }
          } //description-string

        } //container description

        container export {
          description
              "Apply export policies used to determine routes advertised to group peers";
          leaf-list policy-name {
            type string {
              length "1..32";
            }
            max-elements 5;
          } //policy-name

        } //container export

        container import {
          description
              "Apply import policies used to determine routes accepted from peers of group";
          leaf-list policy-name {
            type string {
              length "1..32";
            }
            max-elements 5;
          } //policy-name

        } //container import

        container message-size {
          description
              "Set maximum number of routes in message";
          leaf max-num-of-routes {
            type uint64 {
              range "25..255";
            }
          } //max-num-of-routes

        } //container message-size

        container metric-in {
          description
              "Set metric added to routes from neighbor";
          leaf metric {
            type uint32 {
              range "1..16";
            }
          } //metric

        } //container metric-in

        container metric-out {
          description
              "Set metric added to routes exported into RIP";
          leaf metric {
            type uint32 {
              range "1..16";
            }
          } //metric

        } //container metric-out

        container preference {
          description
              "Set the route preference";
          leaf preference {
            type uint64 {
              range "1..255";
            }
          } //preference

        } //container preference

        container receive {
          description
              "Specify type of updates accepted";
          leaf receive-type {
            type enumeration {
              enum none;
              enum both;
              enum version-1;
              enum version-2;
            }
            description
                "both|none|version-1|version-2 - keywords";
          } //receive-type

        } //container receive

        container send {
          description
              "Specify type of message sent";
          leaf send-type {
            type enumeration {
              enum broadcast;
              enum multicast;
              enum none;
              enum version-1;
            }
            description
                "broadcast|multicast|none|version-1 - keywords";
          } //send-type

        } //container send

        leaf shutdown {
          type boolean;
          description
              "Administratively enable/disable the group";
        }

        container split-horizon {
          description
              "Enable/disable split-horizon";
          leaf enable-disable {
            type enumeration {
              enum enable;
              enum disable;
            }
            description
                "keywords";
          } //enable-disable

        } //container split-horizon

        container timers {
          description
              "Specify number of seconds for each timer";
          leaf update {
            type uint32 {
              range "1..600";
            }
            description
                "[1..600] seconds";
          } //update

          leaf timeout {
            type uint32 {
              range "1..1200";
            }
            description
                "[1..1200] seconds";
          } //timeout

          leaf flush {
            type uint32 {
              range "1..1200";
            }
            description
                "[1..1200] seconds";
          } //flush

        } //container timers

        list neighbor {
          key "ip-int-name";
          description
              "Configure or remove an interface as a RIP neighbor";
          leaf ip-int-name {
            type string {
              length "1..32";
            }
          } //ip-int-name

          container authentication-key {
            description
                "Set authentication key";
            leaf authentication-key-hash-key {
              type string {
                length "1..500";
              }
              description
                  "authentication-key - [16 chars max] 
                   hash-key 
                   hash2-key 
                   custom-key";
            } //authentication-key-hash-key

            leaf hash-hash2-custom {
              type enumeration {
                enum hash;
                enum hash2;
                enum custom;
              }
              description
                  "keywords - specify hashing scheme";
            } //hash-hash2-custom

          } //container authentication-key

          container authentication-type {
            description
                "Set authentication type";
            leaf authentication-type {
              type enumeration {
                enum none;
                enum password;
                enum message-digest;
                enum message-digest-20;
                enum message-digest-16;
                enum message-digest-20-exact;
              }
              description
                  "Attribute authentication-type for authentication-type";
            } //authentication-type

          } //container authentication-type

          leaf bfd-enable {
            type boolean;
            description
                "Enable BFD monitoring of RIP peers";
          }

          container check-zero {
            description
                "Check for zero values";
            leaf enable-disable {
              type enumeration {
                enum enable;
                enum disable;
              }
              description
                  "keywords";
            } //enable-disable

          } //container check-zero

          container description {
            description
                "Create a textual description for the neighbor";
            leaf description-string {
              type string {
                length "1..80";
              }
            } //description-string

          } //container description

          container export {
            description
                "Apply export policies used to determine routes advertised to peers";
            leaf-list policy-name {
              type string {
                length "1..32";
              }
              max-elements 5;
            } //policy-name

          } //container export

          container import {
            description
                "Apply import policies used to determine routes accepted from peers";
            leaf-list policy-name {
              type string {
                length "1..32";
              }
              max-elements 5;
            } //policy-name

          } //container import

          container message-size {
            description
                "Set number of routes in message";
            leaf max-num-of-routes {
              type uint64 {
                range "25..255";
              }
            } //max-num-of-routes

          } //container message-size

          container metric-in {
            description
                "Set metric added to routes from neighbor";
            leaf metric {
              type uint32 {
                range "1..16";
              }
            } //metric

          } //container metric-in

          container metric-out {
            description
                "Set metric added to routes exported into RIP";
            leaf metric {
              type uint32 {
                range "1..16";
              }
            } //metric

          } //container metric-out

          container preference {
            description
                "Set the route preference";
            leaf preference {
              type uint64 {
                range "1..255";
              }
            } //preference

          } //container preference

          container receive {
            description
                "Specify type of updates accepted";
            leaf receive-type {
              type enumeration {
                enum none;
                enum both;
                enum version-1;
                enum version-2;
              }
              description
                  "both|none|version-1|version-2 - keywords";
            } //receive-type

          } //container receive

          container send {
            description
                "Specify type of message sent";
            leaf send-type {
              type enumeration {
                enum broadcast;
                enum multicast;
                enum none;
                enum version-1;
                enum unicast;
              }
            } //send-type

          } //container send

          leaf shutdown {
            type boolean;
            description
                "Administratively enable/disable the neighbor";
          }

          container split-horizon {
            description
                "Enable/disable split-horizon";
            leaf enable-disable {
              type enumeration {
                enum enable;
                enum disable;
              }
              description
                  "keywords";
            } //enable-disable

          } //container split-horizon

          container timers {
            description
                "Specify number of seconds for each timer";
            leaf update {
              type uint32 {
                range "1..600";
              }
              description
                  "[1..600] seconds";
            } //update

            leaf timeout {
              type uint32 {
                range "1..1200";
              }
              description
                  "[1..1200] seconds";
            } //timeout

            leaf flush {
              type uint32 {
                range "1..1200";
              }
              description
                  "[1..1200] seconds";
            } //flush

          } //container timers

          list unicast-address {
            key "ip-address";
            description
                "Create a unicast-address for the neighbor";
            leaf ip-address {
              type inet:ip-address;
            } //ip-address

          } //list unicast-address

        } //list neighbor

      } //list group

    } //container rip

  } //grouping alu-conf-router-rip-r13

} //module  alu-conf-router-rip-r13
