module alu-conf-lag-r13 {
  yang-version "1";

  namespace "urn:alcatel-lucent.com:sros:ns:yang:conf-lag-r13";

  prefix "conf-lag-r13";

  import alu-types {
    prefix "alu";
  }
  import ietf-yang-types {
    prefix "yang";
  }

  alu:alu-major-release "rel20";

  organization "Alcatel-Lucent";

  contact
      "Alcatel-Lucent SR OS Support 
       Web: <http://www.alcatel-lucent.com>";

  description
      "Alcatel-Lucent YANG Data model to configure ethernet LAGs on SR OS based 
       routers. 
       
       Copyright 2014-2015 Alcatel-Lucent, 2016 Nokia. All rights reserved. 
       Reproduction of this document is authorized on the condition that the 
       foregoing copyright notice is included. 
       
       This alu-conf-lag-r13 YANG module embodies Alcatel-Lucent's proprietary 
       intellectual property. Alcatel-Lucent retains all title and ownership in the 
       Specification, including any revisions. 
       
       Alcatel-Lucent grants all interested parties a non-exclusive license to use 
       and distribute an unmodified copy of this Specification in connection with 
       management of Alcatel-Lucent products, and without fee, provided this 
       copyright notice and license appear on all copies. 
       
       This Specification is supplied `as is', and Alcatel-Lucent makes no warranty, 
       either express or implied, as to the use, operation, condition, or performance 
       of the Specification.";

  revision  "2019-12-20";

  grouping alu-conf-lag-r13 {
    list lag {
      key "lag-id";
      description
          "Configure ethernet LAGs";
      leaf lag-id {
        type string;
        description
            "Attribute lag-id for lag";
      } //lag-id

      container description {
        description
            "Add/remove a text description for the link aggregation group";
        leaf long-description-string {
          type string {
            length "1..160";
          }
        } //long-description-string

      } //container description

      leaf dynamic-cost {
        type boolean;
        description
            "Enable/disable OSPF/ISIS costing of a link aggregation group";
      }

      container encap-type {
        description
            "Configure encapsulation method";
        leaf dot1q-null-qinq {
          type enumeration {
            enum dot1q;
            enum null;
            enum qinq;
          }
          description
              "keywords";
        } //dot1q-null-qinq

      } //container encap-type

      container hash-weight-threshold {
        description
            "Configure the minimum hash weight of operational links and the action to take 
             when this threshold is crossed";
        leaf weight {
          type uint32 {
            range "1..6400000";
          }
        } //weight

        leaf action {
          type enumeration {
            enum down;
            enum dynamic-cost;
            enum static-cost;
          }
        } //action

        leaf cost {
          type uint32 {
            range "1..16777215";
          }
        } //cost

      } //container hash-weight-threshold

      container hold-time {
        description
            "Configure hold-time for event reporting";
        leaf down {
          type uint32 {
            range "0..2000";
          }
          description
              "[0..2000] tenths of a second";
        } //down

      } //container hold-time

      container lacp {
        description
            "Enable/disable the LACP protocol";
        leaf mode {
          type enumeration {
            enum passive;
            enum active;
          }
          description
              "[passive|active]";
        } //mode

        leaf administrative-key {
          type uint32 {
            range "1..65535";
          }
        } //administrative-key

        leaf system-id {
          type alu:ieee-address;
          description
              "xx:xx:xx:xx:xx:xx or xx-xx-xx-xx-xx-xx";
        } //system-id

        leaf system-priority {
          type int32 {
            range "0..65535";
          }
        } //system-priority

      } //container lacp

      container lacp-mux-control {
        description
            "Configure the LACP MUX control";
        leaf lacp-mux-control-id {
          type enumeration {
            enum coupled;
            enum independent;
          }
        } //lacp-mux-control-id

      } //container lacp-mux-control

      container lacp-xmit-interval {
        description
            "Configure the timer interval for periodic transmission of LACP packets";
        leaf slow {
          type boolean;
          description
              "keyword - LACP packets are transmitted every 30 seconds";
        } //slow

        leaf fast {
          type boolean;
          description
              "keyword - LACP packets are transmitted every second";
        } //fast

      } //container lacp-xmit-interval

      leaf lacp-xmit-stdby {
        type boolean;
        description
            "Enable/disable LACP message transmission on standby links";
      }

      container mac {
        description
            "Configure a static MAC address for the link aggregation group";
        leaf ieee-address {
          type alu:ieee-address;
          description
              "xx:xx:xx:xx:xx:xx or xx-xx-xx-xx-xx-xx";
        } //ieee-address

      } //container mac

      container mode {
        description
            "Configure the mode of the link aggregation group";
        leaf access-network-hybrid {
          type enumeration {
            enum access;
            enum network;
            enum hybrid;
          }
          description
              "keywords";
        } //access-network-hybrid

      } //container mode

      container monitor-oper-group {
        description
            "Configure the operational group that affects the status of this LAG";
        leaf name {
          type string;
        } //name

      } //container monitor-oper-group

      container per-link-hash {
        description
            "Enable/Disable per link hash";
        leaf weighted {
          type boolean;
        } //weighted

        leaf auto-rebalance {
          type boolean;
        } //auto-rebalance

      } //container per-link-hash

      container port {
        description
            "Add/remove ports from a link aggregation group";
        leaf-list port-id {
          type string;
          max-elements 16;
          description
              "Attribute port-id for port";
        } //port-id

        leaf priority {
          type uint32 {
            range "1..65535";
          }
        } //priority

        leaf sub-group {
          type enumeration {
            enum 1;
            enum 2;
            enum 3;
            enum 4;
            enum 5;
            enum 6;
            enum 7;
            enum 8;
            enum auto-iom;
            enum auto-mda;
          }
          description
              "Attribute sub-group-id for port";
        } //sub-group

        leaf hash-weight {
          type string {
          }
          description
              "[1..100000] | port-speed";
        } //hash-weight

      } //container port

      container port-threshold {
        description
            "Configure the behavior for the LAG if the number of operational links is equal 
             to or below a threshold level";
        leaf value {
          type string;
          description
              "Attribute value for port-threshold";
        } //value

        leaf action {
          type enumeration {
            enum down;
            enum dynamic-cost;
            enum static-cost;
          }
        } //action

        leaf cost {
          type uint32 {
            range "1..16777215";
          }
        } //cost

      } //container port-threshold

      container port-type {
        description
            "Specify the port type for the link aggregation group";
        leaf lag-port-type {
          type enumeration {
            enum standard;
            enum hsmda;
            enum hs;
          }
        } //lag-port-type

      } //container port-type

      container port-weight-speed {
        description
            "Configure the speed corresponding to a port weight unit";
        leaf gbps {
          type enumeration {
            enum 1;
            enum 10;
          }
        } //gbps

      } //container port-weight-speed

      container selection-criteria {
        description
            "Configure selection criteria to select the active LACP sub-group";
        leaf best-port-highest-count-highest-weight {
          type enumeration {
            enum best-port;
            enum highest-count;
            enum highest-weight;
          }
          description
              "keywords";
        } //best-port-highest-count-highest-weight

        leaf slave-to-partner {
          type boolean;
        } //slave-to-partner

        leaf subgroup-hold-time {
          type string {
          }
          description
              "[0..2000] tenths of a second | infinite";
        } //subgroup-hold-time

      } //container selection-criteria

      leaf shutdown {
        type boolean;
        description
            "Shutdown the LAG port";
      }

      container standby-signaling {
        description
            "Configure how the state of a port is signalled to the remote side";
        leaf standby-signaling-id {
          type enumeration {
            enum lacp;
            enum power-off;
          }
        } //standby-signaling-id

      } //container standby-signaling

      container weight-threshold {
        description
            "Configure the minimum weight of operational links and the action to take when 
             this threshold is crossed";
        leaf value {
          type string;
          description
              "Attribute value for weight-threshold";
        } //value

        leaf action {
          type enumeration {
            enum down;
            enum dynamic-cost;
            enum static-cost;
          }
        } //action

        leaf cost {
          type uint32 {
            range "1..16777215";
          }
        } //cost

      } //container weight-threshold

      container access {
        description
            "Configure access params";
        container adapt-qos {
          description
              "Configure Qos Adaptation";
          leaf adapt-qos-id {
            type enumeration {
              enum link;
              enum distribute;
              enum port-fair;
            }
          } //adapt-qos-id

          leaf include-egr-hash-cfg {
            type boolean;
          } //include-egr-hash-cfg

        } //container adapt-qos

        container bandwidth {
          description
              "Configure Access Bandwidth";
          leaf bandwidth-in-kbps {
            type string;
            description
                "[1..6400000000]";
          } //bandwidth-in-kbps

        } //container bandwidth

        container booking-factor {
          description
              "Configure Booking Factor";
          leaf percent-of-LAG-bandwidth {
            type uint16 {
              range "1..1000";
            }
          } //percent-of-LAG-bandwidth

        } //container booking-factor

        leaf per-fp-egr-queuing {
          type boolean;
          description
              "Configure Per FP Egress Queuing";
        }

        leaf per-fp-ing-queuing {
          type boolean;
          description
              "Configure Per FP Ingress Queuing";
        }

        leaf per-fp-sap-instance {
          type boolean;
          description
              "Configure Per FP SAP Instance";
        }

      } //container access

      container bfd {
        description
            "Configure BFD params";
        leaf disable-soft-reset-extension {
          type boolean;
          description
              "Disable/enable extension of BFD timers during soft reset";
        }

        container family {
          description
              "Configure BFD for an address family";
          leaf family-id {
            type enumeration {
              enum ipv4;
              enum ipv6;
            }
          } //family-id

          leaf bfd-on-distributing-only {
            type boolean;
            description
                "Enable/disable restricting micro-BFD sessions to links in LACP state 
                 distributing";
          }

          container local-ip-address {
            description
                "Configure the BFD source address";
            leaf ip-address {
              type string;
              description
                  "Attribute ip-address for local-ip-address";
            } //ip-address

          } //container local-ip-address

          container max-admin-down-time {
            description
                "Configure the maximum time (s) to behave as if the micro-BFD session were Up 
                 while the remote end already signalled it is AdminDown";
            leaf max-admin-down-time-id {
              type int32 {
                range "-1..3600";
              }
            } //max-admin-down-time-id

            leaf infinite {
              type boolean;
            } //infinite

          } //container max-admin-down-time

          container max-setup-time {
            description
                "Configure the maximum time (ms) to behave as if the micro-BFD session were Up 
                 while it is actually still being set up";
            leaf max-setup-time-id {
              type int32 {
                range "-1..60000";
              }
            } //max-setup-time-id

            leaf infinite {
              type boolean;
            } //infinite

          } //container max-setup-time

          container multiplier {
            description
                "Configure the number of BFD messages to be missed before the micro-BFD session 
                 goes down";
            leaf multiplier-id {
              type uint32 {
                range "3..20";
              }
            } //multiplier-id

          } //container multiplier

          container receive-interval {
            description
                "Configure the receive timer in milliseconds";
            leaf interval {
              type uint32 {
                range "10..100000";
              }
            } //interval

          } //container receive-interval

          container remote-ip-address {
            description
                "Configure the destination IP address";
            leaf remote-ip-address-string {
              type string;
              description
                  "ip-address";
            } //remote-ip-address-string

          } //container remote-ip-address

          leaf shutdown {
            type boolean;
            description
                "Disable/enable micro BFD sessions for this address family";
          }

          container transmit-interval {
            description
                "Configure the transmit timer in milliseconds";
            leaf interval {
              type uint32 {
                range "10..100000";
              }
            } //interval

          } //container transmit-interval

        } //container family

      } //container bfd

      container eth-cfm {
        description
            "Configure CFM parameters";
        list mep {
          key "mep-id domain association vlan";
          description
              "Configure a CFM Facility Maintenance Endpoint";
          leaf mep-id {
            type int16 {
              range "1..8191";
            }
          } //mep-id

          leaf domain {
            type uint32 {
              range "1..4294967295";
            }
          } //domain

          leaf association {
            type uint32 {
              range "1..4294967295";
            }
          } //association

          leaf vlan {
            type uint32 {
              range "1..4094";
            }
          } //vlan

          leaf ccm-enable {
            type boolean;
            description
                "Enable/Disable Generation of CCM messages";
          }

          container ccm-ltm-priority {
            description
                "Configure the priority of CCM and LTM messages";
            leaf priority {
              type uint16 {
                range "0..7";
              }
              description
                  "[0..7] - Default highest priority for CCMs and LTMs transmitted by the MEP";
            } //priority

          } //container ccm-ltm-priority

          container ccm-padding-size {
            description
                "Insert additional padding in the CCM packets";
            leaf ccm-padding {
              type uint32 {
                range "3..1500";
              }
              description
                  "3..1500 octets";
            } //ccm-padding

          } //container ccm-padding-size

          container ccm-tlv-ignore {
            description
                "Enable/Disable processing of received CCM TLVs";
            leaf port-status {
              type boolean;
            } //port-status

            leaf interface-status {
              type boolean;
            } //interface-status

          } //container ccm-tlv-ignore

          leaf collect-lmm-stats {
            type boolean;
            description
                "Enable/Disable the collection of statistics for OAM-PM Loss Measurement 
                 Message (LMM) tests";
          }

          container description {
            description
                "Add/remove a text description for the MEP";
            leaf description-string {
              type string {
              }
              description
                  "[80 chars max]";
            } //description-string

          } //container description

          leaf facility-fault {
            type boolean;
            description
                "Enable/Disable reactions to fault conditions on a facility MEP";
          }

          container low-priority-defect {
            description
                "Configure the Lowest Priority Defect for the MEP";
            leaf allDef-macRemErrXcon-remErrXcon-errXcon-xcon-noXcon {
              type enumeration {
                enum allDef;
                enum macRemErrXcon;
                enum remErrXcon;
                enum errXcon;
                enum xcon;
                enum noXcon;
              }
              description
                  "keywords";
            } //allDef-macRemErrXcon-remErrXcon-errXcon-xcon-noXcon

          } //container low-priority-defect

          container mac-address {
            description
                "Configure the MAC Address for the MEP";
            leaf mac-address {
              type yang:mac-address;
            } //mac-address

          } //container mac-address

          container one-way-delay-threshold {
            description
                "Configure the one-way-delay test threshold";
            leaf seconds {
              type uint32 {
                range "0..600";
              }
              default 3;
              description
                  "[0..600] Default: 3";
            } //seconds

          } //container one-way-delay-threshold

          leaf shutdown {
            type boolean;
            description
                "Administratively enable/disable the MEP";
          }

          container ais-enable {
            presence
                "Configure the generation and reception of Alarm Indication Signal (AIS) 
                 message parameters";
            container client-meg-level {
              description
                  "Configure the client meg level";
              leaf t1 {
                type boolean;
                description
                    "[1..7]";
              } //t1

              leaf t2 {
                type boolean;
              } //t2

              leaf t3 {
                type boolean;
              } //t3

              leaf t4 {
                type boolean;
              } //t4

              leaf t5 {
                type boolean;
              } //t5

              leaf t6 {
                type boolean;
              } //t6

              leaf t7 {
                type boolean;
              } //t7

            } //container client-meg-level

            leaf interface-support-enable {
              type boolean;
              description
                  "Enable/disable the generation of AIS PDUs based on the associated endpoint 
                   state";
            }

            container interval {
              description
                  "Configure the transmission interval of AIS messages";
              leaf t1-60 {
                type enumeration {
                  enum 1;
                  enum 60;
                }
                default 1;
                description
                    "seconds - Default: 1";
              } //t1-60

            } //container interval

            container low-priority-defect {
              description
                  "Configure the Lowest Priority Defect for the MEP AIS generation";
              leaf allDef-macRemErrXcon {
                type enumeration {
                  enum allDef;
                  enum macRemErrXcon;
                }
                description
                    "keywords";
              } //allDef-macRemErrXcon

            } //container low-priority-defect

            container priority {
              description
                  "Configure the priority of AIS messages originated by the node";
              leaf priority-value {
                type uint32 {
                  range "0..7";
                }
                default 7;
                description
                    "[0..7] - Default: 7";
              } //priority-value

            } //container priority

          } //container ais-enable

          container alarm-notification {
            description
                "Configure the MEP alarm notification parameters";
            container fng-alarm-time {
              description
                  "Configure the Fault Notification Generation (FNG) alarm time";
              leaf time {
                type enumeration {
                  enum 0;
                  enum 250;
                  enum 500;
                  enum 1000;
                }
                default 0;
                description
                    "[0,250,500,1000] centi-seconds - Default: 0";
              } //time

            } //container fng-alarm-time

            container fng-reset-time {
              description
                  "Configure the Fault Notification Generation (FNG) reset time";
              leaf time {
                type enumeration {
                  enum 0;
                  enum 250;
                  enum 500;
                  enum 1000;
                }
                default 0;
                description
                    "[0,250,500,1000] centi-seconds - Default: 0";
              } //time

            } //container fng-reset-time

          } //container alarm-notification

          container csf-enable {
            presence
                "Configure the reception of Client Signal Fail (CSF) message parameters";
            container multiplier {
              description
                  "Configure the multiplier used for timing out CSF";
              leaf multiplier-value {
                type string;
                description
                    "[0.0|2.0 .. 30.0] - Default: 3.5";
              } //multiplier-value

            } //container multiplier

          } //container csf-enable

          container eth-test-enable {
            presence
                "Enable/Disable eth-test functionality on MEP";
            container bit-error-threshold {
              description
                  "Configure the bit error trap threshold";
              leaf bit-errors {
                type uint32 {
                  range "0..11840";
                }
                default 1;
                description
                    "[0..11840] Default: 1";
              } //bit-errors

            } //container bit-error-threshold

            container test-pattern {
              description
                  "Configure the test pattern for eth-test frames";
              leaf all-zeros-all-ones {
                type enumeration {
                  enum all-zeros;
                  enum all-ones;
                }
                default "all-zeros";
                description
                    "keywords - Test pattern - default: all-zeros";
              } //all-zeros-all-ones

              leaf crc-enable {
                type boolean;
                description
                    "keyword - Generate CRC checksum";
              } //crc-enable

            } //container test-pattern

          } //container eth-test-enable

          container grace {
            description
                "Configure the generation and reception of grace period parameters";
            container eth-ed {
              description
                  "Configure the generation and reception of eth-ed grace period parameters";
              container max-rx-defect-window {
                description
                    "Configure/Disable an upper maximum defect window length; when disabled the 
                     advertised value from the peer will be used; when enabled the lower of the 
                     configured value or the advertised value from the peer will be used";
                leaf seconds {
                  type uint32 {
                    range "1..86400";
                  }
                  description
                      "[1..86400] - Default: no max-rx-defect-window";
                } //seconds

              } //container max-rx-defect-window

              container priority {
                description
                    "Configure/Disable the transmission priority value for ETH-ED PDUs; when 
                     disabled the priority value of ccm-ltm-priority associated with this MEP will 
                     be used";
                leaf priority {
                  type int32 {
                    range "0..7";
                  }
                  default 0;
                  description
                      "[0..7] - Default: no priority";
                } //priority

              } //container priority

              leaf rx-eth-ed {
                type boolean;
                description
                    "Enable/Disable the receiving and processing of ETH-ED PDUs";
              }

              leaf tx-eth-ed {
                type boolean;
                description
                    "Enable/Disable the transmission of ETH-ED PDUs";
              }

            } //container eth-ed

            container eth-vsm-grace {
              description
                  "Configure the generation and reception of sros vendor specific message (vsm) 
                   grace period parameters";
              leaf rx-eth-vsm-grace {
                type boolean;
                description
                    "Enable/Disable the receiving and processing of vendor specific message (vsm) 
                     grace period notifications";
              }

              leaf tx-eth-vsm-grace {
                type boolean;
                description
                    "Enable/Disable the transmission of vsm grace period notifications";
              }

            } //container eth-vsm-grace

          } //container grace

        } //list mep

      } //container eth-cfm

      list link-map-profile {
        key "link-map-profile-id";
        description
            "Configure LAG link map profile information";
        leaf link-map-profile-id {
          type string;
          description
              "Attribute link-map-profile-id for link-map-profile";
        } //link-map-profile-id

        container description {
          description
              "Configure link map profile description";
          leaf description-string {
            type string {
              length "1..80";
            }
          } //description-string

        } //container description

        container failure-mode {
          description
              "Configure link map profile failure mode";
          leaf mode {
            type enumeration {
              enum per-link-hash;
              enum discard;
            }
          } //mode

        } //container failure-mode

        list link {
          key "port-id";
          description
              "Configure associated links";
          leaf port-id {
            type string {
              length "1..17";
            }
            description
                "Attribute port-id for link";
          } //port-id

          leaf link-id {
            type enumeration {
              enum primary;
              enum secondary;
            }
          } //link-id

        } //list link

      } //list link-map-profile

    } //list lag

  } //grouping alu-conf-lag-r13

} //module  alu-conf-lag-r13
