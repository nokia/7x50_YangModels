submodule nokia-state-port-eth-egress {

    yang-version "1.1";

    belongs-to nokia-state { prefix "state"; }

    import ietf-yang-types                { prefix "yang"; }
    import nokia-sros-yang-extensions     { prefix "sros-ext"; }
    import nokia-types-sros               { prefix "types-sros"; }


    sros-ext:sros-major-release "rel20";

    organization "Nokia";

    contact
        "Nokia SR OS Support
         Web: <http://www.nokia.com>";

    description
        "Nokia YANG Data model with operational state for egress capabilities for ethernet ports on SR OS based routers.

         Copyright 2016 Nokia. All rights reserved. Reproduction of this document
         is authorized on the condition that the foregoing copyright notice is included.

         This nokia-state-port-eth-egress YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";

    revision "2020-01-24";

    grouping state-port-eth-egress {
        container egress {
            description "Enter the egress context";

            list expanded-secondary-shaper {
                key "secondary-shaper-name";
                description "Enter the expanded-secondary-shaper list instance";

                leaf secondary-shaper-name {
                    type types-sros:named-item;
                    description "Name for the expanded secondary shaper";
                }

                container aggregate-burst {
                    description "Enter the aggregate-burst context";

                    container statistics {
                        description
                            "The container of egress expanded secondary shaper aggregate
                             statistics for all classes.";

                        leaf forwarded-octets {
                            type yang:counter64;
                            description "Indicates the number of octets forwarded.";
                        }

                        leaf forwarded-packets {
                            type yang:counter64;
                            description "Indicates the number of packets forwarded.";
                        }

                        leaf monitor-over-threshold {
                            type yang:counter64;
                            description "indicates the number of octets above the configured monitor-threshold.";
                        }

                    } // container statistics

                } // container aggregate-burst

                list class {
                    key "class-number";
                    description "Enter the class list instance";

                    leaf class-number {
                        type uint32 {
                            range "1..8";
                        }
                        description "Unique value of the class";
                    }

                    container statistics {
                        description
                            "The container of egress expanded secondary shaper class
                             statistics for Ethernet ports.";

                        leaf forwarded-octets {
                            type yang:counter64;
                            description "Indicates the number of octets forwarded.";
                        }

                        leaf forwarded-packets {
                            type yang:counter64;
                            description "Indicates the number of packets forwarded.";
                        }

                        leaf monitor-over-threshold {
                            type yang:counter64;
                            description "indicates the number of octets above the configured monitor-threshold.";
                        }

                    } // container statistics

                } // list class

            } // list expanded-secondary-shaper

            list hs-secondary-shaper {
                key "secondary-shaper-name";
                description "Enter the hs-secondary-shaper list instance";

                leaf secondary-shaper-name {
                    type types-sros:named-item;
                    description "Specifies the expanded secondary shaper name on the egress side.";
                }

                container aggregate {
                    description "Enter the aggregate context";

                    container statistics {
                        description
                            "The container of egress High Scale secondary shaper aggregate
                             statistics for all classes of this egress HS secondary shaper.";

                        leaf forwarded-octets {
                            type yang:counter64;
                            description "Indicates the number of octets forwarded.";
                        }

                        leaf forwarded-packets {
                            type yang:counter64;
                            description "Indicates the number of packets forwarded.";
                        }

                    } // container statistics

                } // container aggregate

                list class {
                    key "class-number";
                    description "Enter the class list instance";

                    leaf class-number {
                        type uint32 {
                            range "1..6";
                        }
                        description "The unique value of the class.";
                    }

                    container statistics {
                        description
                            "The container of egress High Scale secondary shaper class
                             statistics for Ethernet ports";

                        leaf forwarded-octets {
                            type yang:counter64;
                            description "Indicates the number of octets forwarded.";
                        }

                        leaf forwarded-packets {
                            type yang:counter64;
                            description "Indicates the number of packets forwarded.";
                        }

                    } // container statistics

                } // list class

            } // list hs-secondary-shaper

        } // container egress

    } // grouping state-port-eth-egress

}
