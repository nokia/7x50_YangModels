module nokia-types-ppp {

    yang-version "1.1";

    namespace "urn:nokia.com:sros:ns:yang:sr:types-ppp";

    prefix "types-ppp";

    import ietf-yang-types                { prefix "yang"; }
    import nokia-sros-yang-extensions     { prefix "sros-ext"; }
    import nokia-types-sros               { prefix "types-sros"; }


    sros-ext:sros-major-release "rel20";

    organization "Nokia";

    contact
        "Nokia SR OS Support
         Web: <http://www.nokia.com>";

    description
        "Common PPP data types used in the SR OS management system.

         Copyright 2016 Nokia. All rights reserved. Reproduction of this document
         is authorized on the condition that the foregoing copyright notice is included.

         This nokia-types-ppp YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";

    revision "2018-07-14";

    typedef session-type {
        type enumeration {
            enum "over-ethernet"                { value 1; }
            enum "over-ethernet-over-atm"       { value 2; }
            enum "over-atm"                     { value 3; }
            enum "over-l2tp"                    { value 4; }
        }
        description "The PPP session type";
    }

    typedef mlppp-ip-endpoint {
        type union {
            type types-sros:ipv4-address;
            type enumeration {
                enum "system"                       { value 2; }
            }
        }
        description "The MLPPP endpoint ID as IP address";
    }

    typedef mlppp-mac-endpoint {
        type union {
            type yang:mac-address;
            type enumeration {
                enum "system"                       { value 2; }
            }
        }
        description "The MLPPP endpoint ID as MAC address";
    }

    typedef mlppp-endpoint-class {
        type enumeration {
            enum "null"                         { value 0; }
            enum "local"                        { value 1; }
            enum "ipv4-address"                 { value 2; }
            enum "mac-address"                  { value 3; }
            enum "magic-number"                 { value 4; }
            enum "directory-number"             { value 5; }
        }
        description "The MLPPP endpoint class";
    }

    typedef ppp-control-protocol-state {
        type enumeration {
            enum "starting"                     { value 2; }
            enum "closed"                       { value 3; }
            enum "stopped"                      { value 4; }
            enum "closing"                      { value 5; }
            enum "stopping"                     { value 6; }
            enum "request-sent"                 { value 7; }
            enum "ack-received"                 { value 8; }
            enum "ack-sent"                     { value 9; }
            enum "opened"                       { value 10; }
        }
        description "The state of a PPP control protocol";
    }

    typedef authentication-protocol {
        type enumeration {
            enum "pap"                          { value 2; }
            enum "chap"                         { value 3; }
        }
        description "The authentication protocol";
    }

    typedef user-name {
        type string {
            length "1..253";
        }
        description "The user name used in PPP.";
    }

}
