submodule nokia-state-system-security-cpm {

    yang-version "1.1";

    belongs-to nokia-state { prefix "state"; }

    import nokia-sros-yang-extensions     { prefix "sros-ext"; }
    import nokia-types-system             { prefix "types-system"; }


    sros-ext:sros-major-release "rel20";

    organization "Nokia";

    contact
        "Nokia SR OS Support
         Web: <http://www.nokia.com>";

    description
        "Nokia YANG Data model with operational state for System security cpm-filter and cpm-queue configuration. on SR OS based routers.

         Copyright 2016 Nokia. All rights reserved. Reproduction of this document
         is authorized on the condition that the foregoing copyright notice is included.

         This nokia-state-system-security-cpm YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";

    revision "2019-10-18";

    grouping state-system-security-cpm-cpm-filter {
        container cpm-filter {
            description "Enter the cpm-filter context";

            container ip-filter {
                description "Enter the ip-filter context";

                list entry {
                    key "entry-id";
                    description "Enter the entry list instance";

                    leaf entry-id {
                        type uint32 {
                            range "1..131072";
                        }
                        description "The id used to uniquely identify this filter entry.";
                    }

                    container statistics {
                        description "Filter entry statistics.";

                        leaf dropped-packets {
                            type uint64;
                            description "The number of packets dropped.";
                        }

                        leaf forwarded-packets {
                            type uint64;
                            description "The number of packets forwarded.";
                        }

                    } // container statistics

                } // list entry

            } // container ip-filter

            container ipv6-filter {
                description "Enter the ipv6-filter context";

                list entry {
                    key "entry-id";
                    description "Enter the entry list instance";

                    leaf entry-id {
                        type uint32 {
                            range "1..131072";
                        }
                        description "The id used to uniquely identify this filter entry.";
                    }

                    container statistics {
                        description "Filter entry statistics.";

                        leaf dropped-packets {
                            type uint64;
                            description "The number of packets dropped.";
                        }

                        leaf forwarded-packets {
                            type uint64;
                            description "The number of packets forwarded.";
                        }

                    } // container statistics

                } // list entry

            } // container ipv6-filter

            container mac-filter {
                description "Enter the mac-filter context";

                list entry {
                    key "entry-id";
                    description "Enter the entry list instance";

                    leaf entry-id {
                        type uint32 {
                            range "1..131072";
                        }
                        description "The id used to uniquely identify this filter entry.";
                    }

                    container statistics {
                        description "Filter entry statistics.";

                        leaf dropped-packets {
                            type uint64;
                            description "The number of packets dropped.";
                        }

                        leaf forwarded-packets {
                            type uint64;
                            description "The number of packets forwarded.";
                        }

                    } // container statistics

                } // list entry

            } // container mac-filter

        } // container cpm-filter

    } // grouping state-system-security-cpm-cpm-filter

    grouping state-system-security-cpm-cpm-queue {
        container cpm-queue {
            description "Enter the cpm-queue context";

            list queue {
                key "queue-id";
                description "Enter the queue list instance";

                leaf queue-id {
                    type uint32 {
                        range "33..2000";
                    }
                    description "Unique identifier of a CPM queue";
                }

                leaf references {
                    type uint32;
                    description
                        "Indicates the count of filter entries using this particular queue to forward
                         traffic to the main CPU.";
                }

                leaf oper-pir {
                    type types-system:pir-rate;
                    units "kilobps";
                    description "Indicates the operational value of the Peak Information Rate associated with this queue.";
                }

                leaf oper-cir {
                    type types-system:cir-rate;
                    units "kilobps";
                    description "Indicates the operational value of the Committed Information Rate associated with this queue.";
                }

                container statistics {
                    description "Queue statistics.";

                    leaf in-prof-drop-pkts {
                        type uint64;
                        description "The number of packets complying to the queue QoS profile dropped.";
                    }

                    leaf in-prof-fwd-pkts {
                        type uint64;
                        description "The number of packets complying to the queue QoS profile forwarded.";
                    }

                    leaf in-prof-drop-octets {
                        type uint64;
                        description "The number of octets complying to the queue QoS profile dropped.";
                    }

                    leaf in-prof-fwd-octets {
                        type uint64;
                        description "The number of octets complying to the queue QoS profile forwarded.";
                    }

                    leaf out-prof-drop-pkts {
                        type uint64;
                        description "The number of packets not complying to the queue QoS profile dropped.";
                    }

                    leaf out-prof-fwd-pkts {
                        type uint64;
                        description "The number of packets not complying to the queue QoS profile forwarded.";
                    }

                    leaf out-prof-drop-octets {
                        type uint64;
                        description "The number of octets not complying to the queue QoS profile dropped.";
                    }

                    leaf out-prof-fwd-octets {
                        type uint64;
                        description "The number of octets not complying to the queue QoS profile forwarded.";
                    }

                } // container statistics

            } // list queue

        } // container cpm-queue

    } // grouping state-system-security-cpm-cpm-queue

}
