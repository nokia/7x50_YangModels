submodule nokia-conf-submgt-isa-policer {

    yang-version "1.1";

    belongs-to nokia-conf { prefix "conf"; }

    import nokia-sros-yang-extensions     { prefix "sros-ext"; }
    import nokia-types-qos                { prefix "types-qos"; }
    import nokia-types-sros               { prefix "types-sros"; }

    include nokia-conf-groups;

    sros-ext:sros-major-release "rel20";

    organization "Nokia";

    contact
        "Nokia SR OS Support
         Web: <http://www.nokia.com>";

    description
        "Nokia YANG Data model to configure subscriber management isa policer on SR OS based routers.

         Copyright 2016 Nokia. All rights reserved. Reproduction of this document
         is authorized on the condition that the foregoing copyright notice is included.

         This nokia-conf-submgt-isa-policer YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";

    revision "2019-04-16";

    grouping conf-submgt-isa-policer {
        list isa-policer {
            key "name";
            max-elements 128;
            description "Enter the isa-policer list instance";

            leaf name {
                type types-sros:named-item {
                    pattern "[^_].*" {
                        error-message "Identifiers starting with '_' are reserved for internal use";
                    }
                }
                description "ISA policer name";
            }

            leaf description {
                type types-sros:description;
                description "Text description";
            }

            leaf type {
                type enumeration {
                    enum "single-bucket-bandwidth"      { value 0; description "Police traffic using a single bucket"; }
                    enum "dual-bucket-bandwidth"        { value 1; description "Police traffic using dual buckets"; }
                }
                sros-ext:immutable;
                default "single-bucket-bandwidth";
                description "Policing technique";
            }

            leaf action {
                type enumeration {
                    enum "permit-deny"                  { value 0; description "Permit or deny packets based on policer outcome"; }
                    enum "priority-mark"                { value 1; description "Mark packets as in or out of profile based on policer outcome"; }
                }
                default "permit-deny";
                description "Action to be taken for packets that are in-profile and out-of-profile";
            }

            leaf cbs {
                type types-qos:kilobytes {
                    range "0..131071";
                }
                default "0";
                description "Committed burst size";
            }

            leaf mbs {
                type types-qos:kilobytes {
                    range "0..131071";
                }
                default "0";
                description "Maximum Burst Size";
            }

            leaf-list apply-groups {
                type leafref {
                    path "../../../groups/group/name";
                }
                max-elements 8;
                ordered-by user;
                description "Apply a configuration group at this level";
            }

            container adaptation-rule {
                description "Enter the adaptation-rule context";

                leaf pir {
                    type types-qos:adaptation-rule;
                    default "closest";
                    description "Peak Information Rate";
                }

                leaf cir {
                    type types-qos:adaptation-rule;
                    default "closest";
                    description "Committed information rate";
                }

            } // container adaptation-rule

            container rate {
                description "Enter the rate context";

                leaf pir {
                    type types-qos:isa-policer-pir-rate;
                    default "max";
                    description "Peak Information Rate";
                }

                leaf cir {
                    type types-qos:isa-policer-cir-rate;
                    default "0";
                    description "Committed information rate";
                }

            } // container rate

        } // list isa-policer

    } // grouping conf-submgt-isa-policer

}
