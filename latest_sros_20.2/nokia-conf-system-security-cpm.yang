submodule nokia-conf-system-security-cpm {

    yang-version "1.1";

    belongs-to nokia-conf { prefix "conf"; }

    import ietf-yang-types                { prefix "yang"; }
    import nokia-sros-yang-extensions     { prefix "sros-ext"; }
    import nokia-types-filter             { prefix "types-filter"; }
    import nokia-types-qos                { prefix "types-qos"; }
    import nokia-types-security           { prefix "types-security"; }
    import nokia-types-services           { prefix "types-services"; }
    import nokia-types-sros               { prefix "types-sros"; }
    import nokia-types-system             { prefix "types-system"; }

    include nokia-conf-filter;
    include nokia-conf-groups;
    include nokia-conf-service;
    include nokia-conf-svc-vpls;

    sros-ext:sros-major-release "rel20";

    organization "Nokia";

    contact
        "Nokia SR OS Support
         Web: <http://www.nokia.com>";

    description
        "Nokia YANG Data model to configure System security cpm-filter and cpm-queue configuration. on SR OS based routers.

         Copyright 2016 Nokia. All rights reserved. Reproduction of this document
         is authorized on the condition that the foregoing copyright notice is included.

         This nokia-conf-system-security-cpm YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";

    revision "2019-10-18";

    grouping conf-system-security-cpm-cpm-filter {
        container cpm-filter {
            description "Enter the cpm-filter context";

            leaf default-action {
                type enumeration {
                    enum "drop"                         { value 1; }
                    enum "accept"                       { value 2; }
                }
                default "accept";
                description "Action for packets that do not match any filter entries";
            }

            leaf-list apply-groups {
                type leafref {
                    path "../../../../groups/group/name";
                }
                max-elements 8;
                ordered-by user;
                description "Apply a configuration group at this level";
            }

            container ip-filter {
                description "Enter the ip-filter context";

                leaf admin-state {
                    type types-sros:admin-state;
                    default "disable";
                    description "Administrative state of this CPM filter";
                }

                list entry {
                    key "entry-id";
                    description "Enter the entry list instance";

                    leaf entry-id {
                        type uint32 {
                            range "1..131072";
                        }
                        description "The id used to uniquely identify this filter entry.";
                    }

                    leaf description {
                        type types-sros:description;
                        description "Text description";
                    }

                    leaf log {
                        type leafref {
                            path "../../../../../../filter/log/log-id";
                        }
                        description "Log that is used for packets matching this entry";
                    }

                    leaf-list apply-groups {
                        type leafref {
                            path "../../../../../../groups/group/name";
                        }
                        max-elements 8;
                        ordered-by user;
                        description "Apply a configuration group at this level";
                    }

                    container match {
                        description "Enter the match context";

                        leaf router-instance {
                            type types-sros:named-item-64;
                            description "Specifies router instance to be matched.";
                        }

                        leaf protocol {
                            type types-sros:ipv4-match-protocol;
                            description "Specifies the IP protocol to match. It can be set to -1 to disable matching cpm protocol.";
                        }

                        leaf dscp {
                            type types-qos:dscp-name;
                            description "Specifies the DSCP to be matched on the packet.";
                        }

                        leaf fragment {
                            type enumeration {
                                enum "false"                        { value 2; }
                                enum "true"                         { value 3; }
                            }
                            description "Match criterion based on fragmentation presence/absence";
                        }

                        leaf multiple-option {
                            type boolean;
                            description "Specifies whether multiple options are to be matched.";
                        }

                        leaf option-present {
                            type boolean;
                            description "Specifies whether IP options matching is enabled.";
                        }

                        choice port-selector {
                            case src-dst-port {

                                container src-port {
                                    description "Enter the src-port context";

                                    choice port {
                                        case eq {

                                            leaf eq {
                                                type uint16 {
                                                    range "0..65535";
                                                }
                                                description "Port to match";
                                            }

                                            leaf mask {
                                                type uint16 {
                                                    range "1..65535";
                                                }
                                                default "65535";
                                                description "Mask to apply when matching the port";
                                            }

                                        }
                                        case range {

                                            container range {
                                                presence "Enables port range matching.";
                                                description "Enter the range context";

                                                leaf start {
                                                    type uint16 {
                                                        range "0..65535";
                                                    }
                                                    mandatory true;
                                                    description "Lower bound port to match";
                                                }

                                                leaf end {
                                                    type uint16 {
                                                        range "0..65535";
                                                    }
                                                    mandatory true;
                                                    description "Lower bound port to match";
                                                }

                                            } // container range

                                        }
                                        case port-list {

                                            leaf port-list {
                                                type leafref {
                                                    path "../../../../../../../../filter/match-list/port-list/port-list-name";
                                                }
                                                description "Parameter port list as match criterion";
                                            }

                                        }
                                    }
                                } // container src-port

                                container dst-port {
                                    description "Enter the dst-port context";

                                    choice port {
                                        case eq {

                                            leaf eq {
                                                type uint16 {
                                                    range "0..65535";
                                                }
                                                description "Port to match";
                                            }

                                            leaf mask {
                                                type uint16 {
                                                    range "1..65535";
                                                }
                                                default "65535";
                                                description "Mask to apply when matching the port";
                                            }

                                        }
                                        case range {

                                            container range {
                                                presence "Enables port range matching.";
                                                description "Enter the range context";

                                                leaf start {
                                                    type uint16 {
                                                        range "0..65535";
                                                    }
                                                    mandatory true;
                                                    description "Lower bound port to match";
                                                }

                                                leaf end {
                                                    type uint16 {
                                                        range "0..65535";
                                                    }
                                                    mandatory true;
                                                    description "Lower bound port to match";
                                                }

                                            } // container range

                                        }
                                        case port-list {

                                            leaf port-list {
                                                type leafref {
                                                    path "../../../../../../../../filter/match-list/port-list/port-list-name";
                                                }
                                                description "Parameter port list as match criterion";
                                            }

                                        }
                                    }
                                } // container dst-port

                            }
                            case port {

                                container port {
                                    description "Enter the port context";

                                    choice port {
                                        case eq {

                                            leaf eq {
                                                type uint16 {
                                                    range "0..65535";
                                                }
                                                description "Port to match";
                                            }

                                            leaf mask {
                                                type uint16 {
                                                    range "1..65535";
                                                }
                                                default "65535";
                                                description "Mask to apply when matching the port";
                                            }

                                        }
                                        case range {

                                            container range {
                                                presence "Enables port range matching.";
                                                description "Enter the range context";

                                                leaf start {
                                                    type uint16 {
                                                        range "0..65535";
                                                    }
                                                    mandatory true;
                                                    description "Lower bound port to match";
                                                }

                                                leaf end {
                                                    type uint16 {
                                                        range "0..65535";
                                                    }
                                                    mandatory true;
                                                    description "Lower bound port to match";
                                                }

                                            } // container range

                                        }
                                        case port-list {

                                            leaf port-list {
                                                type leafref {
                                                    path "../../../../../../../../filter/match-list/port-list/port-list-name";
                                                }
                                                description "Parameter port list as match criterion";
                                            }

                                        }
                                    }
                                } // container port

                            }
                        }
                        container ip-option {
                            presence "Enables IP option criteria matching.";
                            description "Enter the ip-option context";

                            leaf type {
                                type types-filter:filter-match-ip-option;
                                mandatory true;
                                description "Specific IP option to match";
                            }

                            leaf mask {
                                type types-filter:filter-match-ip-option {
                                    range "1..255";
                                }
                                default "255";
                                description "Mask that is ANDed with ip-option value in the packet header";
                            }

                        } // container ip-option

                        container src-ip {
                            description "Enter the src-ip context";

                            choice match-address-choice {
                                case address-and-prefix-or-mask {

                                    leaf address {
                                        type union {
                                            type types-sros:ipv4-address;
                                            type types-sros:ipv4-prefix-with-host-bits;
                                        }
                                        description "IP address to match";
                                    }

                                    leaf mask {
                                        type types-sros:ipv4-address;
                                        description "Mask as an AND to the IP address";
                                    }

                                }
                                case ip-prefix-list {

                                    leaf ip-prefix-list {
                                        type leafref {
                                            path "../../../../../../../../filter/match-list/ip-prefix-list/prefix-list-name";
                                        }
                                        description "IP prefix list as match criterion for IP address";
                                    }

                                }
                            }
                        } // container src-ip

                        container dst-ip {
                            description "Enter the dst-ip context";

                            choice match-address-choice {
                                case address-and-prefix-or-mask {

                                    leaf address {
                                        type union {
                                            type types-sros:ipv4-address;
                                            type types-sros:ipv4-prefix-with-host-bits;
                                        }
                                        description "IP address to match";
                                    }

                                    leaf mask {
                                        type types-sros:ipv4-address;
                                        description "Mask as an AND to the IP address";
                                    }

                                }
                                case ip-prefix-list {

                                    leaf ip-prefix-list {
                                        type leafref {
                                            path "../../../../../../../../filter/match-list/ip-prefix-list/prefix-list-name";
                                        }
                                        description "IP prefix list as match criterion for IP address";
                                    }

                                }
                            }
                        } // container dst-ip

                        container icmp {
                            description "Enter the icmp context";

                            choice icmp-code {
                                case code {

                                    leaf code {
                                        type types-filter:ipv4-match-icmp-codes;
                                        description "ICMP code to match";
                                    }

                                }
                            }
                            choice icmp-type {
                                case type {

                                    leaf type {
                                        type types-filter:ipv4-match-icmp-types;
                                        description "ICMP type to match";
                                    }

                                }
                            }
                        } // container icmp

                        container tcp-flags {
                            description "Enter the tcp-flags context";

                            leaf ack {
                                type boolean;
                                description "TCP ACK packet to match";
                            }

                            leaf syn {
                                type boolean;
                                description "TCP SYN packet to match";
                            }

                        } // container tcp-flags

                    } // container match

                    container action {
                        description "Enter the action context";

                        choice action-choice {
                            default "case-drop";
                            case case-drop {

                                leaf drop {
                                    type empty;
                                    description "Drop packet matching this entry";
                                }

                            }
                            case case-accept {

                                leaf accept {
                                    type empty;
                                    description "Packets matching the filter entry are forwarded";
                                }

                            }
                            case case-default {

                                leaf default {
                                    type empty;
                                    description "Action to take on the traffic when the filter entry matches";
                                }

                            }
                            case case-queue {

                                leaf queue {
                                    type leafref {
                                        path "../../../../../cpm-queue/queue/queue-id";
                                    }
                                    description "Packets matching the filter entry to be sent to this queue";
                                }

                            }
                        }
                    } // container action

                } // list entry

            } // container ip-filter

            container ipv6-filter {
                description "Enter the ipv6-filter context";

                leaf admin-state {
                    type types-sros:admin-state;
                    default "disable";
                    description "Administrative state of this CPM filter";
                }

                list entry {
                    key "entry-id";
                    description "Enter the entry list instance";

                    leaf entry-id {
                        type uint32 {
                            range "1..131072";
                        }
                        description "The id used to uniquely identify this filter entry.";
                    }

                    leaf description {
                        type types-sros:description;
                        description "Text description";
                    }

                    leaf log {
                        type leafref {
                            path "../../../../../../filter/log/log-id";
                        }
                        description "Log that is used for packets matching this entry";
                    }

                    leaf-list apply-groups {
                        type leafref {
                            path "../../../../../../groups/group/name";
                        }
                        max-elements 8;
                        ordered-by user;
                        description "Apply a configuration group at this level";
                    }

                    container match {
                        description "Enter the match context";

                        leaf router-instance {
                            type types-sros:named-item-64;
                            description "Specifies router instance to be matched.";
                        }

                        leaf next-header {
                            type types-sros:ipv6-match-next-header;
                            description "IPv6 next header to match. Because the match criteria only pertains to the last next-header, the following values will not match a filter entry: 0, 43, 44, 50, 51, and 60.";
                        }

                        leaf dscp {
                            type types-qos:dscp-name;
                            description "Specifies the DSCP to be matched on the packet.";
                        }

                        leaf flow-label {
                            type types-filter:filter-match-flow-label;
                            description "Specifies the flow label to be matched.";
                        }

                        leaf fragment {
                            type enumeration {
                                enum "false"                        { value 2; }
                                enum "true"                         { value 3; }
                            }
                            description "Match criterion based on fragmentation presence/absence";
                        }

                        choice port-selector {
                            case src-dst-port {

                                container src-port {
                                    description "Enter the src-port context";

                                    choice port {
                                        case eq {

                                            leaf eq {
                                                type uint16 {
                                                    range "0..65535";
                                                }
                                                description "Port to match";
                                            }

                                            leaf mask {
                                                type uint16 {
                                                    range "1..65535";
                                                }
                                                default "65535";
                                                description "Mask to apply when matching the port";
                                            }

                                        }
                                        case range {

                                            container range {
                                                presence "Enables port range matching.";
                                                description "Enter the range context";

                                                leaf start {
                                                    type uint16 {
                                                        range "0..65535";
                                                    }
                                                    mandatory true;
                                                    description "Lower bound port to match";
                                                }

                                                leaf end {
                                                    type uint16 {
                                                        range "0..65535";
                                                    }
                                                    mandatory true;
                                                    description "Lower bound port to match";
                                                }

                                            } // container range

                                        }
                                        case port-list {

                                            leaf port-list {
                                                type leafref {
                                                    path "../../../../../../../../filter/match-list/port-list/port-list-name";
                                                }
                                                description "Parameter port list as match criterion";
                                            }

                                        }
                                    }
                                } // container src-port

                                container dst-port {
                                    description "Enter the dst-port context";

                                    choice port {
                                        case eq {

                                            leaf eq {
                                                type uint16 {
                                                    range "0..65535";
                                                }
                                                description "Port to match";
                                            }

                                            leaf mask {
                                                type uint16 {
                                                    range "1..65535";
                                                }
                                                default "65535";
                                                description "Mask to apply when matching the port";
                                            }

                                        }
                                        case range {

                                            container range {
                                                presence "Enables port range matching.";
                                                description "Enter the range context";

                                                leaf start {
                                                    type uint16 {
                                                        range "0..65535";
                                                    }
                                                    mandatory true;
                                                    description "Lower bound port to match";
                                                }

                                                leaf end {
                                                    type uint16 {
                                                        range "0..65535";
                                                    }
                                                    mandatory true;
                                                    description "Lower bound port to match";
                                                }

                                            } // container range

                                        }
                                        case port-list {

                                            leaf port-list {
                                                type leafref {
                                                    path "../../../../../../../../filter/match-list/port-list/port-list-name";
                                                }
                                                description "Parameter port list as match criterion";
                                            }

                                        }
                                    }
                                } // container dst-port

                            }
                            case port {

                                container port {
                                    description "Enter the port context";

                                    choice port {
                                        case eq {

                                            leaf eq {
                                                type uint16 {
                                                    range "0..65535";
                                                }
                                                description "Port to match";
                                            }

                                            leaf mask {
                                                type uint16 {
                                                    range "1..65535";
                                                }
                                                default "65535";
                                                description "Mask to apply when matching the port";
                                            }

                                        }
                                        case range {

                                            container range {
                                                presence "Enables port range matching.";
                                                description "Enter the range context";

                                                leaf start {
                                                    type uint16 {
                                                        range "0..65535";
                                                    }
                                                    mandatory true;
                                                    description "Lower bound port to match";
                                                }

                                                leaf end {
                                                    type uint16 {
                                                        range "0..65535";
                                                    }
                                                    mandatory true;
                                                    description "Lower bound port to match";
                                                }

                                            } // container range

                                        }
                                        case port-list {

                                            leaf port-list {
                                                type leafref {
                                                    path "../../../../../../../../filter/match-list/port-list/port-list-name";
                                                }
                                                description "Parameter port list as match criterion";
                                            }

                                        }
                                    }
                                } // container port

                            }
                        }
                        container src-ip {
                            description "Enter the src-ip context";

                            choice match-address-choice {
                                case address-and-prefix-or-mask {

                                    leaf address {
                                        type union {
                                            type types-sros:ipv6-address;
                                            type types-sros:ipv6-prefix-with-host-bits;
                                        }
                                        description "IPv6 address used as a filter policy match criterion";
                                    }

                                    leaf mask {
                                        type types-sros:ipv6-address;
                                        description "Mask as an AND to IPv6 address";
                                    }

                                }
                                case ipv6-prefix-list {

                                    leaf ipv6-prefix-list {
                                        type leafref {
                                            path "../../../../../../../../filter/match-list/ipv6-prefix-list/prefix-list-name";
                                        }
                                        description "IP prefix list as match criterion for IP address";
                                    }

                                }
                            }
                        } // container src-ip

                        container dst-ip {
                            description "Enter the dst-ip context";

                            choice match-address-choice {
                                case address-and-prefix-or-mask {

                                    leaf address {
                                        type union {
                                            type types-sros:ipv6-address;
                                            type types-sros:ipv6-prefix-with-host-bits;
                                        }
                                        description "IPv6 address used as a filter policy match criterion";
                                    }

                                    leaf mask {
                                        type types-sros:ipv6-address;
                                        description "Mask as an AND to IPv6 address";
                                    }

                                }
                                case ipv6-prefix-list {

                                    leaf ipv6-prefix-list {
                                        type leafref {
                                            path "../../../../../../../../filter/match-list/ipv6-prefix-list/prefix-list-name";
                                        }
                                        description "IP prefix list as match criterion for IP address";
                                    }

                                }
                            }
                        } // container dst-ip

                        container extension-header {
                            description "Enter the extension-header context";

                            leaf hop-by-hop {
                                type boolean;
                                description "Match a packet as per the existence of a Hop-By-Hop options Extension Header";
                            }

                        } // container extension-header

                        container icmp {
                            description "Enter the icmp context";

                            choice icmp-code {
                                case code {

                                    leaf code {
                                        type types-filter:ipv6-match-icmp-codes;
                                        description "ICMP code to match";
                                    }

                                }
                            }
                            choice icmp-type {
                                case type {

                                    leaf type {
                                        type types-filter:ipv6-match-icmp-types;
                                        description "ICMP type to match";
                                    }

                                }
                            }
                        } // container icmp

                        container tcp-flags {
                            description "Enter the tcp-flags context";

                            leaf ack {
                                type boolean;
                                description "TCP ACK packet to match";
                            }

                            leaf syn {
                                type boolean;
                                description "TCP SYN packet to match";
                            }

                        } // container tcp-flags

                    } // container match

                    container action {
                        description "Enter the action context";

                        choice action-choice {
                            default "case-drop";
                            case case-drop {

                                leaf drop {
                                    type empty;
                                    description "Drop packet matching this entry";
                                }

                            }
                            case case-accept {

                                leaf accept {
                                    type empty;
                                    description "Packets matching the filter entry are forwarded";
                                }

                            }
                            case case-default {

                                leaf default {
                                    type empty;
                                    description "Action to take on the traffic when the filter entry matches";
                                }

                            }
                            case case-queue {

                                leaf queue {
                                    type leafref {
                                        path "../../../../../cpm-queue/queue/queue-id";
                                    }
                                    description "Packets matching the filter entry to be sent to this queue";
                                }

                            }
                        }
                    } // container action

                } // list entry

            } // container ipv6-filter

            container mac-filter {
                description "Enter the mac-filter context";

                leaf admin-state {
                    type types-sros:admin-state;
                    default "disable";
                    description "Administrative state of this CPM filter";
                }

                list entry {
                    key "entry-id";
                    description "Enter the entry list instance";

                    leaf entry-id {
                        type uint32 {
                            range "1..131072";
                        }
                        description "The id used to uniquely identify this filter entry.";
                    }

                    leaf description {
                        type types-sros:description;
                        description "Text description";
                    }

                    leaf log {
                        type leafref {
                            path "../../../../../../filter/log/log-id";
                        }
                        description "Log that is used for packets matching this entry";
                    }

                    leaf-list apply-groups {
                        type leafref {
                            path "../../../../../../groups/group/name";
                        }
                        max-elements 8;
                        ordered-by user;
                        description "Apply a configuration group at this level";
                    }

                    container match {
                        description "Enter the match context";

                        leaf service {
                            type leafref {
                                path "../../../../../../../service/vpls/service-name";
                            }
                            description "Specifies the VPLS service in which the packet is to be received for this entry to match.";
                        }

                        leaf frame-type {
                            type enumeration {
                                enum "802dot2-llc"                  { value 1; }
                                enum "ethernet-ii"                  { value 3; }
                            }
                            description "MAC frame as match criteria";
                        }

                        leaf etype {
                            type types-services:etype-value;
                            description "Ethernet type";
                        }

                        container src-mac {
                            presence "Source MAC address match criteria.";
                            description "Enter the src-mac context";

                            leaf address {
                                type yang:mac-address;
                                mandatory true;
                                description "MAC address used as MAC filter match criterion";
                            }

                            leaf mask {
                                type yang:mac-address;
                                default "ff:ff:ff:ff:ff:ff";
                                description "MAC address mask";
                            }

                        } // container src-mac

                        container dst-mac {
                            presence "Destination MAC address match criteria.";
                            description "Enter the dst-mac context";

                            leaf address {
                                type yang:mac-address;
                                mandatory true;
                                description "MAC address used as MAC filter match criterion";
                            }

                            leaf mask {
                                type yang:mac-address;
                                default "ff:ff:ff:ff:ff:ff";
                                description "MAC address mask";
                            }

                        } // container dst-mac

                        container llc-ssap {
                            presence "Enable SSAP criteria matching.";
                            description "Enter the llc-ssap context";

                            leaf ssap {
                                type types-qos:service-access-point;
                                mandatory true;
                                description "SSAP value";
                            }

                            leaf mask {
                                type types-qos:service-access-point {
                                    range "1..255";
                                }
                                default "255";
                                description "SAP mask";
                            }

                        } // container llc-ssap

                        container llc-dsap {
                            presence "Enable DSAP criteria matching.";
                            description "Enter the llc-dsap context";

                            leaf dsap {
                                type types-qos:service-access-point;
                                mandatory true;
                                description "DSAP value";
                            }

                            leaf mask {
                                type types-qos:service-access-point {
                                    range "1..255";
                                }
                                default "255";
                                description "DSAP mask";
                            }

                        } // container llc-dsap

                        container cfm-opcode {
                            description "Enter the cfm-opcode context";

                            choice cfm-opcode {
                                case eq {

                                    leaf eq {
                                        type uint32 {
                                            range "0..255";
                                        }
                                        description "Value of the opcode to match";
                                    }

                                }
                                case lt {

                                    leaf lt {
                                        type uint32 {
                                            range "1..255";
                                        }
                                        description "Upper bound for the range of opcode to match";
                                    }

                                }
                                case gt {

                                    leaf gt {
                                        type uint32 {
                                            range "0..254";
                                        }
                                        description "Lower bound for the range of opcode to match";
                                    }

                                }
                                case range {

                                    container range {
                                        presence "Enable range configuration.";
                                        description "Enter the range context";

                                        leaf start {
                                            type uint32 {
                                                range "0..254";
                                            }
                                            mandatory true;
                                            description "Lower bound for the range of opcode to match";
                                        }

                                        leaf end {
                                            type uint32 {
                                                range "1..255";
                                            }
                                            mandatory true;
                                            description "Upper bound for the range of opcode to match";
                                        }

                                    } // container range

                                }
                            }
                        } // container cfm-opcode

                    } // container match

                    container action {
                        description "Enter the action context";

                        choice action-choice {
                            default "case-drop";
                            case case-drop {

                                leaf drop {
                                    type empty;
                                    description "Drop packet matching this entry";
                                }

                            }
                            case case-accept {

                                leaf accept {
                                    type empty;
                                    description "Packets matching the filter entry are forwarded";
                                }

                            }
                            case case-default {

                                leaf default {
                                    type empty;
                                    description "Action to take on the traffic when the filter entry matches";
                                }

                            }
                            case case-queue {

                                leaf queue {
                                    type leafref {
                                        path "../../../../../cpm-queue/queue/queue-id";
                                    }
                                    description "Packets matching the filter entry to be sent to this queue";
                                }

                            }
                        }
                    } // container action

                } // list entry

            } // container mac-filter

        } // container cpm-filter

    } // grouping conf-system-security-cpm-cpm-filter

    grouping conf-system-security-cpm-cpm-queue {
        container cpm-queue {
            description "Enter the cpm-queue context";

            leaf-list apply-groups {
                type leafref {
                    path "../../../../groups/group/name";
                }
                max-elements 8;
                ordered-by user;
                description "Apply a configuration group at this level";
            }

            list queue {
                key "queue-id";
                description "Enter the queue list instance";

                leaf queue-id {
                    type uint32 {
                        range "33..2000";
                    }
                    description "Unique identifier of a CPM queue";
                }

                leaf cbs {
                    type types-security:burst-size;
                    units "kilobps";
                    description "CBS (Committed Burst Excess) associated with this queue";
                }

                leaf mbs {
                    type types-security:burst-size;
                    units "kilobps";
                    description "MBS (Maximum Burst Size) associated with this queue";
                }

                leaf-list apply-groups {
                    type leafref {
                        path "../../../../../groups/group/name";
                    }
                    max-elements 8;
                    ordered-by user;
                    description "Apply a configuration group at this level";
                }

                container rate {
                    description "Enter the rate context";

                    leaf pir {
                        type types-system:pir-rate;
                        units "kilobps";
                        default "max";
                        description "Peak information rate associated with this queue";
                    }

                    leaf cir {
                        type types-system:cir-rate;
                        units "kilobps";
                        default "max";
                        description "Amount of bandwidth committed to the queue";
                    }

                } // container rate

            } // list queue

        } // container cpm-queue

    } // grouping conf-system-security-cpm-cpm-queue

}
