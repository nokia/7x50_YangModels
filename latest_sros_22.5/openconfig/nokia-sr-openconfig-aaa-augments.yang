module nokia-sr-openconfig-aaa-augments {

    namespace "urn:nokia.com:sros:ns:yang:sr:openconfig-aaa-augments";

    prefix "nokia-oc-aaa-augs";

    import nokia-sros-yang-extensions     { prefix "sros-ext"; }
    import openconfig-aaa-types           { prefix "oc-aaa-types"; }

    sros-ext:sros-major-release "rel22";

    organization "Nokia";

    contact
        "Nokia SR OS Support
         Web: <http://www.nokia.com>";

    description
        "This module contains the list of augments against the openconfig-aaa
          module for the Nokia SR OS based routers.

         Copyright 2016 Nokia. All rights reserved. Reproduction of this document
         is authorized on the condition that the foregoing copyright notice is included.

         This nokia-sr-openconfig-aaa-augments YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";

    revision "2022-01-31";

    identity SYSTEM_ROLE_DEFAULT {
        base oc-aaa-types:SYSTEM_DEFINED_ROLES;
        description "Built-in role regular users.";
    }

}
