module nokia-sr-openconfig-system-deviations {

    namespace "urn:nokia.com:sros:ns:yang:sr:openconfig-system-deviations";

    prefix "nokia-oc-sys-devs";

    import nokia-sros-yang-extensions     { prefix "sros-ext"; }
    import openconfig-aaa                 { prefix "oc-aaa"; }
    import openconfig-aaa-types           { prefix "oc-aaa-types"; }
    import openconfig-alarms              { prefix "oc-alarms"; }
    import openconfig-extensions          { prefix "oc-ext"; }
    import openconfig-inet-types          { prefix "oc-inet"; }
    import openconfig-license             { prefix "oc-license"; }
    import openconfig-messages            { prefix "oc-messages"; }
    import openconfig-procmon             { prefix "oc-proc"; }
    import openconfig-system              { prefix "oc-sys"; }
    import openconfig-system-logging      { prefix "oc-sys-log"; }
    import openconfig-system-management   { prefix "oc-sys-mgmt"; }
    import openconfig-system-terminal     { prefix "oc-sys-term"; }
    import openconfig-types               { prefix "oc-types"; }
    import openconfig-yang-types          { prefix "oc-yang"; }

    sros-ext:sros-major-release "rel22";

    organization "Nokia";

    contact
        "Nokia SR OS Support
         Web: <http://www.nokia.com>";

    description
        "This module contains the list of deviations against the openconfig-system
          module for the Nokia SR OS based routers.

         Copyright 2016 Nokia. All rights reserved. Reproduction of this document
         is authorized on the condition that the foregoing copyright notice is included.

         This nokia-sr-openconfig-system-deviations YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";

    revision "2020-03-25";

    deviation /oc-sys:system/oc-sys:config/oc-sys:hostname {
        deviate not-supported;
    }

    deviation /oc-sys:system/oc-sys:config/oc-sys:domain-name {
        deviate not-supported;
    }

    deviation /oc-sys:system/oc-sys:config/oc-sys:login-banner {
        deviate not-supported;
    }

    deviation /oc-sys:system/oc-sys:config/oc-sys:motd-banner {
        deviate not-supported;
    }

    deviation /oc-sys:system/oc-sys:state/oc-sys:hostname {
        deviate not-supported;
    }

    deviation /oc-sys:system/oc-sys:state/oc-sys:domain-name {
        deviate not-supported;
    }

    deviation /oc-sys:system/oc-sys:state/oc-sys:login-banner {
        deviate not-supported;
    }

    deviation /oc-sys:system/oc-sys:state/oc-sys:motd-banner {
        deviate not-supported;
    }

    deviation /oc-sys:system/oc-sys:state/oc-sys:current-datetime {
        deviate not-supported;
    }

    deviation /oc-sys:system/oc-sys:state/oc-sys:boot-time {
        deviate not-supported;
    }

    deviation /oc-sys:system/oc-sys:aaa/oc-sys:authentication/oc-sys:config/oc-sys:authentication-method {
        description
            "Ordered list of authentication methods for users.  This
             is a defined designation in the AAA_METHOD_TYPE identity.
             If authentication fails with one method, the next defined
             method is tried -- failure of all methods results in the
             user being denied access.";
        deviate replace {
            type union {
                type identityref {
                    base oc-aaa-types:AAA_METHOD_TYPE;
                }
            }
        }
        deviate add {
            max-elements 3;
        }
    }

    deviation /oc-sys:system/oc-sys:aaa/oc-sys:authentication/oc-sys:state/oc-sys:authentication-method {
        description
            "Ordered list of authentication methods for users.  This
             is a defined designation in the AAA_METHOD_TYPE identity.
             If authentication fails with one method, the next defined
             method is tried -- failure of all methods results in the
             user being denied access.";
        deviate replace {
            type union {
                type identityref {
                    base oc-aaa-types:AAA_METHOD_TYPE;
                }
            }
        }
        deviate add {
            max-elements 3;
        }
    }

    deviation /oc-sys:system/oc-sys:aaa/oc-sys:authentication/oc-sys:users/oc-sys:user/oc-sys:config/oc-sys:username {
        deviate replace {
            type string {
                pattern "(.*\\S.*)|()";
                length 1..32;
            }
        }
    }

    deviation /oc-sys:system/oc-sys:aaa/oc-sys:authentication/oc-sys:users/oc-sys:user/oc-sys:config/oc-sys:password {
        deviate not-supported;
    }

    deviation /oc-sys:system/oc-sys:aaa/oc-sys:authentication/oc-sys:users/oc-sys:user/oc-sys:config/oc-sys:password-hashed {
        description "Extending type to include accepting clear-text input";
        deviate add {
            mandatory true;
        }
    }

    deviation /oc-sys:system/oc-sys:aaa/oc-sys:authentication/oc-sys:users/oc-sys:user/oc-sys:config/oc-sys:ssh-key {
        description "SSH public key for the user (RSA)";
        deviate replace {
            type string {
                pattern "(.*\\S.*)|()";
                length 1..800;
            }
        }
    }

    deviation /oc-sys:system/oc-sys:aaa/oc-sys:authentication/oc-sys:users/oc-sys:user/oc-sys:config/oc-sys:role {
        description
            "Role assigned to the user. The role may be one of
             roles defined by the SYSTEM_DEFINED_ROLES identity.";
        deviate replace {
            type union {
                type identityref {
                    base oc-aaa-types:SYSTEM_DEFINED_ROLES;
                }
            }
        }
    }

    deviation /oc-sys:system/oc-sys:aaa/oc-sys:authentication/oc-sys:users/oc-sys:user/oc-sys:state/oc-sys:username {
        deviate replace {
            type string {
                pattern "(.*\\S.*)|()";
                length 1..32;
            }
        }
    }

    deviation /oc-sys:system/oc-sys:aaa/oc-sys:authentication/oc-sys:users/oc-sys:user/oc-sys:state/oc-sys:password {
        deviate not-supported;
    }

    deviation /oc-sys:system/oc-sys:aaa/oc-sys:authentication/oc-sys:users/oc-sys:user/oc-sys:state/oc-sys:password-hashed {
        description "Extending type to include accepting clear-text input";
        deviate add {
            mandatory true;
        }
    }

    deviation /oc-sys:system/oc-sys:aaa/oc-sys:authentication/oc-sys:users/oc-sys:user/oc-sys:state/oc-sys:ssh-key {
        description "SSH public key for the user (RSA)";
        deviate replace {
            type string {
                pattern "(.*\\S.*)|()";
                length 1..800;
            }
        }
    }

    deviation /oc-sys:system/oc-sys:aaa/oc-sys:authentication/oc-sys:users/oc-sys:user/oc-sys:state/oc-sys:role {
        description
            "Role assigned to the user. The role may be one of
             roles defined by the SYSTEM_DEFINED_ROLES identity.";
        deviate replace {
            type union {
                type identityref {
                    base oc-aaa-types:SYSTEM_DEFINED_ROLES;
                }
            }
        }
    }

    deviation /oc-sys:system/oc-sys:aaa/oc-sys:authentication/oc-sys:admin-user {
        deviate not-supported;
    }

    deviation /oc-sys:system/oc-sys:aaa/oc-sys:authorization/oc-sys:config/oc-sys:authorization-method {
        description
            "Ordered list of methods for authorizing commands.  The first
             method that provides a response (positive or negative) should
             be used.  The list may contain a well-defined method such
             as the set of all TACACS or RADIUS servers.";
        deviate replace {
            type union {
                type identityref {
                    base oc-aaa-types:AAA_METHOD_TYPE;
                }
            }
        }
        deviate add {
            max-elements 3;
        }
    }

    deviation /oc-sys:system/oc-sys:aaa/oc-sys:authorization/oc-sys:state/oc-sys:authorization-method {
        description
            "Ordered list of methods for authorizing commands.  The first
             method that provides a response (positive or negative) should
             be used.  The list may contain a well-defined method such
             as the set of all TACACS or RADIUS servers.";
        deviate replace {
            type union {
                type identityref {
                    base oc-aaa-types:AAA_METHOD_TYPE;
                }
            }
        }
        deviate add {
            max-elements 3;
        }
    }

    deviation /oc-sys:system/oc-sys:aaa/oc-sys:authorization/oc-sys:events {
        deviate not-supported;
    }

    deviation /oc-sys:system/oc-sys:aaa/oc-sys:accounting/oc-sys:config/oc-sys:accounting-method {
        description
            "An ordered list of methods used for AAA accounting for this
             event type.  The method is defined by the destination for
             accounting data, which may be specified as the group of
             all TACACS+/RADIUS servers or the local system.";
        deviate replace {
            type union {
                type identityref {
                    base oc-aaa-types:AAA_METHOD_TYPE;
                }
            }
        }
        deviate add {
            max-elements 3;
        }
    }

    deviation /oc-sys:system/oc-sys:aaa/oc-sys:accounting/oc-sys:state/oc-sys:accounting-method {
        description
            "An ordered list of methods used for AAA accounting for this
             event type.  The method is defined by the destination for
             accounting data, which may be specified as the group of
             all TACACS+/RADIUS servers or the local system.";
        deviate replace {
            type union {
                type identityref {
                    base oc-aaa-types:AAA_METHOD_TYPE;
                }
            }
        }
        deviate add {
            max-elements 3;
        }
    }

    deviation /oc-sys:system/oc-sys:aaa/oc-sys:accounting/oc-sys:events {
        deviate not-supported;
    }

    deviation /oc-sys:system/oc-sys:aaa/oc-sys:server-groups/oc-sys:server-group/oc-sys:config/oc-sys:type {
        deviate add {
            mandatory true;
        }
    }

    deviation /oc-sys:system/oc-sys:aaa/oc-sys:server-groups/oc-sys:server-group/oc-sys:state/oc-sys:type {
        deviate add {
            mandatory true;
        }
    }

    deviation /oc-sys:system/oc-sys:aaa/oc-sys:server-groups/oc-sys:server-group/oc-sys:servers/oc-sys:server/oc-sys:config/oc-sys:timeout {
        deviate replace {
            type uint16 {
                range 1..90;
            }
        }
    }

    deviation /oc-sys:system/oc-sys:aaa/oc-sys:server-groups/oc-sys:server-group/oc-sys:servers/oc-sys:server/oc-sys:state/oc-sys:timeout {
        deviate replace {
            type uint16 {
                range 1..90;
            }
        }
    }

    deviation /oc-sys:system/oc-sys:aaa/oc-sys:server-groups/oc-sys:server-group/oc-sys:servers/oc-sys:server/oc-sys:state/oc-sys:connection-opens {
        deviate not-supported;
    }

    deviation /oc-sys:system/oc-sys:aaa/oc-sys:server-groups/oc-sys:server-group/oc-sys:servers/oc-sys:server/oc-sys:state/oc-sys:connection-closes {
        deviate not-supported;
    }

    deviation /oc-sys:system/oc-sys:aaa/oc-sys:server-groups/oc-sys:server-group/oc-sys:servers/oc-sys:server/oc-sys:state/oc-sys:connection-aborts {
        deviate not-supported;
    }

    deviation /oc-sys:system/oc-sys:aaa/oc-sys:server-groups/oc-sys:server-group/oc-sys:servers/oc-sys:server/oc-sys:state/oc-sys:errors-received {
        deviate not-supported;
    }

    deviation /oc-sys:system/oc-sys:aaa/oc-sys:server-groups/oc-sys:server-group/oc-sys:servers/oc-sys:server/oc-sys:tacacs/oc-sys:config/oc-sys:port {
        deviate replace {
            type oc-inet:port-number {
                range 1..65535;
            }
        }
    }

    deviation /oc-sys:system/oc-sys:aaa/oc-sys:server-groups/oc-sys:server-group/oc-sys:servers/oc-sys:server/oc-sys:tacacs/oc-sys:config/oc-sys:secret-key {
        deviate replace {
            type oc-types:routing-password {
                length 1..199;
                pattern "(.{1,128})|(.{1,192} hash)|(.{1,192} hash2)|(.{1,192} custom)";
            }
        }
        deviate add {
            mandatory true;
        }
    }

    deviation /oc-sys:system/oc-sys:aaa/oc-sys:server-groups/oc-sys:server-group/oc-sys:servers/oc-sys:server/oc-sys:tacacs/oc-sys:state/oc-sys:port {
        deviate replace {
            type oc-inet:port-number {
                range 1..65535;
            }
        }
    }

    deviation /oc-sys:system/oc-sys:aaa/oc-sys:server-groups/oc-sys:server-group/oc-sys:servers/oc-sys:server/oc-sys:tacacs/oc-sys:state/oc-sys:secret-key {
        deviate replace {
            type oc-types:routing-password {
                length 1..199;
                pattern "(.{1,128})|(.{1,192} hash)|(.{1,192} hash2)|(.{1,192} custom)";
            }
        }
        deviate add {
            mandatory true;
        }
    }

    deviation /oc-sys:system/oc-sys:aaa/oc-sys:server-groups/oc-sys:server-group/oc-sys:servers/oc-sys:server/oc-sys:radius/oc-sys:config/oc-sys:auth-port {
        deviate replace {
            type oc-inet:port-number {
                range 1..65535;
            }
        }
    }

    deviation /oc-sys:system/oc-sys:aaa/oc-sys:server-groups/oc-sys:server-group/oc-sys:servers/oc-sys:server/oc-sys:radius/oc-sys:config/oc-sys:acct-port {
        deviate replace {
            type oc-inet:port-number {
                range 1..65535;
            }
        }
    }

    deviation /oc-sys:system/oc-sys:aaa/oc-sys:server-groups/oc-sys:server-group/oc-sys:servers/oc-sys:server/oc-sys:radius/oc-sys:config/oc-sys:secret-key {
        deviate replace {
            type oc-types:routing-password {
                length 1..115;
                pattern "(.{1,64})|(.{1,108} hash)|(.{1,108} hash2)|(.{1,108} custom)";
            }
        }
        deviate add {
            mandatory true;
        }
    }

    deviation /oc-sys:system/oc-sys:aaa/oc-sys:server-groups/oc-sys:server-group/oc-sys:servers/oc-sys:server/oc-sys:radius/oc-sys:config/oc-sys:retransmit-attempts {
        deviate replace {
            type uint8 {
                range 1..10;
            }
        }
    }

    deviation /oc-sys:system/oc-sys:aaa/oc-sys:server-groups/oc-sys:server-group/oc-sys:servers/oc-sys:server/oc-sys:radius/oc-sys:state/oc-sys:auth-port {
        deviate replace {
            type oc-inet:port-number {
                range 1..65535;
            }
        }
    }

    deviation /oc-sys:system/oc-sys:aaa/oc-sys:server-groups/oc-sys:server-group/oc-sys:servers/oc-sys:server/oc-sys:radius/oc-sys:state/oc-sys:acct-port {
        deviate replace {
            type oc-inet:port-number {
                range 1..65535;
            }
        }
    }

    deviation /oc-sys:system/oc-sys:aaa/oc-sys:server-groups/oc-sys:server-group/oc-sys:servers/oc-sys:server/oc-sys:radius/oc-sys:state/oc-sys:secret-key {
        deviate replace {
            type oc-types:routing-password {
                length 1..115;
                pattern "(.{1,64})|(.{1,108} hash)|(.{1,108} hash2)|(.{1,108} custom)";
            }
        }
        deviate add {
            mandatory true;
        }
    }

    deviation /oc-sys:system/oc-sys:aaa/oc-sys:server-groups/oc-sys:server-group/oc-sys:servers/oc-sys:server/oc-sys:radius/oc-sys:state/oc-sys:retransmit-attempts {
        deviate replace {
            type uint8 {
                range 1..10;
            }
        }
    }

    deviation /oc-sys:system/oc-sys:aaa/oc-sys:server-groups/oc-sys:server-group/oc-sys:servers/oc-sys:server/oc-sys:radius/oc-sys:state/oc-sys:counters/oc-sys:retried-access-requests {
        deviate not-supported;
    }

    deviation /oc-sys:system/oc-sys:aaa/oc-sys:server-groups/oc-sys:server-group/oc-sys:servers/oc-sys:server {
        deviate add {
            max-elements 5;
        }
    }

    deviation /oc-sys:system/oc-sys:aaa/oc-sys:server-groups/oc-sys:server-group {
        deviate add {
            max-elements 2;
        }
    }

    deviation /oc-sys:system/oc-sys:memory/oc-sys:config {
        deviate not-supported;
    }

    deviation /oc-sys:system/oc-sys:memory {
        deviate replace {
            config false;
        }
    }

    deviation /oc-sys:system/oc-sys:cpus/oc-sys:cpu/oc-sys:state/oc-sys:total/oc-sys:min {
        deviate not-supported;
    }

    deviation /oc-sys:system/oc-sys:cpus/oc-sys:cpu/oc-sys:state/oc-sys:total/oc-sys:max {
        deviate not-supported;
    }

    deviation /oc-sys:system/oc-sys:cpus/oc-sys:cpu/oc-sys:state/oc-sys:total/oc-sys:min-time {
        deviate not-supported;
    }

    deviation /oc-sys:system/oc-sys:cpus/oc-sys:cpu/oc-sys:state/oc-sys:total/oc-sys:max-time {
        deviate not-supported;
    }

    deviation /oc-sys:system/oc-sys:cpus/oc-sys:cpu/oc-sys:state/oc-sys:user {
        deviate not-supported;
    }

    deviation /oc-sys:system/oc-sys:cpus/oc-sys:cpu/oc-sys:state/oc-sys:kernel {
        deviate not-supported;
    }

    deviation /oc-sys:system/oc-sys:cpus/oc-sys:cpu/oc-sys:state/oc-sys:nice {
        deviate not-supported;
    }

    deviation /oc-sys:system/oc-sys:cpus/oc-sys:cpu/oc-sys:state/oc-sys:idle/oc-sys:min {
        deviate not-supported;
    }

    deviation /oc-sys:system/oc-sys:cpus/oc-sys:cpu/oc-sys:state/oc-sys:idle/oc-sys:max {
        deviate not-supported;
    }

    deviation /oc-sys:system/oc-sys:cpus/oc-sys:cpu/oc-sys:state/oc-sys:idle/oc-sys:min-time {
        deviate not-supported;
    }

    deviation /oc-sys:system/oc-sys:cpus/oc-sys:cpu/oc-sys:state/oc-sys:idle/oc-sys:max-time {
        deviate not-supported;
    }

    deviation /oc-sys:system/oc-sys:cpus/oc-sys:cpu/oc-sys:state/oc-sys:wait {
        deviate not-supported;
    }

    deviation /oc-sys:system/oc-sys:cpus/oc-sys:cpu/oc-sys:state/oc-sys:hardware-interrupt {
        deviate not-supported;
    }

    deviation /oc-sys:system/oc-sys:cpus/oc-sys:cpu/oc-sys:state/oc-sys:software-interrupt {
        deviate not-supported;
    }

    deviation /oc-sys:system/oc-sys:processes/oc-sys:process/oc-sys:state/oc-sys:args {
        deviate not-supported;
    }

    deviation /oc-sys:system/oc-sys:processes/oc-sys:process/oc-sys:state/oc-sys:start-time {
        deviate not-supported;
    }

    deviation /oc-sys:system/oc-sys:processes/oc-sys:process/oc-sys:state/oc-sys:cpu-usage-user {
        deviate not-supported;
    }

    deviation /oc-sys:system/oc-sys:processes/oc-sys:process/oc-sys:state/oc-sys:cpu-usage-system {
        deviate not-supported;
    }

    deviation /oc-sys:system/oc-sys:messages {
        deviate not-supported;
    }

    deviation /oc-sys:system/oc-sys:license {
        deviate not-supported;
    }

    deviation /oc-sys:system/oc-sys:clock {
        deviate not-supported;
    }

    deviation /oc-sys:system/oc-sys:dns {
        deviate not-supported;
    }

    deviation /oc-sys:system/oc-sys:ntp {
        deviate not-supported;
    }

    deviation /oc-sys:system/oc-sys:alarms {
        deviate not-supported;
    }

}
