module nokia-sr-ietf-netconf-monitoring-deviations {
  yang-version "1.1";

  namespace "urn:nokia.com:sros:ns:yang:sr:ietf-netconf-monitoring-deviations";
  prefix nokia-ncm-devs;

  import ietf-netconf-monitoring {
    prefix ncm;
    revision-date 2010-10-04;
  }

  organization "Nokia";

  contact
      "Nokia SR OS Support
       Web: <http://www.nokia.com>";

  description
      "YANG Data model for Nokia NETCONF Monitoring deviations.

      Copyright 2021 Nokia. All rights reserved.
      Reproduction of this document is authorized on the condition
      that the foregoing copyright notice is included.

      This nokia-sr-ietf-netconf-monitoring-deviations YANG module
      embodies Nokia's proprietary intellectual property.  Nokia
      retains all title and ownership in the Specification, including
      any revisions.

      Nokia grants all interested parties a non-exclusive license
      to use and distribute an unmodified copy of this Specification
      in connection with management of Nokia products, and without
      fee, provided this copyright notice and license appear on all
      copies.

      This Specification is supplied `as is`, and Nokia makes no
      warranty, either express or implied, as to the use, operation,
      condition, or performance of the Specification.

      NOTE: This module is currently for prototype use and is not
      shipped as part of SR OS.  The purpose of this module is for
      pre-release and must be manually referenced/loaded from a YANG
      capable client/compiler.  Do not redistribute.
      ";

  revision 2021-02-23;

  //Deviations

  deviation /ncm:netconf-state/ncm:capabilities {
    description
        "capabilites subtree is not supported.";
    deviate not-supported;
  }

  deviation /ncm:netconf-state/ncm:datastores {
    description
        "datastores subtree is not supported.";
    deviate not-supported;
  }

  deviation /ncm:netconf-state/ncm:sessions {
    description
        "sessions subtree is not supported.";
    deviate not-supported;
  }

  deviation /ncm:netconf-state/ncm:statistics {
    description
        "statistics subtree is not supported.";
    deviate not-supported;
  }
}
