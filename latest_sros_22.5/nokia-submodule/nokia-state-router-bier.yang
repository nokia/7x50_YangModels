submodule nokia-state-router-bier {

    yang-version "1.1";

    belongs-to nokia-state { prefix "state"; }

    import ietf-inet-types                { prefix "inet"; }
    import nokia-sros-yang-extensions     { prefix "sros-ext"; }
    import nokia-types-sros               { prefix "types-sros"; }


    sros-ext:sros-major-release "rel22";

    organization "Nokia";

    contact
        "Nokia SR OS Support
         Web: <http://www.nokia.com>";

    description
        "Nokia YANG Data model with operational state for Base router BIER protocol on SR OS based routers.

         Copyright 2016 Nokia. All rights reserved. Reproduction of this document
         is authorized on the condition that the foregoing copyright notice is included.

         This nokia-state-router-bier YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";

    revision "2021-06-16";

    grouping state-router-bier {
        container bier {
            description "Enter the bier context";

            leaf oper-state {
                type types-sros:oper-state;
                description "BIER operational state.";
            }

            list template {
                key "template-name";
                description "Enter the template list instance";

                leaf template-name {
                    type types-sros:named-item;
                    description "BIER template name";
                }

                leaf oper-state {
                    type types-sros:oper-state;
                    description "BIER template operational state.";
                }

            } // list template

            list database {
                key "template-name sub-domain-id";
                description "Enter the database list instance";

                leaf template-name {
                    type types-sros:named-item;
                    description "BIER template name";
                }

                leaf sub-domain-id {
                    type inet:as-number {
                        range "0..255";
                    }
                    description "bier sub-domain start value.";
                }

                leaf bit-string-length {
                    type uint32;
                    description "The current supported bit string length.";
                }

                leaf bfr-prefix {
                    type types-sros:ip-address;
                    description "The address to be advertised in this sub-domain.";
                }

                leaf multi-topology {
                    type enumeration {
                        enum "ipv4-unicast"                 { value 0; }
                        enum "ipv6-unicast"                 { value 2; }
                        enum "ipv4-multicast"               { value 3; }
                        enum "ipv6-multicast"               { value 4; }
                    }
                    description "The ISIS Multi-topolog ID where the BIER template should be applied.";
                }

                leaf mpls-start-label {
                    type uint32;
                    description "The mpls start label.";
                }

                leaf mpls-end-label {
                    type uint32;
                    description "The mpls end label.";
                }

                leaf mpls-total-label {
                    type uint32;
                    description "Total number of mpls labels.";
                }

                leaf bfr-id {
                    type uint32;
                    description "A BFR ID uniquely identifies a BFIR/BFER within the sub-domain.";
                }

            } // list database

            list forwarding {
                key "sub-domain-id bit-string-length next-hop-prefix next-hop-interface-name set-id";
                description "Enter the forwarding list instance";

                leaf sub-domain-id {
                    type inet:as-number {
                        range "0..255";
                    }
                    description "bier sub-domain start value.";
                }

                leaf bit-string-length {
                    type uint32;
                    description "The current supported bit string length.";
                }

                leaf next-hop-prefix {
                    type types-sros:ipv4-address;
                    description "Address of the destination prefix.";
                }

                leaf next-hop-interface-name {
                    type types-sros:interface-name;
                    description "Next hop interface name.";
                }

                leaf set-id {
                    type uint32;
                    description "The set identifier.";
                }

                leaf neighbor-prefix {
                    type types-sros:ip-address;
                    description "Address of the BFR prefix to be advertised in this sub-domain.";
                }

                leaf bit-string {
                    type types-sros:display-string-or-empty;
                    description "The bit string value.";
                }

                leaf mpls-label {
                    type uint32;
                    description "The service BIER label for the sender tunnel.";
                }

                list destination {
                    key "destination-prefix";
                    description "Enter the destination list instance";

                    leaf destination-prefix {
                        type types-sros:ip-address;
                        description "Address of the destination prefix.";
                    }

                    leaf bfr-id {
                        type uint32;
                        description "A BFR ID uniquely identifies a BFIR/BFER within the sub-domain.";
                    }

                } // list destination

                container backup {
                    description "Enter the backup context";

                    leaf neighbor-prefix {
                        type types-sros:ip-address;
                        description "Address of the backup BFR prefix to be advertised in this sub-domain.";
                    }

                    leaf next-hop-prefix {
                        type types-sros:ipv4-address;
                        description "Address of the backup destination prefix.";
                    }

                    leaf next-hop-interface-name {
                        type types-sros:interface-name;
                        description "Backup next hop interface name.";
                    }

                    leaf bit-string {
                        type types-sros:display-string-or-empty;
                        description "The backup bit string value.";
                    }

                    leaf mpls-label {
                        type uint32;
                        description "The backup service BIER label for the sender tunnel.";
                    }

                    list destination {
                        key "destination-prefix";
                        description "Enter the destination list instance";

                        leaf destination-prefix {
                            type types-sros:ip-address;
                            description "Address of the destination prefix.";
                        }

                        leaf bfr-id {
                            type uint32;
                            description "A BFR ID uniquely identifies a BFIR/BFER within the sub-domain for backup part.";
                        }

                    } // list destination

                } // container backup

            } // list forwarding

            list routing {
                key "sub-domain-id bit-string-length next-hop-prefix next-hop-interface-name destination-prefix";
                description "Enter the routing list instance";

                leaf sub-domain-id {
                    type inet:as-number {
                        range "0..255";
                    }
                    description "bier sub-domain start value.";
                }

                leaf bit-string-length {
                    type uint32;
                    description "The current supported bit string length.";
                }

                leaf next-hop-prefix {
                    type types-sros:ipv4-address;
                    description "Address of the destination prefix.";
                }

                leaf next-hop-interface-name {
                    type types-sros:interface-name;
                    description "Next hop interface name.";
                }

                leaf destination-prefix {
                    type types-sros:ip-address;
                    description "Address of the destination prefix.";
                }

                leaf neighbor-prefix {
                    type types-sros:ip-address;
                    description "Address of the BFR prefix to be advertised in this sub-domain.";
                }

                leaf bfr-id {
                    type uint32;
                    description "A BFR ID uniquely identifies a BFIR/BFER within the sub-domain.";
                }

                container backup {
                    description "Enter the backup context";

                    leaf neighbor-prefix {
                        type types-sros:ip-address;
                        description "Address of the backup BFR prefix to be advertised in this sub-domain.";
                    }

                    leaf next-hop-prefix {
                        type types-sros:ipv4-address;
                        description "Address of the backup destination prefix.";
                    }

                    leaf next-hop-interface-name {
                        type types-sros:interface-name;
                        description "Backup next hop interface name.";
                    }

                } // container backup

            } // list routing

            list tunnel {
                key "tunnel-index";
                description "Enter the tunnel list instance";

                leaf tunnel-index {
                    type uint32;
                    description "Tunnel index for the bier tunnel, internally maintained.";
                }

                leaf tunnel-type {
                    type enumeration {
                        enum "tx"                           { value 0; }
                        enum "rx"                           { value 1; }
                    }
                    description "The tunnel type identifies whether tunnel is transmitter or receiver.";
                }

                leaf bfr-prefix {
                    type types-sros:ip-address;
                    description "Address of the tunnel originator, advertised in PTA.";
                }

                leaf sub-domain-id {
                    type inet:as-number {
                        range "0..255";
                    }
                    description "BIER sub-domain value, where the tunnel is resolved, advertised in PTA.";
                }

                leaf mpls-svc-label {
                    type uint32;
                    description "The mpls service label to be used for this tunnel, advertised in PTA.";
                }

                leaf bfr-id {
                    type uint32;
                    description "BFR ID of the tunnel in the sub-domain, advertised in PTA.";
                }

                leaf oper-state {
                    type types-sros:oper-state;
                    description "Indicates the operational state of the bier tunnel.";
                }

                leaf number-of-leaves {
                    type uint32;
                    description "Indicates number of leaves for each transmitting tunnels.";
                }

                leaf last-oper-down-reason {
                    type uint32;
                    description "Indicates the reason for last time tunnel was flapped.";
                }

                list tunnel-leaf {
                    key "tunnel-leaf-prefix";
                    description "Enter the tunnel-leaf list instance";

                    leaf tunnel-leaf-prefix {
                        type types-sros:ip-address;
                        description "Tunnel leaf router address";
                    }

                    leaf mvpn-id {
                        type uint32;
                        description "The MVPN ID indicates the service instance id, internaly used";
                    }

                    leaf oper-state {
                        type types-sros:oper-state;
                        description "This indecates the operational state of the transmitting tunnel";
                    }

                    leaf bfr-prefix {
                        type types-sros:ip-address;
                        description "This indicates the address of the BFR prefix to be advertised via the PMSI attribute";
                    }

                    leaf bfr-id {
                        type uint32;
                        description "This indicates the BFR-ID of the BFR prefix in the sub-domain to be advertised via the PMSI attribute";
                    }

                    leaf sub-domain {
                        type uint32;
                        description "This indicates the sub-domain id to be advertised via the PMSI attribute";
                    }

                    leaf mpls-label {
                        type uint32;
                        description "This indicates the MPLS label to be advertised via the PMSI attribute";
                    }

                    leaf leaf-bfr-id {
                        type uint32;
                        description "The leaf BFR-ID field indicates each leaf BFR IDs, joined to this tunnel";
                    }

                } // list tunnel-leaf

            } // list tunnel

            container statistics {
                description "Enter the statistics context";

                leaf total-learnt-routes {
                    type uint32;
                    description "The value indicates the total number of learnt BFR prefixes.";
                }

                leaf total-valid-routes {
                    type uint32;
                    description "The value indicates the total number of BFR prefixes with valid BFR info.";
                }

                leaf valid-neighbor-nethops {
                    type uint32;
                    description "The value indicates the total number of neighbors or next-hops with valid BFR info.";
                }

                leaf received-invalid-bier-info {
                    type uint32;
                    description "The value indicates the number of learnt BFR prefixes with invalid BIER info.";
                }

                leaf received-invalid-bfr-info {
                    type uint32;
                    description "The value indecates the number of learnt BFR prefixes with invalid BFR info.";
                }

                leaf received-invalid-encap-info {
                    type uint32;
                    description "The value indicates the number of learnt BFR prefixes with invalid encapsulation info.";
                }

                leaf received-invalid-mpls-info {
                    type uint32;
                    description "The value indicates the number of learnt BFR prefixes with invalid MPLS info.";
                }

                leaf discard-tunneled-nexthop {
                    type uint32;
                    description "The value indicates the number of tunneled next-hops discarded.";
                }

                leaf discard-non-network-nexthop {
                    type uint32;
                    description "The value indicates the number of non network nexthops discarded.";
                }

                leaf discard-non-fp4-nexthop {
                    type uint32;
                    description "The value indicates the number of non FP4 nexthops discarded.";
                }

                leaf sub-domain-bit-string-length-mismatch {
                    type uint32;
                    description "The value indicates the number of BFR prefixes received with sub-domain and BSL value different from configured values.";
                }

                leaf multi-topology-mismatch {
                    type uint32;
                    description "The value indicates the number of BFR prefixes received with multi-topology value different from the configured value.";
                }

                leaf unsupported-ipv6-routes {
                    type uint32;
                    description "The value indicates the number of BFR prefixes learnt with IPv6 addresses.";
                }

                leaf bfr-id-duplicate {
                    type uint32;
                    description "The value indicates the number of duplicate BFR id received in multiple BFR prefixes.";
                }

            } // container statistics

        } // container bier

    } // grouping state-router-bier

}
