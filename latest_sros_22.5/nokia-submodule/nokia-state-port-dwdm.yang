submodule nokia-state-port-dwdm {

    yang-version "1.1";

    belongs-to nokia-state { prefix "state"; }

    import nokia-sros-yang-extensions     { prefix "sros-ext"; }
    import nokia-types-port               { prefix "types-port"; }
    import nokia-types-sros               { prefix "types-sros"; }

    include nokia-state-port-dwdm-coherent;


    sros-ext:sros-major-release "rel22";

    organization "Nokia";

    contact
        "Nokia SR OS Support
         Web: <http://www.nokia.com>";

    description
        "Nokia YANG Data model with operational state for dense wavelength division multiplexing ports on SR OS based routers.

         Copyright 2016 Nokia. All rights reserved. Reproduction of this document
         is authorized on the condition that the foregoing copyright notice is included.

         This nokia-state-port-dwdm YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";

    revision "2021-12-02";

    grouping state-port-dwdm {
        container dwdm {
            description "Enter the dwdm context";

            leaf rxdtv-current-adjustment {
                status obsolete;
                type uint32 {
                    range "0..10000";
                }
                units "centipercent";
                description "Indicates the current relative adjustment of the receive decision threshold voltage.";
            }

            leaf laser-tunability {
                type enumeration {
                    enum "unequipped"                   { value 0; }
                    enum "not-tunable"                  { value 1; }
                    enum "fully-tunable"                { value 2; }
                    enum "tunable-100g"                 { value 3; }
                    enum "flex-tunable"                 { value 4; }
                }
                description "Indicates if the optical interface laser is tunable or fixed. Value 'unequipped' indicates the optical interface is not equipped with a laser.";
            }

            leaf minimum-channel {
                status obsolete;
                type types-port:optical-dwdm-extended-channel;
                description "Indicates the minimum DWDM ITU channel supported by a tunable optical interface.";
            }

            leaf maximum-channel {
                status obsolete;
                type types-port:optical-dwdm-extended-channel;
                description "Indicates the maximum DWDM ITU channel supported by a tunable optical interface.";
            }

            leaf oper-frequency {
                type types-port:optical-dwdm-frequency;
                description "Indicates the frequency that the equipped optical module is operating at.";
            }

            leaf minimum-frequency {
                type types-port:optical-dwdm-frequency;
                description "Indicates the minimum frequency supported by the equipped optical module.";
            }

            leaf maximum-frequency {
                type types-port:optical-dwdm-frequency;
                description "Indicates the maximum frequency supported by the equipped optical module.";
            }

            leaf supported-grids {
                type bits {
                    bit grid-100-ghz                   { position 0; }
                    bit grid-75-ghz                    { position 1; }
                    bit grid-50-ghz                    { position 2; }
                    bit grid-33-ghz                    { position 3; }
                    bit grid-25-ghz                    { position 4; }
                    bit grid-12500-mhz                 { position 5; }
                    bit grid-6250-mhz                  { position 6; }
                    bit grid-3125-mhz                  { position 7; }
                }
                description "Indicates the frequency grids supported by the equipped tunable optical port.";
            }

            container fine-tuning {
                description "Enter the fine-tuning context";

                leaf range {
                    type uint32;
                    units "megahertz";
                    description "Indicates the positive or negative offset that can be applied when using frequency fine tuning. The offset is from a frequency of one of the grids supported by the equipped optical module.";
                }

                leaf resolution {
                    type uint32;
                    units "megahertz";
                    description "Indicates the resolution that can be used for frequency fine tuning.";
                }

            } // container fine-tuning

            container wavetracker {
                status obsolete;
                description "Enter the wavetracker context";

                leaf current-alarms {
                    status obsolete;
                    type types-port:dwdm-wavetracker-report-alarms;
                    description "Indicates which monitored alarms are raised against the port.";
                }

                leaf port-type {
                    status obsolete;
                    type enumeration {
                        enum "unknown"                      { value 0; }
                        enum "fixed"                        { value 1; }
                        enum "pluggable"                    { value 2; }
                    }
                    description "Indicates if the port is fixed or if it supports pluggable equipment.";
                }

                container power-control {
                    status obsolete;
                    description "Enter the power-control context";

                    leaf measured-power {
                        status obsolete;
                        type decimal64 {
                            fraction-digits 2;
                        }
                        units "decibel-milliwatts";
                        description "Indicates the current average output power of the port's transmitted optical signal.";
                    }

                    leaf maximum-power {
                        status obsolete;
                        type decimal64 {
                            fraction-digits 2;
                        }
                        units "decibel-milliwatts";
                        description "Indicates the maximum average output power of the port's transmitted optical signal at end of life.";
                    }

                    leaf minimum-power {
                        status obsolete;
                        type decimal64 {
                            fraction-digits 2;
                        }
                        units "decibel-milliwatts";
                        description "Indicates the maximum average output power of the port's transmitted optical signal at end of life.";
                    }

                    leaf lower-power-margin {
                        status obsolete;
                        type decimal64 {
                            fraction-digits 2;
                        }
                        units "decibel-milliwatts";
                        description "Indicates how much the average output power of the port's transmitted optical signal can be decreased.";
                    }

                    leaf upper-power-margin {
                        status obsolete;
                        type decimal64 {
                            fraction-digits 2;
                        }
                        units "decibel-milliwatts";
                        description "Indicates how much the average output power of the port's transmitted optical signal can be increased.";
                    }

                } // container power-control

                container sff-voa {
                    status obsolete;
                    description "Enter the sff-voa context";

                    leaf equipped {
                        status obsolete;
                        type boolean;
                        description "Indicates whether or not an SFF VOA is present.";
                    }

                    leaf model-number {
                        status obsolete;
                        type types-sros:named-item-255-or-empty;
                        description "Indicates the model number information for the SFF VOA.";
                    }

                    leaf serial-number {
                        status obsolete;
                        type types-sros:named-item-255-or-empty;
                        description "Indicates the serial number information for the SFF VOA.";
                    }

                    leaf type {
                        status obsolete;
                        type enumeration {
                            enum "none"                         { value 0; }
                            enum "fast"                         { value 1; }
                            enum "slow"                         { value 2; }
                        }
                        description "Indicates if the SFP VOA is fast or slow.";
                    }

                } // container sff-voa

            } // container wavetracker

            uses state-port-dwdm-coherent;
        } // container dwdm

    } // grouping state-port-dwdm

}
