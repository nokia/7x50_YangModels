submodule nokia-state-port-ethernet {

    yang-version "1.1";

    belongs-to nokia-state { prefix "state"; }

    import ietf-yang-types                { prefix "yang"; }
    import nokia-sros-yang-extensions     { prefix "sros-ext"; }
    import nokia-types-eth-cfm            { prefix "types-eth-cfm"; }
    import nokia-types-port               { prefix "types-port"; }
    import nokia-types-sros               { prefix "types-sros"; }

    include nokia-state-eth-cfm;
    include nokia-state-port-eth-access;
    include nokia-state-port-eth-dot1x;
    include nokia-state-port-eth-efm-oam;
    include nokia-state-port-eth-egress;
    include nokia-state-port-eth-lldp;
    include nokia-state-port-eth-network;


    sros-ext:sros-major-release "rel22";

    organization "Nokia";

    contact
        "Nokia SR OS Support
         Web: <http://www.nokia.com>";

    description
        "Nokia YANG Data model with operational state for ethernet ports on SR OS based routers.

         Copyright 2016 Nokia. All rights reserved. Reproduction of this document
         is authorized on the condition that the foregoing copyright notice is included.

         This nokia-state-port-ethernet YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";

    revision "2022-02-16";

    grouping state-port-ethernet {
        container ethernet {
            description "Enter the ethernet context";

            leaf current-alarms {
                type types-port:ethernet-report-alarms;
                description "Indicates the current alarms on the Ethernet port.";
            }

            leaf mdi-type {
                type enumeration {
                    enum "unknown"                      { value 0; }
                    enum "mdi"                          { value 1; }
                    enum "mdi-with-crossover"           { value 2; }
                }
                description "Indicates the Media Dependent Interface (MDI) type of the Ethernet port.";
            }

            leaf oper-duplex {
                type types-port:oper-duplex-mode;
                description "Indicates the operational duplex mode of the Ethernet port.";
            }

            leaf oper-speed {
                type uint32;
                units "megabps";
                description "Indicates the operational speed of the Ethernet port.";
            }

            leaf oper-state-change-count {
                type yang:counter32;
                description "Indicates the number of times a physical port state has changed from 'linkDown (3)' to either 'linkUp (4)' or 'up (5)', and from either 'linkUp (4)' or 'up (5)' to 'linkDown (3)'. The count does not include transitions between 'linkUp (4)' and 'up (5)'. This leaf is automatically reset to zero, once the port enters the 'ghost (2)' state.";
            }

            leaf oper-tx-clock {
                type types-port:ethernet-oper-tx-clock;
                description "Indicates the result of Master/Slave resolution on the Ethernet port.";
            }

            leaf eth-bn-egress-rate {
                type int32;
                units "kilobps";
                description "indicates the ETH-BN (Ethernet Bandwidth Notification) egress rate received from the ETH-CFM (Ethernet Connectivity Fault Management) subsystem.";
            }

            leaf oper-egress-rate {
                type union {
                    type uint32;
                    type enumeration {
                        enum "unrestricted"                 { value -1; }
                    }
                }
                units "kilobps";
                description "indicates the operational egress bandwidth (in kilobits per second) that the Ethernet interface can generate. The value is the minimum of the admin egress rate tmnxPortEtherEgressRate, the ETH-BN egress rate tmnxPortEtherEthBnEgressRate, and the port's maximum rate.";
            }

            container crc-monitor {
                description "Enter the crc-monitor context";

                leaf current-alarms {
                    type types-port:ethernet-monitor-report-status;
                    description "Indicates the current status of the Ethernet CRC monitored alarms on the port.";
                }

            } // container crc-monitor

            container dampening {
                description "Enter the dampening context";

                leaf current-penalties {
                    type yang:counter64;
                    description "Indicates the accumulated penalties applied to the port. Penalties are accumulated on every port down event except a system restart.";
                }

                leaf max-penalties {
                    type yang:counter64;
                    description "Indicates the maximum possible value of the accumulated penalties against the port.";
                }

                leaf oper-state {
                    type enumeration {
                        enum "active"                       { value 1; }
                        enum "idle"                         { value 2; }
                    }
                    description "Indicates if the port up state of the port is suppressed or not. The port up state is 'idle' if the value of current-penalties exceeds the value of suppress-threshold. The port up state will be 'active' when current-penalties falls below the value of reuse-threshold.";
                }

            } // container dampening

            container down-when-looped {
                description "Enter the down-when-looped context";

                leaf loop-state {
                    type enumeration {
                        enum "no-loop-detected"             { value 1; }
                        enum "loop-detected"                { value 2; }
                    }
                    description "Indicates whether or not a physical loop has been detected on the Ethernet port.";
                }

            } // container down-when-looped

            container eth-cfm {
                description "Enter the eth-cfm context";

                list mep {
                    key "md-admin-name ma-admin-name mep-id";
                    description "Enter the mep list instance";

                    leaf md-admin-name {
                        type leafref {
                            path "../../../../../eth-cfm/domain/md-admin-name";
                        }
                        description "Maintenance Domain (MD) name";
                    }

                    leaf ma-admin-name {
                        type leafref {
                            path "../../../../../eth-cfm/domain[md-admin-name=current()/../md-admin-name]/association/ma-admin-name";
                        }
                        description "Maintenance Association (MA) name";
                    }

                    leaf mep-id {
                        type types-eth-cfm:mep-id-type;
                        description "Maintenance Endpoint (MEP) ID";
                    }

                    leaf if-index {
                        type uint32;
                        description "Port ID of the MEP.";
                    }

                    leaf oper-mac-address {
                        type yang:mac-address;
                        description "Operational MAC address of the MEP.";
                    }

                    container ais {
                        description "Enter the ais context";

                        container received {
                            description "Enter the received context";

                            leaf ais-packet {
                                type boolean;
                                description "Indicates if the MEP is receiving AIS test frames from one or more of its sub-layer MEPs.";
                            }

                            leaf interval {
                                type uint32 {
                                    range "1|60";
                                }
                                units "seconds";
                                description "Indicates the AIS Interval received in the last AIS Frame.";
                            }

                        } // container received

                        container transmitted {
                            description "Enter the transmitted context";

                            leaf ais-packet {
                                type enumeration {
                                    enum "no-transmit"                  { value 0; }
                                    enum "transmit"                     { value 1; }
                                    enum "pending"                      { value 2; }
                                }
                                description "Indicates if the MEP is transmitting AIS test frames from one or more of its sub-layer MEPs.";
                            }

                        } // container transmitted

                    } // container ais

                    container csf {
                        description "Enter the csf context";

                        container received {
                            description "Enter the received context";

                            leaf state {
                                type enumeration {
                                    enum "los"                          { value 0; }
                                    enum "ais"                          { value 1; }
                                    enum "rdi"                          { value 2; }
                                    enum "dci"                          { value 3; }
                                }
                                description "Indicates the state of the received CSF frames for the MEP. los (0) - Client Loss of Signal ais (1) - Client Forward Defect Indication rdi (2) - Client Reverse Defect Indication dci (3) - Client Defect Clear Indication.";
                            }

                            leaf interval {
                                type uint32 {
                                    range "1|60";
                                }
                                units "seconds";
                                description "Indicates the CSF Interval received in the most recent CSF frame.";
                            }

                        } // container received

                    } // container csf

                    container grace {
                        description "Enter the grace context";

                        container transmitted {
                            description "Enter the transmitted context";

                            leaf grace-notification {
                                type enumeration {
                                    enum "no-transmit"                  { value 0; }
                                    enum "grace"                        { value 1; }
                                    enum "eth-ed"                       { value 2; }
                                }
                                description "Indicates the state of the MEP grace period PDU transmission.";
                            }

                        } // container transmitted

                        container received {
                            description "Enter the received context";

                            leaf process-grace-notification {
                                type boolean;
                                description "Indicates whether the local MEP is receiving and processing grace notifications from one or more peer MEPs. A value of 'true ' indicates the local MEP is receiving and processing grace from at least one peer MEP. A value of 'false' indicates that no peer grace notifications are being received and processed.";
                            }

                        } // container received

                    } // container grace

                    container ccm-states {
                        description "Enter the ccm-states context";

                        leaf transmit-status {
                            type enumeration {
                                enum "no-transmit"                  { value 0; }
                                enum "transmit"                     { value 1; }
                                enum "suppressed"                   { value 2; }
                            }
                            description "Indicates the state of the MEP CCM PDU transmission. Values: noTransmit (0) - no CCM PDUs are being transmitted by the MEP transmit (1) - MEP is currently transmitting CCM PDUs suppressed (2) - MEP should be transmitting CCM PDUs but is suppressing them due to an internal condition";
                        }

                        leaf sequence-error {
                            type yang:counter32;
                            description "The total number of out-of-sequence CCMs received from all remote MEPs.";
                        }

                        leaf fng-state {
                            type types-eth-cfm:fng-state-type;
                            description "Current state of the MEP Fault Notification Generator State Machine.";
                        }

                        container transmitted {
                            description "Enter the transmitted context";

                            leaf count {
                                type yang:counter32;
                                description "Total number of CCMs transmitted.";
                            }

                            leaf interface-status {
                                type types-eth-cfm:interface-status;
                                description "Indicates the interface status TLV information included in the most recent Connectivity Check Message (CCM) transmission from the local MEP. If the local MEP CCM transmissions are not enabled, or if no interface status TLV was included in the most recent transmission, then ccm-tx-if-status will return a value of is-no-interface-status-tlv (0).";
                            }

                            leaf port-status {
                                type types-eth-cfm:port-status;
                                description "Indicates the port status TLV information included in the most recent Connectivity Check Message (CCM) transmission from the local MEP. If the local MEP CCM transmissions are not enabled, or if no port status TLV was included in the most recent transmission, then ccm-tx-port-status will return a value of ps-no-port-state-tlv (0).";
                            }

                            leaf remote-defect-indicator {
                                type boolean;
                                description "Indicates whether or not the Remote Defect Indication (RDI) bit was set on the most recent Connectivity Check Message (CCM) transmission from the local MEP. If the local MEP CCM transmissions are not eanbled, or if the RDI bit was not set in the most recent transmission, then ccm-tx-rdi will return a value of 'false (2)'.";
                            }

                        } // container transmitted

                        container received {
                            description "Enter the received context";

                            leaf highest-priority-defect {
                                type types-eth-cfm:highest-priority-defect-type;
                                description "The highest priority defect that has been present since the MEPs Fault Notification Generator State Machine was last in the reset state.";
                            }

                            leaf defect-flags {
                                type types-eth-cfm:mep-defect-flags;
                                description "A vector of boolean error conditions, any of which may be true.";
                            }

                            list remote-mep-peer {
                                key "remote-mep-id";
                                description "Enter the remote-mep-peer list instance";

                                leaf remote-mep-id {
                                    type types-eth-cfm:mep-id-type;
                                    description "The Remote MEP ID within the same Maintenance Association.";
                                }

                                leaf auto-discovered {
                                    type boolean;
                                    description "Specifies whether or not the remote peer was automatically discovered ('true') or not. Auto-discovered remote peers are created by the system only, and are of a 'volatile' storage type. Specifying the value of 'false' will mark an auto-discovered remote peer as permanently configured.";
                                }

                                leaf receiving-ccm {
                                    type types-eth-cfm:remote-mep-state-type;
                                    description "The operational CCM receiving state of the remote MEP.";
                                }

                                leaf ccm-status-since {
                                    type yang:date-and-time;
                                    description "The time at which the Remote MEP last entered either the mep-failed or mep-ok state.";
                                }

                                leaf peer-mac-address {
                                    type yang:mac-address;
                                    description "The MAC address of the remote MEP.";
                                }

                                leaf receiving-remote-defect-indicator {
                                    type boolean;
                                    description "State of the RDI bit in the last received CCM (true for rdi=1), or false if none has been received.";
                                }

                                leaf port-status-tlv {
                                    type types-eth-cfm:port-status;
                                    description "An enumerated value of the Port status TLV received in the last CCM from the remote MEP or the default value ps-no-port-state-tlv indicating either no CCM has been received, or that no port status TLV was received in the last CCM.";
                                }

                                leaf interface-status-tlv {
                                    type types-eth-cfm:interface-status;
                                    description "An enumerated value of the Interface status TLV received in the last CCM from the remote MEP or the default value is-no-interface-status-tlv indicating either no CCM has been received, or that no interface status TLV was received in the last CCM.";
                                }

                            } // list remote-mep-peer

                        } // container received

                    } // container ccm-states

                    container mc-lag {
                        description "Enter the mc-lag context";

                        leaf inactive-state {
                            type enumeration {
                                enum "not-applicable"               { value 0; }
                                enum "standby"                      { value 1; }
                                enum "active"                       { value 2; }
                            }
                            description "Indicates the MC-LAG inactive state of the mep. The value of system/eth-cfm/redundancy/mc-lag/standby-mep must be 'true (1)' on the node for this leaf to have meaning.";
                        }

                    } // container mc-lag

                    container statistics {
                        description "Enter the statistics context";

                        list opcode {
                            key "opcode-name";
                            description "Enter the opcode list instance";

                            leaf opcode-name {
                                type types-eth-cfm:statistics-opcode-name;
                                description "Integer that defines which CFM PDU Opcode the statictics refer to.";
                            }

                            leaf transmitted {
                                type yang:counter32;
                                description "The total number of PDUs transmitted from the node with the specified Opcode.";
                            }

                            leaf received {
                                type yang:counter32;
                                description "The total number of PDUs received on the node with the specified Opcode.";
                            }

                        } // list opcode

                    } // container statistics

                    container eth-bn {
                        description "Enter the eth-bn context";

                        leaf update-pacing-timer-seconds-remaining {
                            type types-sros:time-interval;
                            units "centiseconds";
                            description "Indicates the time interval, in centiseconds, until the next report is sent to the MEP port.";
                        }

                        container received {
                            description "Enter the received context";

                            leaf port-id {
                                type uint32;
                                description "Indicates the port id received in the Eth-BN PDU.";
                            }

                            leaf period-seconds {
                                type uint32;
                                units "seconds";
                                description "Indicates the interval in seconds, between reception of ETH-BN PDUs.";
                            }

                            leaf last-reported {
                                type yang:date-and-time;
                                description "Indicates when the most recent ETH-BN report was sent to the MEP port.";
                            }

                            container bandwidth-megabits-per-second {
                                description "Enter the bandwidth-megabits-per-second context";

                                leaf nominal {
                                    type types-eth-cfm:bandwidth-notif-rate;
                                    units "megabps";
                                    description "Indicates the data rate received in the ETH-BN PDU. It is the nominal egress rate of the physical port of the facility MEP. A value of '-1' indicates the rate value is not available.";
                                }

                                leaf current {
                                    type types-eth-cfm:bandwidth-notif-rate;
                                    units "megabps";
                                    description "Indicates the bandwidth of the outdoor radio link received in the ETH-BN PDU. The value advises the physical port to change its egress rate. A value of '-1' indicates that the rate value is not available.";
                                }

                                leaf reported {
                                    type types-eth-cfm:bandwidth-notif-rate;
                                    units "megabps";
                                    description "Indicates the most recent egress rate that the MEP reported to its port. A value of '-1' indicates that the rate value is not available.";
                                }

                            } // container bandwidth-megabits-per-second

                        } // container received

                    } // container eth-bn

                } // list mep

            } // container eth-cfm

            container elmi {
                description "Enter the elmi context";

                leaf link-status {
                    type enumeration {
                        enum "up"                           { value 1; }
                        enum "down"                         { value 2; }
                    }
                    description "Indicates the operational status of the Ethernet LMI interface.";
                }

                list ethernet-virtual-connection {
                    key "vlan-id";
                    description "Enter the ethernet-virtual-connection list instance";

                    leaf vlan-id {
                        type types-sros:encap-val;
                        description "Specifies the VLAN Identifier of the EVC.";
                    }

                    leaf identifier {
                        type string {
                            length "0..100";
                        }
                        description "Indicates the unique value used in ELMI validation.";
                    }

                    leaf status {
                        type enumeration {
                            enum "not-active"                   { value 0; }
                            enum "new-and-not-active"           { value 1; }
                            enum "active"                       { value 2; }
                            enum "new-and-active"               { value 3; }
                            enum "partially-active"             { value 4; }
                            enum "new-and-partially-active"     { value 5; }
                        }
                        description "Indicates the status reported in the EVC Status Information Element.";
                    }

                    leaf status-time {
                        type yang:date-and-time;
                        description "Indicates the time when status changed state.";
                    }

                    leaf type {
                        type enumeration {
                            enum "point-to-point"               { value 0; }
                            enum "multipoint-to-multipoint"     { value 1; }
                        }
                        description "Indicates the type of EVC.";
                    }

                } // list ethernet-virtual-connection

                container user-network-interface {
                    description "Enter the user-network-interface context";

                    leaf identifier {
                        type string {
                            length "0..64";
                        }
                        description "Indicates the UNI identifier of the E-LMI entity.";
                    }

                    leaf type {
                        type enumeration {
                            enum "not-used"                     { value 0; }
                            enum "all-to-one-bundling"          { value 1; }
                            enum "svc-multiplex-no-bundling"    { value 2; }
                            enum "bundling"                     { value 3; }
                        }
                        description "Indicates the information retrieved from the CE-VLAN ID/EVC Map Type contained in the UNI Status Information Element.";
                    }

                } // container user-network-interface

                container statistics {
                    description "Enter the statistics context";

                    container received {
                        description "Enter the received context";

                        leaf discarded-messages {
                            type yang:counter32;
                            description "Indicates the number of times the ELMI agent discarded a received message because it wasn't expecting it, the type of message was incorrect, or the contents of the message were invalid.";
                        }

                        leaf invalid-sequence-number-messages {
                            type yang:counter32;
                            description "Indicates the number of times the ELMI agent received a message with an invalid receive sequence number: i.e. a sequence number that does not match the last transmitted sequence number of the agent.";
                        }

                        leaf status-check-message-time {
                            type yang:date-and-time;
                            description "Indicates the time of the last received ELMI Status Check message.";
                        }

                        leaf status-enquiry-messages {
                            type yang:counter32;
                            description "Indicates the number of ELMI Status Enquiry messages received on this Ethernet interface.";
                        }

                        leaf status-enquiry-message-time {
                            type yang:date-and-time;
                            description "Indicates the time of the last received ELMI Status Enquiry message.";
                        }

                        leaf status-enquiry-message-timeouts {
                            type yang:counter32;
                            description "Indicates the number of times the ELMI agent did not receive a Status Enquiry message within the allotted time";
                        }

                    } // container received

                    container transmitted {
                        description "Enter the transmitted context";

                        leaf asynchronous-status-messages {
                            type yang:counter32;
                            description "Indicates the number of times the ELMI agent received a message with an invalid receive sequence number: i.e. a sequence number that does not match the last transmitted sequence number of the agent.";
                        }

                        leaf status-check-message-time {
                            type yang:date-and-time;
                            description "Indicates the time of the last transmitted ELMI Status Check message.";
                        }

                        leaf status-messages {
                            type yang:counter32;
                            description "Indicates the number of ELMI Status messages transmitted on this Ethernet interface.";
                        }

                        leaf status-enquiry-message-time {
                            type yang:date-and-time;
                            description "Indicates the time of the last transmitted ELMI Status message.";
                        }

                    } // container transmitted

                } // container statistics

            } // container elmi

            container ssm {
                description "Enter the ssm context";

                leaf received-quality-level {
                    type enumeration {
                        enum "unknown"                      { value 0; }
                        enum "prs"                          { value 1; }
                        enum "stu"                          { value 2; }
                        enum "st2"                          { value 3; }
                        enum "tnc"                          { value 4; }
                        enum "st3e"                         { value 5; }
                        enum "st3"                          { value 6; }
                        enum "smc"                          { value 7; }
                        enum "st4"                          { value 8; }
                        enum "dus"                          { value 9; }
                        enum "prc"                          { value 10; }
                        enum "ssua"                         { value 11; }
                        enum "ssub"                         { value 12; }
                        enum "sec"                          { value 13; }
                        enum "dnu"                          { value 14; }
                        enum "inv"                          { value 15; }
                        enum "pno"                          { value 16; }
                        enum "eec1"                         { value 17; }
                        enum "eec2"                         { value 18; }
                        enum "failed"                       { value 19; }
                    }
                    description "Indicates the quality level of received SSM messages.";
                }

                leaf received-ssm-code {
                    type uint32 {
                        range "0..255";
                    }
                    description "Indicates the SSM code received on the Ethernet Synchronization Messaging Channel of the Ethernet port. This is only meaningful if ssm/admin-state is 'enable', and ssm/received-quality-level is not 'failed'.";
                }

                leaf transmitted-quality-level {
                    type enumeration {
                        enum "reserved0"                    { value 0; }
                        enum "prs"                          { value 1; }
                        enum "stu"                          { value 2; }
                        enum "st2"                          { value 3; }
                        enum "tnc"                          { value 4; }
                        enum "st3e"                         { value 5; }
                        enum "reserved6"                    { value 6; }
                        enum "smc"                          { value 7; }
                        enum "reserved8"                    { value 8; }
                        enum "dus"                          { value 9; }
                        enum "prc"                          { value 10; }
                        enum "ssua"                         { value 11; }
                        enum "ssub"                         { value 12; }
                        enum "reserved13"                   { value 13; }
                        enum "dnu"                          { value 14; }
                        enum "reserved15"                   { value 15; }
                        enum "pno"                          { value 16; }
                        enum "eec1"                         { value 17; }
                        enum "eec2"                         { value 18; }
                        enum "reserved19"                   { value 19; }
                    }
                    description "Indicates the quality level of transmitted SSM messages.";
                }

            } // container ssm

            container statistics {
                description "Enter the statistics context";

                leaf in-broadcast-packets {
                    status deprecated;
                    type yang:counter64;
                    description "Indicates the number of packets, delivered by this sub-layer to a higher (sub-)layer, which were addressed to a broadcast address at this sub-layer. Discontinuities in the value of this counter can occur at re-initialization of the management system, and at other times as indicated by the value of counter-discontinuity-time. This leaf was deprecated in release 19.5 on Nokia SROS series systems. It has been replaced by /port/in-broadcast-packets.";
                }

                leaf in-multicast-packets {
                    status deprecated;
                    type yang:counter64;
                    description "Indicates the number of packets, delivered by this sub-layer to a higher (sub-)layer, which were addressed to a multicast address at this sub-layer. For a MAC layer protocol, this includes both Group and Functional addresses. Discontinuities in the value of this counter can occur at re-initialization of the management system, and at other times as indicated by the value of counter-discontinuity-time. This leaf was deprecated in release 19.5 on Nokia SROS series systems. It has been replaced by /port/in-multicast-packets.";
                }

                leaf in-unicast-packets {
                    status deprecated;
                    type yang:counter64;
                    description "Indicates the number of packets, delivered by this sub-layer to a higher (sub-)layer, which were not addressed to a multicast or broadcast address at this sub-layer. Discontinuities in the value of this counter can occur at re-initialization of the management system, and at other times as indicated by the value of counter-discontinuity-time. This leaf was deprecated in release 19.5 on Nokia SROS series systems. It has been replaced by /port/in-unicast-packets.";
                }

                leaf in-errors {
                    status deprecated;
                    type yang:counter32;
                    description "Indicates for packet-oriented interfaces, the number of inbound packets that contained errors preventing them from being deliverable to a higher-layer protocol. For character- oriented or fixed-length interfaces, the number of inbound transmission units that contained errors preventing them from being deliverable to a higher-layer protocol. Discontinuities in the value of this counter can occur at re-initialization of the management system, and at other times as indicated by the value of counter-discontinuity-time. This leaf was deprecated in release 19.5 on Nokia SROS series systems. It has been replaced by /port/in-errors.";
                }

                leaf in-octets {
                    status deprecated;
                    type yang:counter64;
                    description "Indicates the total number of octets received on the interface, including framing characters. Discontinuities in the value of this counter can occur at re-initialization of the management system, and at other times as indicated by the value of counter-discontinuity-time. This leaf was deprecated in release 19.5 on Nokia SROS series systems. It has been replaced by /port/in-octets.";
                }

                leaf in-utilization {
                    type uint32 {
                        range "0..10000";
                    }
                    units "centipercent";
                    description "Indicates the utilization of the port in relation to data received and the port capacity.";
                }

                leaf out-broadcast-packets {
                    status deprecated;
                    type yang:counter64;
                    description "Indicates the total number of packets that higher-level protocols requested be transmitted, and which were addressed to a broadcast address at this sub-layer, including those that were discarded or not sent. Discontinuities in the value of this counter can occur at re-initialization of the management system, and at other times as indicated by the value of counter-discontinuity-time. This leaf was deprecated in release 19.5 on Nokia SROS series systems. It has been replaced by /port/out-broadcast-packets.";
                }

                leaf out-multicast-packets {
                    status deprecated;
                    type yang:counter64;
                    description "Indicates the total number of packets that higher-level protocols requested be transmitted, and which were addressed to a multicast address at this sub-layer, including those that were discarded or not sent. For a MAC layer protocol, this includes both Group and Functional addresses. Discontinuities in the value of this counter can occur at re-initialization of the management system, and at other times as indicated by the value of counter-discontinuity-time. This leaf was deprecated in release 19.5 on Nokia SROS series systems. It has been replaced by /port/out-multicast-packets.";
                }

                leaf out-unicast-packets {
                    status deprecated;
                    type yang:counter64;
                    description "Indicates the total number of packets that higher-level protocols requested be transmitted, and which were not addressed to a multicast or broadcast address at this sub-layer, including those that were discarded or not sent. Discontinuities in the value of this counter can occur at re-initialization of the management system, and at other times as indicated by the value of counter-discontinuity-time. This leaf was deprecated in release 19.5 on Nokia SROS series systems. It has been replaced by /port/out-unicast-packets.";
                }

                leaf out-errors {
                    status deprecated;
                    type yang:counter32;
                    description "Indicates for packet-oriented interfaces, the number of outbound packets that could not be transmitted because of errors. For character-oriented or fixed-length interfaces, the number of outbound transmission units that could not be transmitted because of errors. Discontinuities in the value of this counter can occur at re-initialization of the management system, and at other times as indicated by the value of counter-discontinuity-time. This leaf was deprecated in release 19.5 on Nokia SROS series systems. It has been replaced by /port/out-errors.";
                }

                leaf out-octets {
                    status deprecated;
                    type yang:counter64;
                    description "Indicates the total number of octets transmitted out of the interface, including framing characters. Discontinuities in the value of this counter can occur at re-initialization of the management system, and at other times as indicated by the value of counter-discontinuity-time. This leaf was deprecated in release 19.5 on Nokia SROS series systems. It has been replaced by /port/out-octets.";
                }

                leaf out-utilization {
                    type uint32 {
                        range "0..10000";
                    }
                    units "centipercent";
                    description "Indicates the utilization of the port in relation to data transmitted and the port capacity.";
                }

                leaf collisions {
                    type yang:counter64;
                    description "Indicates the number of collisions that have occurred.";
                }

                leaf crc-align-errors {
                    type yang:counter64;
                    description "Indicates the number of CRC/Align errors that have occurred.";
                }

                leaf drop-events {
                    type yang:counter64;
                    description "Indicates the number of dropped events.";
                }

                leaf fragments {
                    type yang:counter64;
                    description "Indicates the number of fragements.";
                }

                leaf jabbers {
                    type yang:counter64;
                    description "Indicates the number of jabbers.";
                }

                leaf oversize-packets {
                    type yang:counter64;
                    description "Indicates the number of oversize packets received.";
                }

                leaf undersize-packets {
                    type yang:counter64;
                    description "Indicates the number of undersize packets received.";
                }

                leaf total-broadcast-packets {
                    type yang:counter64;
                    description "Indicates the total number of broadcast packets received.";
                }

                leaf total-multicast-packets {
                    type yang:counter64;
                    description "Indicates the total number of multicast packets received.";
                }

                leaf total-octets {
                    type yang:counter64;
                    description "Indicates the total number of octets received.";
                }

                leaf total-packets {
                    type yang:counter64;
                    description "Indicates the total number of packets received.";
                }

                container ethernet-like-medium {
                    description "Enter the ethernet-like-medium context";

                    leaf frame-too-long {
                        type yang:counter64;
                        description "Indicates a count of frames received on a particular interface that exceed the maximum permitted frame size.";
                    }

                    container collision {
                        description "Enter the collision context";

                        leaf excessive {
                            type yang:counter64;
                            description "Indicates a count of frames for which transmission on a particular interface fails due to excessive collisions.";
                        }

                        leaf late {
                            type yang:counter64;
                            description "Indicates the number of times that a collision is detected on a particular interface later than one slot-time into the transmission of a packet.";
                        }

                        leaf multiple {
                            type yang:counter64;
                            description "Indicates a count of frames that are involved in more than one collision and are subsequently transmitted successfully.";
                        }

                        leaf single {
                            type yang:counter64;
                            description "Indicates a count of frames that are involved in a single collision, and are subsequently transmitted successfully.";
                        }

                    } // container collision

                    container error {
                        description "Enter the error context";

                        leaf alignment {
                            type yang:counter64;
                            description "Indicates a count of frames received on a particular interface that are not an integral number of octets in length and do not pass the FCS check.";
                        }

                        leaf carrier-sense {
                            type yang:counter64;
                            description "Indicates the number of times that the carrier sense condition was lost or never asserted when attempting to transmit a frame on a particular interface.";
                        }

                        leaf fcs {
                            type yang:counter64;
                            description "Indicates a count of frames received on a particular interface that are an integral number of octets in length but do not pass the FCS check.";
                        }

                        leaf internal-mac-transmitted {
                            type yang:counter64;
                            description "Indicates a count of frames for which transmission on a particular interface fails due to an internal MAC sublayer transmit error.";
                        }

                        leaf sqe-test {
                            type yang:counter64;
                            description "Indicates a count of times that the SQE test error is received on a particular interface.";
                        }

                        leaf symbol {
                            type yang:counter64;
                            description "Indicates the number of times there was an invalid data symbol when a valid carrier was present.";
                        }

                    } // container error

                    container pause {
                        description "Enter the pause context";

                        leaf frames-received {
                            type yang:counter64;
                            description "Indicates a count of MAC Control frames received on this interface with an opcode indicating the PAUSE operation.";
                        }

                        leaf frames-transmitted {
                            type yang:counter64;
                            description "Indicates a count of MAC Control frames transmitted on this interface with an opcode indicating the PAUSE operation.";
                        }

                    } // container pause

                } // container ethernet-like-medium

                container packet-size {
                    description "Enter the packet-size context";

                    leaf octets-64 {
                        type yang:counter64;
                        description "Indicates the total number of packets received that were 64 octets.";
                    }

                    leaf octets-65-to-127 {
                        type yang:counter64;
                        description "Indicates the total number of packets received where the frame size is between 65 and 127 octets.";
                    }

                    leaf octets-128-to-255 {
                        type yang:counter64;
                        description "Indicates the total number of packets received where the frame size is between 128 and 255 octets.";
                    }

                    leaf octets-256-to-511 {
                        type yang:counter64;
                        description "Indicates the total number of packets received where the frame size is between 256 and 511 octets.";
                    }

                    leaf octets-512-to-1023 {
                        type yang:counter64;
                        description "Indicates the total number of packets received where the frame size is between 512 and 1023 octets.";
                    }

                    leaf octets-1024-to-1518 {
                        type yang:counter64;
                        description "Indicates the total number of packets received where the frame size is between 1024 and 1518 octets.";
                    }

                    leaf octets-1519-to-max {
                        type yang:counter64;
                        description "Indicates the total number of packets received where the frame size is between 1519 and the maximum frame size.";
                    }

                } // container packet-size

            } // container statistics

            container symbol-monitor {
                description "Enter the symbol-monitor context";

                leaf current-alarms {
                    type types-port:ethernet-monitor-report-status;
                    description "Indicates the current status of the Ethernet symbol monitored alarms on the port.";
                }

                leaf total-errors {
                    type yang:counter64;
                    description "Indicates the total number of symbol monitor errors since admin-state was set to enabled.";
                }

            } // container symbol-monitor

            uses state-port-eth-access;
            uses state-port-eth-dot1x;
            uses state-port-eth-efm-oam;
            uses state-port-eth-egress;
            uses state-port-eth-lldp;
            uses state-port-eth-network;
        } // container ethernet

    } // grouping state-port-ethernet

}
