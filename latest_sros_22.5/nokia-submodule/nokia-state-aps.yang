submodule nokia-state-aps {

    yang-version "1.1";

    belongs-to nokia-state { prefix "state"; }

    import ietf-yang-types                { prefix "yang"; }
    import nokia-sros-yang-extensions     { prefix "sros-ext"; }
    import nokia-types-port               { prefix "types-port"; }


    sros-ext:sros-major-release "rel22";

    organization "Nokia";

    contact
        "Nokia SR OS Support
         Web: <http://www.nokia.com>";

    description
        "Nokia YANG Data model with operational state for aps port parameters on SR OS based routers.

         Copyright 2016 Nokia. All rights reserved. Reproduction of this document
         is authorized on the condition that the foregoing copyright notice is included.

         This nokia-state-aps YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";

    revision "2021-04-13";

    grouping state-aps {
        list aps {
            key "group-id";
            description "Enter the aps list instance";

            leaf group-id {
                type uint32 {
                    range "1..128";
                }
                description "APS group ID";
            }

            leaf active-circuit {
                type enumeration {
                    enum "protection"                   { value 0; }
                    enum "working"                      { value 1; }
                    enum "working-1"                    { value 2; }
                    enum "working-2"                    { value 3; }
                }
                description "Indicates the active circuit.";
            }

            leaf annexb-mode {
                type boolean;
                description "Indicates whether APS is in Annex B mode.";
            }

            leaf annexb-active-circuit-type {
                type enumeration {
                    enum "primary"                      { value 0; }
                    enum "secondary"                    { value 1; }
                }
                description "Indicates the active circuit type when in Annex B mode.";
            }

            leaf annexb-last-switchover-command {
                type enumeration {
                    enum "no-command"                   { value 1; }
                    enum "lockout"                      { value 2; }
                    enum "clear"                        { value 3; }
                }
                description "Indicates the last switchover command when in Annex B mode.";
            }

            leaf control-link-state {
                type enumeration {
                    enum "up"                           { value 0; }
                    enum "down-signaling-failure"       { value 1; }
                    enum "down-incompatible-neighbor"   { value 2; }
                }
                description "Indicates the current state of the Multi-Chassis APC group control link.";
            }

            leaf current-aps-status {
                type bits {
                    bit mode-mismatch                  { position 0; }
                    bit channel-mismatch               { position 1; }
                    bit psbf                           { position 2; }
                    bit feplf                          { position 3; }
                    bit extra-traffic                  { position 4; }
                }
                description "Indicates the current status of the APS group.";
            }

            leaf multi-chassis-aps {
                type boolean;
                description "Indicates whether APS is operating in multi-chassis.";
            }

            leaf switching-arch {
                type enumeration {
                    enum "one-plus-one-signalling"      { value 0; }
                    enum "one-plus-one-signalling-and-data" { value 1; }
                }
                description "Indicates the APS switching arch.";
            }

            container k1k2-byte {
                description "Enter the k1k2-byte context";

                leaf received {
                    type string {
                        length "2";
                    }
                    description "Indicates the current value of the K1 and K2 bytes received on the protection channel.";
                }

                leaf transmitted {
                    type string {
                        length "2";
                    }
                    description "Indicates the current value of the K1 and K2 bytes transmitted on the protection channel.";
                }

            } // container k1k2-byte

            container failures {
                description "Enter the failures context";

                leaf protection-switch-byte {
                    type yang:counter32;
                    description "Indicates a count of Protection Switch Byte Failure conditions.";
                }

                leaf far-end-protection-line {
                    type yang:counter32;
                    description "Indicates a count of Far-End Protection-Line Failure conditions.";
                }

            } // container failures

            container mismatches {
                description "Enter the mismatches context";

                leaf channel {
                    type yang:counter32;
                    description "Indicates a count of Channel Mismatch conditions.";
                }

                leaf mode {
                    type yang:counter32;
                    description "Indicates a count of Mode Mismatch conditions.";
                }

            } // container mismatches

            list circuit {
                key "circuit-type";
                description "Enter the circuit list instance";

                leaf circuit-type {
                    type enumeration {
                        enum "protection"                   { value 0; }
                        enum "working"                      { value 1; }
                        enum "working-1"                    { value 2; }
                        enum "working-2"                    { value 3; }
                    }
                    description "Indicates the circuit type.";
                }

                leaf current-aps-status {
                    type bits {
                        bit locked-out                     { position 0; }
                        bit signal-degrade                 { position 1; }
                        bit signal-failure                 { position 2; }
                        bit switched                       { position 3; }
                        bit wait-to-restore                { position 4; }
                    }
                    description "Indicates the current APS status.";
                }

                leaf last-exercise-result {
                    type enumeration {
                        enum "passed"                       { value 1; }
                        enum "failed"                       { value 2; }
                        enum "preempted"                    { value 3; }
                        enum "unknown"                      { value 4; }
                    }
                    description "Indicates the result of the last exercise command.";
                }

                leaf signal-degrade-count {
                    type yang:counter32;
                    description "Indicates a count of signal degrade conditions.";
                }

                leaf signal-failure-count {
                    type yang:counter32;
                    description "Indicates a count of signal degrade conditions.";
                }

                leaf transmit-line-alarm-indication-signal {
                    type yang:counter32;
                    description "Indicates the number of Transmit Line Alarm Indication Signal (Tx L-AIS) occurrences.";
                }

                container switchover {
                    description "Enter the switchover context";

                    leaf occurrences {
                        type yang:counter32;
                        description "Indicates the number of switchover occurrences.";
                    }

                    leaf last-occurrence {
                        type yang:date-and-time;
                        description "Indicates the time at which the last occurrence occurred.";
                    }

                    leaf cumulative-duration {
                        type yang:counter32;
                        units "seconds";
                        description "Indicates the cumulative protection switching duration. For a working channel, this is the cumulative number of seconds that service was carried on the protection line. For the protection line, this is the cumulative number of seconds that the protection line has been use to carry any working channel traffic.";
                    }

                    leaf last-command {
                        type types-port:aps-switch-command;
                        description "Indicates the last command written.";
                    }

                } // container switchover

            } // list circuit

        } // list aps

    } // grouping state-aps

}
