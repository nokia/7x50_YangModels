submodule nokia-state-svc-epipe {

    yang-version "1.1";

    belongs-to nokia-state { prefix "state"; }

    import ietf-yang-types                { prefix "yang"; }
    import nokia-sros-yang-extensions     { prefix "sros-ext"; }
    import nokia-types-card               { prefix "types-card"; }
    import nokia-types-eth-cfm            { prefix "types-eth-cfm"; }
    import nokia-types-mpls               { prefix "types-mpls"; }
    import nokia-types-qos                { prefix "types-qos"; }
    import nokia-types-services           { prefix "types-services"; }
    import nokia-types-sros               { prefix "types-sros"; }

    include nokia-state-eth-cfm;
    include nokia-state-router;
    include nokia-state-router-segment-routing;


    sros-ext:sros-major-release "rel22";

    organization "Nokia";

    contact
        "Nokia SR OS Support
         Web: <http://www.nokia.com>";

    description
        "Nokia YANG Data model with operational state for epipe services on SR OS based routers.

         Copyright 2016 Nokia. All rights reserved. Reproduction of this document
         is authorized on the condition that the foregoing copyright notice is included.

         This nokia-state-svc-epipe YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";

    revision "2022-04-22";

    grouping state-svc-epipe {
        list epipe {
            key "service-name";
            description "Enter the epipe list instance";

            leaf service-name {
                type types-services:service-name;
                description "Administrative service name";
            }

            leaf oper-service-id {
                type types-services:service-id;
                description "Service identifier";
            }

            leaf oper-state {
                type types-sros:oper-state;
                description "Operational state.";
            }

            leaf sap-count {
                type int32;
                description "Number of SAPs";
            }

            leaf sdp-bind-count {
                type int32;
                description "Number of SDP binds";
            }

            leaf template-used {
                type string;
                description "Template used to create this service";
            }

            leaf creation-origin {
                type types-sros:creation-origin;
                description "Creation origin of the service";
            }

            list segment-routing-v6 {
                key "instance";
                description "Enter the segment-routing-v6 list instance";

                leaf instance {
                    type types-services:epipe-srv6-instance;
                    description "Segment routing v6 instance";
                }

                list locator {
                    key "locator-name";
                    description "Enter the locator list instance";

                    leaf locator-name {
                        type leafref {
                            path "../../../../../router/segment-routing/segment-routing-v6/locator/locator-name";
                        }
                        description "SRv6 locator name";
                    }

                    container function {
                        description "Enter the function context";

                        container end-dx2 {
                            description "Enter the end-dx2 context";

                            leaf oper-value {
                                type uint32;
                                description "SRv6 function value.";
                            }

                            leaf status {
                                type types-sros:srv6-error-status;
                                description "specifies the current state of this function.";
                            }

                            leaf segment-identifier {
                                type types-sros:ipv6-address;
                                description "address used in the SRv6 packet.";
                            }

                        } // container end-dx2

                    } // container function

                } // list locator

            } // list segment-routing-v6

            list bgp {
                key "bgp-instance";
                description "Enter the bgp list instance";

                leaf bgp-instance {
                    type int32 {
                        range "1";
                    }
                    description "BGP instance";
                }

                leaf oper-route-distinguisher-type {
                    type types-services:route-distinguisher-type;
                    description "Type of operational route-distinguisher.";
                }

                leaf oper-route-distinguisher {
                    type string;
                    description "Operational route-distinguisher used when advertising NLRIs.";
                }

                container route-target {
                    description "Enter the route-target context";

                    leaf export-origin {
                        type types-services:route-target-origin;
                        description "Origin of route-target export policy";
                    }

                    leaf oper-export {
                        type string;
                        description "Operational route-target used when advertising NLRIs.";
                    }

                    leaf import-origin {
                        type types-services:route-target-origin;
                        description "Origin of route-target import policy";
                    }

                    leaf oper-import {
                        type string;
                        description "Operational route-target used when importing NLRIs.";
                    }

                } // container route-target

            } // list bgp

            container bgp-vpws {
                description "Enter the bgp-vpws context";

                leaf pw-template-name {
                    type string;
                    description "Name of PW template used in transmitting BGP-VPWS NLRI information for this VPWS edge";
                }

            } // container bgp-vpws

            list endpoint {
                key "name";
                description "Enter the endpoint list instance";

                leaf name {
                    type types-sros:named-item;
                    description "Service endpoint name";
                }

                leaf revert-time-count-down {
                    type types-services:revert-time;
                    units "seconds";
                    description "The count down timer that is used before reverting back to the primary spoke-sdp defined on this service endpoint, after having failed over to a backup spoke-sdp. This count down timer begins after primary Spoke SDP becomes operational.";
                }

                leaf creation-origin {
                    type enumeration {
                        enum "manual"                       { value 0; }
                        enum "bgp-vpws"                     { value 1; }
                    }
                    description "The origin mechanism used to create this endpoint.";
                }

                container tx-active {
                    description "Enter the tx-active context";

                    leaf type {
                        type enumeration {
                            enum "none"                         { value 0; }
                            enum "sap"                          { value 1; }
                            enum "sdp-bind"                     { value 2; }
                            enum "sdp-fec"                      { value 3; }
                            enum "evpn-mpls"                    { value 4; }
                        }
                        description "The type of endpoint object that is current transmit active.";
                    }

                    leaf object {
                        type string;
                        description "The object that is transmit active";
                    }

                    leaf change-count {
                        type uint32;
                        description "The number of times active transmit change has taken place.";
                    }

                    leaf up-time {
                        type uint32;
                        units "centiseconds";
                        description "The active 'up' time of the endpoint object that is current transmit active.";
                    }

                } // container tx-active

            } // list endpoint

            list spoke-sdp {
                key "sdp-bind-id";
                description "Enter the spoke-sdp list instance";

                leaf sdp-bind-id {
                    type types-services:sdp-bind-id;
                    description "SDP binding ID";
                }

                leaf oper-state {
                    type enumeration {
                        enum "up"                           { value 1; }
                        enum "down"                         { value 5; }
                    }
                    description "Indicates the operating status of this Service-SDP binding.";
                }

                leaf oper-flags {
                    type bits {
                        bit sdp-bind-admin-down            { position 0; }
                        bit svc-admin-down                 { position 1; }
                        bit stitching-svc-txdown           { position 2; }
                        bit sdp-oper-down                  { position 3; }
                        bit sdp-path-mtu-too-small         { position 4; }
                        bit no-ingress-vc-label            { position 5; }
                        bit no-egress-vc-label             { position 6; }
                        bit svc-mtu-mismatch               { position 7; }
                        bit vc-type-mismatch               { position 8; }
                        bit relearn-limit-exceeded         { position 9; }
                        bit ies-if-admin-down              { position 10; }
                        bit released-ingress-vc-label      { position 11; }
                        bit labels-exhausted               { position 12; }
                        bit svc-param-mismatch             { position 13; }
                        bit insufficient-bandwidth         { position 14; }
                        bit pw-peer-fault-status-bits      { position 15; }
                        bit mesh-sdp-down                  { position 16; }
                        bit not-managed-by-mcring          { position 17; }
                        bit out-of-resource                { position 18; }
                        bit mh-standby                     { position 19; }
                        bit oam-down-mep-fault             { position 20; }
                        bit oam-up-mep-fault               { position 21; }
                        bit standby-sig-slave-tx-down      { position 22; }
                        bit oper-grp-down                  { position 23; }
                        bit withdrawn-ingress-vc-label     { position 24; }
                        bit vpls-pmsi-down                 { position 25; }
                        bit rec-prot-src-mac               { position 26; }
                        bit peer-fault-status-tx-down      { position 27; }
                        bit evpn-route-conflict            { position 28; }
                        bit admin-locked                   { position 29; }
                        bit evpn-p2mp-conflict             { position 30; }
                        bit label-stack-limit-exceeded     { position 31; }
                        bit vccv-bfd-down                  { position 32; }
                        bit stitching-svc-pw-fault         { position 33; }
                    }
                    description "This object indicates all the conditions that affect the operating status of this SDP Bind.";
                }

                leaf pw-peer-status-bits {
                    type bits {
                        bit pw-not-forwarding              { position 0; }
                        bit lac-ingress-fault              { position 1; }
                        bit lac-egress-fault               { position 2; }
                        bit psn-ingress-fault              { position 3; }
                        bit psn-egress-fault               { position 4; }
                        bit pw-fwding-standby              { position 5; }
                    }
                    description "Indicates bits set by the LDP peer when there is a fault on its side of the pseudowire";
                }

                leaf pw-local-status-bits {
                    type bits {
                        bit pw-not-forwarding              { position 0; }
                        bit lac-ingress-fault              { position 1; }
                        bit lac-egress-fault               { position 2; }
                        bit psn-ingress-fault              { position 3; }
                        bit psn-egress-fault               { position 4; }
                        bit pw-fwding-standby              { position 5; }
                    }
                    description "Indicates locally set bits when there is a fault.";
                }

                leaf peer-vccv-cv-bits {
                    type bits {
                        bit icmp-ping                      { position 0; }
                        bit lsp-ping                       { position 1; }
                        bit bfd-fault-detection            { position 2; }
                        bit bfd-fault-detection-and-signalling { position 3; }
                    }
                    description "Indicates CV type bits set by the LDP peer if it supports VCCV.";
                }

                leaf peer-vccv-cc-bits {
                    type bits {
                        bit pwe3-control-word              { position 0; }
                        bit mpls-router-alert-label        { position 1; }
                        bit mpls-pw-demultiplex-or-label   { position 2; }
                    }
                    description "Indicates CC type bits set by the LDP peer if it supports VCCV.";
                }

                leaf oper-control-word {
                    type boolean;
                    description "Status of control word.";
                }

                leaf pw-fault-ip-address {
                    type types-sros:ip-address;
                    description "Faulty IP address sent by peer.";
                }

                leaf class-forwarding-oper-state {
                    type types-sros:oper-state;
                    description "Operational state of forwarding-class based forwarding on this SDP bind.";
                }

                leaf creation-origin {
                    type types-sros:creation-origin;
                    description "Creation origin of the service.";
                }

                leaf oper-hash-label {
                    type boolean;
                    description "Indicates the negotiated value of hash lavel that is used on this SDP binding.";
                }

                leaf min-required-sdp-oper-mtu {
                    type int32;
                    description "Minimum required SDP MTU size used with this SDP binding.";
                }

                container ingress {
                    description "Enter the ingress context";

                    leaf oper-label {
                        type uint32;
                        description "MPLS service label used by the far-end device to send packets to the local PEs sdp-bind.";
                    }

                    container statistics {
                        description "Enter the statistics context";

                        leaf forwarded-packets {
                            type yang:counter64;
                            description "Forwarded packets";
                        }

                        leaf forwarded-octets {
                            type yang:counter64;
                            description "Forwarded octets";
                        }

                        leaf dropped-packets {
                            type yang:counter64;
                            description "Dropped packets";
                        }

                        leaf dropped-octets {
                            type yang:counter64;
                            description "Dropped octets";
                        }

                    } // container statistics

                } // container ingress

                container egress {
                    description "Enter the egress context";

                    leaf oper-label {
                        type uint32;
                        description "MPLS service label used to send packets to the far-end device via this sdp-bind.";
                    }

                    container statistics {
                        description "Enter the statistics context";

                        leaf forwarded-packets {
                            type yang:counter64;
                            description "Forwarded packets";
                        }

                        leaf forwarded-octets {
                            type yang:counter64;
                            description "Forwarded octets";
                        }

                    } // container statistics

                } // container egress

                container eth-cfm {
                    description "Enter the eth-cfm context";

                    list mep {
                        key "md-admin-name ma-admin-name mep-id";
                        description "Enter the mep list instance";

                        leaf md-admin-name {
                            type leafref {
                                path "../../../../../../eth-cfm/domain/md-admin-name";
                            }
                            description "Maintenance Domain (MD) name";
                        }

                        leaf ma-admin-name {
                            type leafref {
                                path "../../../../../../eth-cfm/domain[md-admin-name=current()/../md-admin-name]/association/ma-admin-name";
                            }
                            description "Maintenance Association (MA) name";
                        }

                        leaf mep-id {
                            type types-eth-cfm:mep-id-type;
                            description "Maintenance Endpoint (MEP) ID";
                        }

                        leaf if-index {
                            type uint32;
                            description "Port ID of the MEP.";
                        }

                        leaf oper-mac-address {
                            type yang:mac-address;
                            description "Operational MAC address of the MEP.";
                        }

                        container ais {
                            description "Enter the ais context";

                            container received {
                                description "Enter the received context";

                                leaf ais-packet {
                                    type boolean;
                                    description "Indicates if the MEP is receiving AIS test frames from one or more of its sub-layer MEPs.";
                                }

                                leaf interval {
                                    type uint32 {
                                        range "1|60";
                                    }
                                    units "seconds";
                                    description "Indicates the AIS Interval received in the last AIS Frame.";
                                }

                            } // container received

                            container transmitted {
                                description "Enter the transmitted context";

                                leaf ais-packet {
                                    type enumeration {
                                        enum "no-transmit"                  { value 0; }
                                        enum "transmit"                     { value 1; }
                                        enum "pending"                      { value 2; }
                                    }
                                    description "Indicates if the MEP is transmitting AIS test frames from one or more of its sub-layer MEPs.";
                                }

                            } // container transmitted

                        } // container ais

                        container csf {
                            description "Enter the csf context";

                            container received {
                                description "Enter the received context";

                                leaf state {
                                    type enumeration {
                                        enum "los"                          { value 0; }
                                        enum "ais"                          { value 1; }
                                        enum "rdi"                          { value 2; }
                                        enum "dci"                          { value 3; }
                                    }
                                    description "Indicates the state of the received CSF frames for the MEP. los (0) - Client Loss of Signal ais (1) - Client Forward Defect Indication rdi (2) - Client Reverse Defect Indication dci (3) - Client Defect Clear Indication.";
                                }

                                leaf interval {
                                    type uint32 {
                                        range "1|60";
                                    }
                                    units "seconds";
                                    description "Indicates the CSF Interval received in the most recent CSF frame.";
                                }

                            } // container received

                        } // container csf

                        container grace {
                            description "Enter the grace context";

                            container transmitted {
                                description "Enter the transmitted context";

                                leaf grace-notification {
                                    type enumeration {
                                        enum "no-transmit"                  { value 0; }
                                        enum "grace"                        { value 1; }
                                        enum "eth-ed"                       { value 2; }
                                    }
                                    description "Indicates the state of the MEP grace period PDU transmission.";
                                }

                            } // container transmitted

                            container received {
                                description "Enter the received context";

                                leaf process-grace-notification {
                                    type boolean;
                                    description "Indicates whether the local MEP is receiving and processing grace notifications from one or more peer MEPs. A value of 'true ' indicates the local MEP is receiving and processing grace from at least one peer MEP. A value of 'false' indicates that no peer grace notifications are being received and processed.";
                                }

                            } // container received

                        } // container grace

                        container ccm-states {
                            description "Enter the ccm-states context";

                            leaf transmit-status {
                                type enumeration {
                                    enum "no-transmit"                  { value 0; }
                                    enum "transmit"                     { value 1; }
                                    enum "suppressed"                   { value 2; }
                                }
                                description "Indicates the state of the MEP CCM PDU transmission. Values: noTransmit (0) - no CCM PDUs are being transmitted by the MEP transmit (1) - MEP is currently transmitting CCM PDUs suppressed (2) - MEP should be transmitting CCM PDUs but is suppressing them due to an internal condition";
                            }

                            leaf sequence-error {
                                type yang:counter32;
                                description "The total number of out-of-sequence CCMs received from all remote MEPs.";
                            }

                            leaf fng-state {
                                type types-eth-cfm:fng-state-type;
                                description "Current state of the MEP Fault Notification Generator State Machine.";
                            }

                            container transmitted {
                                description "Enter the transmitted context";

                                leaf count {
                                    type yang:counter32;
                                    description "Total number of CCMs transmitted.";
                                }

                                leaf interface-status {
                                    type types-eth-cfm:interface-status;
                                    description "Indicates the interface status TLV information included in the most recent Connectivity Check Message (CCM) transmission from the local MEP. If the local MEP CCM transmissions are not enabled, or if no interface status TLV was included in the most recent transmission, then ccm-tx-if-status will return a value of is-no-interface-status-tlv (0).";
                                }

                                leaf port-status {
                                    type types-eth-cfm:port-status;
                                    description "Indicates the port status TLV information included in the most recent Connectivity Check Message (CCM) transmission from the local MEP. If the local MEP CCM transmissions are not enabled, or if no port status TLV was included in the most recent transmission, then ccm-tx-port-status will return a value of ps-no-port-state-tlv (0).";
                                }

                                leaf remote-defect-indicator {
                                    type boolean;
                                    description "Indicates whether or not the Remote Defect Indication (RDI) bit was set on the most recent Connectivity Check Message (CCM) transmission from the local MEP. If the local MEP CCM transmissions are not eanbled, or if the RDI bit was not set in the most recent transmission, then ccm-tx-rdi will return a value of 'false (2)'.";
                                }

                            } // container transmitted

                            container received {
                                description "Enter the received context";

                                leaf highest-priority-defect {
                                    type types-eth-cfm:highest-priority-defect-type;
                                    description "The highest priority defect that has been present since the MEPs Fault Notification Generator State Machine was last in the reset state.";
                                }

                                leaf defect-flags {
                                    type types-eth-cfm:mep-defect-flags;
                                    description "A vector of boolean error conditions, any of which may be true.";
                                }

                                list remote-mep-peer {
                                    key "remote-mep-id";
                                    description "Enter the remote-mep-peer list instance";

                                    leaf remote-mep-id {
                                        type types-eth-cfm:mep-id-type;
                                        description "The Remote MEP ID within the same Maintenance Association.";
                                    }

                                    leaf auto-discovered {
                                        type boolean;
                                        description "Specifies whether or not the remote peer was automatically discovered ('true') or not. Auto-discovered remote peers are created by the system only, and are of a 'volatile' storage type. Specifying the value of 'false' will mark an auto-discovered remote peer as permanently configured.";
                                    }

                                    leaf receiving-ccm {
                                        type types-eth-cfm:remote-mep-state-type;
                                        description "The operational CCM receiving state of the remote MEP.";
                                    }

                                    leaf ccm-status-since {
                                        type yang:date-and-time;
                                        description "The time at which the Remote MEP last entered either the mep-failed or mep-ok state.";
                                    }

                                    leaf peer-mac-address {
                                        type yang:mac-address;
                                        description "The MAC address of the remote MEP.";
                                    }

                                    leaf receiving-remote-defect-indicator {
                                        type boolean;
                                        description "State of the RDI bit in the last received CCM (true for rdi=1), or false if none has been received.";
                                    }

                                    leaf port-status-tlv {
                                        type types-eth-cfm:port-status;
                                        description "An enumerated value of the Port status TLV received in the last CCM from the remote MEP or the default value ps-no-port-state-tlv indicating either no CCM has been received, or that no port status TLV was received in the last CCM.";
                                    }

                                    leaf interface-status-tlv {
                                        type types-eth-cfm:interface-status;
                                        description "An enumerated value of the Interface status TLV received in the last CCM from the remote MEP or the default value is-no-interface-status-tlv indicating either no CCM has been received, or that no interface status TLV was received in the last CCM.";
                                    }

                                } // list remote-mep-peer

                            } // container received

                        } // container ccm-states

                        container mc-lag {
                            description "Enter the mc-lag context";

                            leaf inactive-state {
                                type enumeration {
                                    enum "not-applicable"               { value 0; }
                                    enum "standby"                      { value 1; }
                                    enum "active"                       { value 2; }
                                }
                                description "Indicates the MC-LAG inactive state of the mep. The value of system/eth-cfm/redundancy/mc-lag/standby-mep must be 'true (1)' on the node for this leaf to have meaning.";
                            }

                        } // container mc-lag

                        container statistics {
                            description "Enter the statistics context";

                            list opcode {
                                key "opcode-name";
                                description "Enter the opcode list instance";

                                leaf opcode-name {
                                    type types-eth-cfm:statistics-opcode-name;
                                    description "Integer that defines which CFM PDU Opcode the statictics refer to.";
                                }

                                leaf transmitted {
                                    type yang:counter32;
                                    description "The total number of PDUs transmitted from the node with the specified Opcode.";
                                }

                                leaf received {
                                    type yang:counter32;
                                    description "The total number of PDUs received on the node with the specified Opcode.";
                                }

                            } // list opcode

                        } // container statistics

                    } // list mep

                    list mip {
                        key "primary-vlan";
                        description "Enter the mip list instance";

                        leaf primary-vlan {
                            type types-eth-cfm:vlan-id-or-none;
                            description "VLAN ID to which the MIP is attached";
                        }

                        leaf instantiated {
                            type boolean;
                            description "Indicates if the MIP is instanstiated or not.";
                        }

                        leaf direction {
                            type enumeration {
                                enum "both"                         { value 0; }
                            }
                            description "Indicates the direction in which the MIP faces on the Bridge Port.";
                        }

                        leaf level {
                            type types-eth-cfm:mp-level;
                            description "Indicate the MD (Maintenance Domain) Level at which MHFs (MIP Half Function) are created.";
                        }

                        leaf level-authority {
                            type types-eth-cfm:mip-authority;
                            description "Indicates the authority context used for leaf level of the instatiated MIP.";
                        }

                        leaf mhf-creation {
                            type enumeration {
                                enum "none"                         { value 1; }
                                enum "default"                      { value 2; }
                                enum "explicit"                     { value 3; }
                                enum "defer"                        { value 4; }
                                enum "static"                       { value 32; }
                            }
                            description "A value indicating if the Management entity can create MHFs (MIP Half Function).";
                        }

                        leaf mhf-creation-authority {
                            type types-eth-cfm:mip-authority;
                            description "Indicates the authority context used for leaf mhf-creation of the instatiated MIP.";
                        }

                        leaf id-permission {
                            type types-eth-cfm:permission-type;
                            description "Indicates the sender ID TLV permissions for the instantiated MIP.";
                        }

                        leaf id-permission-authority {
                            type types-eth-cfm:mip-authority;
                            description "Indicates the authority context used for leaf id-permission of the instatiated MIP.";
                        }

                        leaf mip-ltr-priority {
                            type types-eth-cfm:frame-priority;
                            description "Indicates the priority to use in linktrace response frames to be transmitted for this MIP.";
                        }

                        leaf mip-ltr-priority-authority {
                            type types-eth-cfm:mip-authority;
                            description "Indicates the authority context used for leaf mip-ltr-priority of the instatiated MIP.";
                        }

                    } // list mip

                } // container eth-cfm

                container bfd {
                    description "Enter the bfd context";

                    leaf oper-state {
                        type types-services:bfd-oper-state;
                        description "BFD oper state";
                    }

                    leaf remaining-up-time {
                        type int32;
                        units "seconds";
                        description "Remaining uptime";
                    }

                } // container bfd

                container ethernet-segment {
                    description "Enter the ethernet-segment context";

                    leaf name {
                        type types-sros:named-item-or-empty;
                        description "Ethernet segment name.";
                    }

                    leaf oper-state {
                        type types-services:evpn-mh-es-status;
                        description "Operational status of the ethernet-segment.";
                    }

                } // container ethernet-segment

            } // list spoke-sdp

            list bgp-mh-site {
                key "site-name";
                description "Enter the bgp-mh-site list instance";

                leaf site-name {
                    type types-sros:named-item;
                    description "Name for the specific site";
                }

                leaf oper-state {
                    type enumeration {
                        enum "up"                           { value 1; }
                        enum "down"                         { value 2; }
                        enum "out-of-resource"              { value 3; }
                    }
                    description "Operational status of the site";
                }

                leaf active-timer-remain {
                    type uint32;
                    units "seconds";
                    description "Remaining time in the active-timer";
                }

                leaf boot-timer-remain {
                    type uint32;
                    units "seconds";
                    description "Remaining time in the boot-timer";
                }

                leaf min-down-timer-remain {
                    type uint32;
                    units "seconds";
                    description "Remaining time in the down-timer";
                }

                container designated-forwarder {
                    description "Enter the designated-forwarder context";

                    leaf state {
                        type boolean;
                        description "State of designated forwarder";
                    }

                    leaf up-time {
                        type uint32;
                        units "seconds";
                        description "Uptime of the designated forwarder";
                    }

                    leaf change-count {
                        type uint32;
                        description "Number of times designated forwarder has changed";
                    }

                } // container designated-forwarder

            } // list bgp-mh-site

            list sap {
                key "sap-id";
                description "Enter the sap list instance";

                leaf sap-id {
                    type types-sros:sap;
                    description "SAP ID";
                }

                leaf oper-state {
                    type enumeration {
                        enum "up"                           { value 1; }
                        enum "down"                         { value 2; }
                    }
                    description "Operating state of this SAP";
                }

                leaf oper-flags {
                    type types-services:l2-sap-oper-flags;
                    description "Conditions that affect the operating status of this SAP.";
                }

                leaf mirror-state {
                    type enumeration {
                        enum "ingress"                      { value 1; }
                        enum "egress"                       { value 2; }
                        enum "ingress-and-egress"           { value 3; }
                        enum "disabled"                     { value 4; }
                    }
                    description "Indicates whether traffic mirroring has been enabled on this SAP";
                }

                leaf template-used {
                    type types-sros:named-item-or-empty;
                    description "Name of the sap-template used to create this sap.";
                }

                leaf oper-dist-cpu-prot-policy {
                    type types-sros:named-item-or-empty;
                    description "Operational Distributed CPU Protection Policy.";
                }

                container statistics {
                    description "Enter the statistics context";

                } // container statistics

                container ingress {
                    description "Enter the ingress context";

                    container qos {
                        description "Enter the qos context";

                        container sap-ingress {
                            description "Enter the sap-ingress context";

                            container forwarding-engine {
                                description "Enter the forwarding-engine context";

                                container statistics {
                                    description "Enter the statistics context";

                                    leaf dropped-packets {
                                        type yang:counter64;
                                        description "Policy ID";
                                    }

                                    leaf dropped-octets {
                                        type yang:counter64;
                                        description "The number of octets dropped by the ingress packet processor due to: SAP state, ingress MAC, IP or IPv6 filter, same segment discard, bad checksum, etc.";
                                    }

                                    leaf received-valid-packets {
                                        type yang:counter64;
                                        description "The value of received-valid indicates number of received valid packets, as determined by the SAP ingress QoS policy, offered by the packet processor to the traffic manager.";
                                    }

                                    leaf received-valid-octets {
                                        type yang:counter64;
                                        description "The value of received-valid indicates number of received valid octets, as determined by the SAP ingress QoS policy, offered by the packet processor to the traffic manager.";
                                    }

                                    leaf high-priority-offered-packets {
                                        type yang:counter64;
                                        description "The number of high priority packets, as determined by the SAP ingress QoS policy, offered by the packet processor to the traffic manager.";
                                    }

                                    leaf high-priority-offered-octets {
                                        type yang:counter64;
                                        description "The number of high priority octets, as determined by the SAP ingress QoS policy, offered by the packet processor to the traffic manager.";
                                    }

                                    leaf low-priority-offered-packets {
                                        type yang:counter64;
                                        description "The number of low priority packets, as determined by the SAP ingress QoS policy, offered by the packet processor to the traffic manager.";
                                    }

                                    leaf low-priority-offered-octets {
                                        type yang:counter64;
                                        description "The number of low priority octets, as determined by the SAP ingress QoS policy, offered by the packet processor to the traffic manager.";
                                    }

                                    leaf uncolor-offered-packets {
                                        type yang:counter64;
                                        description "The number of uncolored packets, as determined by the SAP ingress QoS policy, offered by the packet processor to the traffic manager.";
                                    }

                                    leaf uncolor-offered-octets {
                                        type yang:counter64;
                                        description "The number of uncolored octets, as determined by the SAP ingress QoS policy, offered by the packet processor to the traffic manager.";
                                    }

                                    leaf managed-offered-packets {
                                        type yang:counter64;
                                        description "The value of managed-offered indicates number of managed multicast packets, as determined by the SAP ingress QoS policy, offered by the packet processor to the traffic manager.";
                                    }

                                    leaf managed-offered-octets {
                                        type yang:counter64;
                                        description "The value of managed-offered indicates number of managed multicast octets, as determined by the SAP ingress QoS policy, offered by the packet processor to the traffic manager.";
                                    }

                                    leaf aggregate-offered-packets {
                                        type yang:counter64;
                                        description "The value of aggregate-offered indicates aggregate number of hi, lo priority and uncolour packets, as determined by the SAP ingress QoS policy, offered by the packet processor to the traffic manager.";
                                    }

                                    leaf aggregate-offered-octets {
                                        type yang:counter64;
                                        description "The value of managed-offered indicates aggregate number of hi, lo priority and uncolour octets, as determined by the SAP ingress QoS policy, offered by the packet processor to the traffic manager.";
                                    }

                                    leaf last-cleared-time {
                                        type yang:date-and-time;
                                        description "Time when the counters in this table were last cleared.";
                                    }

                                } // container statistics

                            } // container forwarding-engine

                            container traffic-manager {
                                description "Enter the traffic-manager context";

                                container statistics {
                                    description "Enter the statistics context";

                                    leaf cpm-packets {
                                        type yang:counter64;
                                        description "The value of cpm-packets indicates ingress traffic in terms of packets destined to CPM associated with this SAP.";
                                    }

                                    leaf cpm-octets {
                                        type yang:counter64;
                                        description "The value of cpm indicates ingress traffic in terms of bytes destined to CPM associated with this SAP.";
                                    }

                                    leaf high-priority-dropped-packets {
                                        type yang:counter64;
                                        description "The number of high priority packets, as determined by the SAP ingress QoS policy, dropped by the traffic manager due to: MBS exceeded, buffer pool limit exceeded, etc.";
                                    }

                                    leaf high-priority-dropped-octets {
                                        type yang:counter64;
                                        description "The number of high priority octets, as determined by the SAP ingress QoS policy, dropped by the traffic manager due to: MBS exceeded, buffer pool limit exceeded, etc.";
                                    }

                                    leaf low-priority-dropped-packets {
                                        type yang:counter64;
                                        description "The number of low priority packets, as determined by the SAP ingress QoS policy, dropped by the traffic manager due to: MBS exceeded, buffer pool limit exceeded, etc.";
                                    }

                                    leaf low-priority-dropped-octets {
                                        type yang:counter64;
                                        description "The number of low priority octets, as determined by the SAP ingress QoS policy, dropped by the traffic manager due to: MBS exceeded, buffer pool limit exceeded, etc.";
                                    }

                                    leaf in-profile-forwarded-packets {
                                        type yang:counter64;
                                        description "The number of in-profile packets (rate below CIR) forwarded by the ingress traffic manager.";
                                    }

                                    leaf in-profile-forwarded-octets {
                                        type yang:counter64;
                                        description "The number of in-profile octets (rate below CIR) forwarded by the ingress traffic manager.";
                                    }

                                    leaf out-profile-forwarded-packets {
                                        type yang:counter64;
                                        description "The number of out-of-profile packets (rate above CIR) forwarded by the ingress traffic manager.";
                                    }

                                    leaf out-profile-forwarded-octets {
                                        type yang:counter64;
                                        description "The number of out-of-profile octets (rate above CIR) forwarded by the ingress traffic manager.";
                                    }

                                    leaf aggregate-forwarded-packets {
                                        type yang:counter64;
                                        description "The aggregate number of in and out-of profile packets forwarded by the ingress traffic manager.";
                                    }

                                    leaf aggregate-forwarded-octets {
                                        type yang:counter64;
                                        description "The aggregate number of in and out-of-profile octets forwarded by the ingress traffic manager.";
                                    }

                                    leaf aggregate-dropped-packets {
                                        type yang:counter64;
                                        description "The aggregate number of in and out-of profile packets, dropped by the traffic manager due to: MBS exceeded, buffer pool limit exceeded, etc.";
                                    }

                                    leaf aggregate-dropped-octets {
                                        type yang:counter64;
                                        description "The aggregate number of in and out-of profile octets, dropped by the traffic manager due to: MBS exceeded, buffer pool limit exceeded, etc.";
                                    }

                                    leaf last-cleared-time {
                                        type yang:date-and-time;
                                        description "Time when the counters in this table were last cleared.";
                                    }

                                } // container statistics

                            } // container traffic-manager

                            container qos-traffic {
                                description "Enter the qos-traffic context";

                                container statistics {
                                    description "Enter the statistics context";

                                    leaf ingress-packets {
                                        type yang:counter64;
                                        description "The number of ingress packets on this SAP.";
                                    }

                                    leaf ingress-octets {
                                        type yang:counter64;
                                        description "The number of ingress octets on this SAP.";
                                    }

                                } // container statistics

                            } // container qos-traffic

                            list queue {
                                key "queue-id";
                                description "Enter the queue list instance";

                                leaf queue-id {
                                    type types-qos:ingress-queue-id;
                                    description "The unique identifier for the queue.";
                                }

                                container statistics {
                                    description "Enter the statistics context";

                                    choice stat-mode {
                                        case unicast-priority {

                                            container unicast-priority {
                                                description "Enter the unicast-priority context";

                                                leaf high-priority-offered-packets {
                                                    type yang:counter64;
                                                    description "The number of high-priority packets offered by packet processor to traffic manager.";
                                                }

                                                leaf high-priority-offered-octets {
                                                    type yang:counter64;
                                                    description "The number of high-priority octets offered by packet processor to traffic manager.";
                                                }

                                                leaf low-priority-offered-packets {
                                                    type yang:counter64;
                                                    description "The number of low-priority packets offered by packet processor to traffic manager.";
                                                }

                                                leaf low-priority-offered-octets {
                                                    type yang:counter64;
                                                    description "The number of low-priority octets offered by packet processor to traffic manager.";
                                                }

                                                leaf high-priority-dropped-packets {
                                                    type yang:counter64;
                                                    description "The number of high-priority packets dropped by packet processor to traffic manager.";
                                                }

                                                leaf high-priority-dropped-octets {
                                                    type yang:counter64;
                                                    description "The number of high-priority octets dropped by packet processor to traffic manager.";
                                                }

                                                leaf low-priority-dropped-packets {
                                                    type yang:counter64;
                                                    description "The number of low-priority packets dropped by packet processor to traffic manager.";
                                                }

                                                leaf low-priority-dropped-octets {
                                                    type yang:counter64;
                                                    description "The number of low-priority octets dropped by packet processor to traffic manager.";
                                                }

                                                leaf in-profile-forwarded-packets {
                                                    type yang:counter64;
                                                    description "The number of in-profile packets (rate below CIR) forwarded.";
                                                }

                                                leaf in-profile-forwarded-octets {
                                                    type yang:counter64;
                                                    description "The number of in-profile octets (rate below CIR) forwarded.";
                                                }

                                                leaf out-profile-forwarded-packets {
                                                    type yang:counter64;
                                                    description "The number of out-of-profile packets (rate below CIR) forwarded.";
                                                }

                                                leaf out-profile-forwarded-octets {
                                                    type yang:counter64;
                                                    description "The number of out-of-profile octets (rate below CIR) forwarded.";
                                                }

                                            } // container unicast-priority

                                        }
                                        case unicast-profile {

                                            container unicast-profile {
                                                description "Enter the unicast-profile context";

                                                leaf color-in-offered-packets {
                                                    type yang:counter64;
                                                    description "The number of color-in packets offered to traffic manager.";
                                                }

                                                leaf color-in-offered-octets {
                                                    type yang:counter64;
                                                    description "The number of color-in octets offered to traffic manager.";
                                                }

                                                leaf color-out-offered-packets {
                                                    type yang:counter64;
                                                    description "The number of color-out packets offered to traffic manager.";
                                                }

                                                leaf color-out-offered-octets {
                                                    type yang:counter64;
                                                    description "The number of color-out octets offered to traffic manager.";
                                                }

                                                leaf color-offered-packets {
                                                    type yang:counter64;
                                                    description "The number of color packets offered to traffic manager.";
                                                }

                                                leaf color-offered-octets {
                                                    type yang:counter64;
                                                    description "The number of color octets offered to traffic manager.";
                                                }

                                                leaf uncolor-offered-packets {
                                                    type yang:counter64;
                                                    description "The number of uncolor packets offered to traffic manager.";
                                                }

                                                leaf uncolor-offered-octets {
                                                    type yang:counter64;
                                                    description "The number of uncolor octets offered to traffic manager.";
                                                }

                                                leaf color-out-dropped-packets {
                                                    type yang:counter64;
                                                    description "The number of color-out packets dropped.";
                                                }

                                                leaf color-out-dropped-octets {
                                                    type yang:counter64;
                                                    description "The number of color-out octets dropped.";
                                                }

                                                leaf color-in-uncolor-dropped-packets {
                                                    type yang:counter64;
                                                    description "The number of color-in/uncolor packets dropped.";
                                                }

                                                leaf color-in-uncolor-dropped-octets {
                                                    type yang:counter64;
                                                    description "The number of color-in/uncolor octets dropped.";
                                                }

                                                leaf in-profile-forwarded-packets {
                                                    type yang:counter64;
                                                    description "The number of in-profile packets (rate below CIR) forwarded.";
                                                }

                                                leaf in-profile-forwarded-octets {
                                                    type yang:counter64;
                                                    description "The number of in-profile octets (rate below CIR) forwarded.";
                                                }

                                                leaf out-profile-forwarded-packets {
                                                    type yang:counter64;
                                                    description "The number of out-of-profile packets (rate below CIR) forwarded.";
                                                }

                                                leaf out-profile-forwarded-octets {
                                                    type yang:counter64;
                                                    description "The number of out-of-profile octets (rate below CIR) forwarded.";
                                                }

                                            } // container unicast-profile

                                        }
                                        case multipoint-priority {

                                            container multipoint-priority {
                                                description "Enter the multipoint-priority context";

                                                leaf high-priority-offered-packets {
                                                    type yang:counter64;
                                                    description "The number of high-priority packets offered by packet processor to traffic manager.";
                                                }

                                                leaf high-priority-offered-octets {
                                                    type yang:counter64;
                                                    description "The number of high-priority octets offered by packet processor to traffic manager.";
                                                }

                                                leaf low-priority-offered-packets {
                                                    type yang:counter64;
                                                    description "The number of low-priority packets offered by packet processor to traffic manager.";
                                                }

                                                leaf low-priority-offered-octets {
                                                    type yang:counter64;
                                                    description "The number of low-priority octets offered by packet processor to traffic manager.";
                                                }

                                                leaf combined-offered-packets {
                                                    type yang:counter64;
                                                    description "The number of combined high and low priority packets offered by packet processor to traffic manager.";
                                                }

                                                leaf combined-offered-octets {
                                                    type yang:counter64;
                                                    description "The number of combined high and low priority octets offered by packet processor to traffic manager.";
                                                }

                                                leaf managed-offered-packets {
                                                    type yang:counter64;
                                                    description "The number of managed packets offered by packet processor to traffic manager.";
                                                }

                                                leaf managed-offered-octets {
                                                    type yang:counter64;
                                                    description "The number of managed octets offered by packet processor to traffic manager.";
                                                }

                                                leaf high-priority-dropped-packets {
                                                    type yang:counter64;
                                                    description "The number of high-priority packets dropped by packet processor to traffic manager.";
                                                }

                                                leaf high-priority-dropped-octets {
                                                    type yang:counter64;
                                                    description "The number of high-priority octets dropped by packet processor to traffic manager.";
                                                }

                                                leaf low-priority-dropped-packets {
                                                    type yang:counter64;
                                                    description "The number of low-priority packets dropped by packet processor to traffic manager.";
                                                }

                                                leaf low-priority-dropped-octets {
                                                    type yang:counter64;
                                                    description "The number of low-priority octets dropped by packet processor to traffic manager.";
                                                }

                                                leaf in-profile-forwarded-packets {
                                                    type yang:counter64;
                                                    description "The number of in-profile packets (rate below CIR) forwarded.";
                                                }

                                                leaf in-profile-forwarded-octets {
                                                    type yang:counter64;
                                                    description "The number of in-profile octets (rate below CIR) forwarded.";
                                                }

                                                leaf out-profile-forwarded-packets {
                                                    type yang:counter64;
                                                    description "The number of out-of-profile packets (rate below CIR) forwarded.";
                                                }

                                                leaf out-profile-forwarded-octets {
                                                    type yang:counter64;
                                                    description "The number of out-of-profile octets (rate below CIR) forwarded.";
                                                }

                                            } // container multipoint-priority

                                        }
                                        case multipoint-profile {

                                            container multipoint-profile {
                                                description "Enter the multipoint-profile context";

                                                leaf color-in-offered-packets {
                                                    type yang:counter64;
                                                    description "The number of color-in packets offered to traffic manager.";
                                                }

                                                leaf color-in-offered-octets {
                                                    type yang:counter64;
                                                    description "The number of color-in octets offered to traffic manager.";
                                                }

                                                leaf color-out-offered-packets {
                                                    type yang:counter64;
                                                    description "The number of color-out packets offered to traffic manager.";
                                                }

                                                leaf color-out-offered-octets {
                                                    type yang:counter64;
                                                    description "The number of color-out octets offered to traffic manager.";
                                                }

                                                leaf uncolor-offered-packets {
                                                    type yang:counter64;
                                                    description "The number of uncolor packets offered to traffic manager.";
                                                }

                                                leaf uncolor-offered-octets {
                                                    type yang:counter64;
                                                    description "The number of uncolor octets offered to traffic manager.";
                                                }

                                                leaf combined-offered-packets {
                                                    type yang:counter64;
                                                    description "The number of combined colored in, out and uncolored packets offered to traffic manager.";
                                                }

                                                leaf combined-offered-octets {
                                                    type yang:counter64;
                                                    description "The number of combined colored in, out and uncolored octets offered to traffic manager.";
                                                }

                                                leaf managed-offered-packets {
                                                    type yang:counter64;
                                                    description "The number of managed packets offered by packet processor to traffic manager.";
                                                }

                                                leaf managed-offered-octets {
                                                    type yang:counter64;
                                                    description "The number of managed octets offered by packet processor to traffic manager.";
                                                }

                                                leaf color-out-dropped-packets {
                                                    type yang:counter64;
                                                    description "The number of color-out packets dropped.";
                                                }

                                                leaf color-out-dropped-octets {
                                                    type yang:counter64;
                                                    description "The number of color-out octets dropped.";
                                                }

                                                leaf color-in-uncolor-dropped-packets {
                                                    type yang:counter64;
                                                    description "The number of color-in/uncolor packets dropped.";
                                                }

                                                leaf color-in-uncolor-dropped-octets {
                                                    type yang:counter64;
                                                    description "The number of color-in/uncolor octets dropped.";
                                                }

                                                leaf in-profile-forwarded-packets {
                                                    type yang:counter64;
                                                    description "The number of in-profile packets (rate below CIR) forwarded.";
                                                }

                                                leaf in-profile-forwarded-octets {
                                                    type yang:counter64;
                                                    description "The number of in-profile octets (rate below CIR) forwarded.";
                                                }

                                                leaf out-profile-forwarded-packets {
                                                    type yang:counter64;
                                                    description "The number of out-of-profile packets (rate below CIR) forwarded.";
                                                }

                                                leaf out-profile-forwarded-octets {
                                                    type yang:counter64;
                                                    description "The number of out-of-profile octets (rate below CIR) forwarded.";
                                                }

                                            } // container multipoint-profile

                                        }
                                        case v4-v6 {

                                            container v4-v6 {
                                                description "Enter the v4-v6 context";

                                                leaf ipv4-offered-packets {
                                                    type yang:counter64;
                                                    description "The number of ipv4 packets offered by packet processor to traffic manager.";
                                                }

                                                leaf ipv4-offered-octets {
                                                    type yang:counter64;
                                                    description "The number of ipv4 octets offered by packet processor to traffic manager.";
                                                }

                                                leaf ipv6-offered-packets {
                                                    type yang:counter64;
                                                    description "The number of ipv6 packets offered by packet processor to traffic manager.";
                                                }

                                                leaf ipv6-offered-octets {
                                                    type yang:counter64;
                                                    description "The number of ipv6 octets offered by packet processor to traffic manager.";
                                                }

                                                leaf ipv4-dropped-packets {
                                                    type yang:counter64;
                                                    description "The number of ipv4 packets dropped by packet processor to traffic manager.";
                                                }

                                                leaf ipv4-dropped-octets {
                                                    type yang:counter64;
                                                    description "The number of ipv4 octets dropped by packet processor to traffic manager.";
                                                }

                                                leaf ipv6-dropped-packets {
                                                    type yang:counter64;
                                                    description "The number of ipv6 packets dropped by packet processor to traffic manager.";
                                                }

                                                leaf ipv6-dropped-octets {
                                                    type yang:counter64;
                                                    description "The number of ipv6 octets dropped by packet processor to traffic manager.";
                                                }

                                                leaf ipv4-forwarded-packets {
                                                    type yang:counter64;
                                                    description "The number of ipv4 packets forwarded.";
                                                }

                                                leaf ipv4-forwarded-octets {
                                                    type yang:counter64;
                                                    description "The number of ipv4 octets forwarded.";
                                                }

                                                leaf ipv6-forwarded-packets {
                                                    type yang:counter64;
                                                    description "The number of ipv6 packets forwarded.";
                                                }

                                                leaf ipv6-forwarded-octets {
                                                    type yang:counter64;
                                                    description "The number of ipv6 octets forwarded.";
                                                }

                                            } // container v4-v6

                                        }
                                    }
                                } // container statistics

                                container queue-depth {
                                    description "Enter the queue-depth context";

                                    leaf elapsed-time {
                                        type types-sros:time-interval;
                                        description "Indicated the elapsed time.";
                                    }

                                    leaf depth-0-to-10-percent {
                                        type decimal64 {
                                            fraction-digits 2;
                                        }
                                        description "Indicated the depth 0 to 10 percent.";
                                    }

                                    leaf depth-11-to-20-percent {
                                        type decimal64 {
                                            fraction-digits 2;
                                        }
                                        description "Indicated the depth 0 to 20 percent.";
                                    }

                                    leaf depth-21-to-30-percent {
                                        type decimal64 {
                                            fraction-digits 2;
                                        }
                                        description "Indicated the depth 0 to 30 percent.";
                                    }

                                    leaf depth-31-to-40-percent {
                                        type decimal64 {
                                            fraction-digits 2;
                                        }
                                        description "Indicated the depth 0 to 40 percent.";
                                    }

                                    leaf depth-41-to-50-percent {
                                        type decimal64 {
                                            fraction-digits 2;
                                        }
                                        description "Indicated the depth 0 to 50 percent.";
                                    }

                                    leaf depth-51-to-60-percent {
                                        type decimal64 {
                                            fraction-digits 2;
                                        }
                                        description "Indicated the depth 0 to 60 percent.";
                                    }

                                    leaf depth-61-to-70-percent {
                                        type decimal64 {
                                            fraction-digits 2;
                                        }
                                        description "Indicated the depth 0 to 70 percent.";
                                    }

                                    leaf depth-71-to-80-percent {
                                        type decimal64 {
                                            fraction-digits 2;
                                        }
                                        description "Indicated the depth 0 to 80 percent.";
                                    }

                                    leaf depth-81-to-90-percent {
                                        type decimal64 {
                                            fraction-digits 2;
                                        }
                                        description "Indicated the depth 0 to 90 percent.";
                                    }

                                    leaf depth-91-to-100-percent {
                                        type decimal64 {
                                            fraction-digits 2;
                                        }
                                        description "Indicated the depth 0 to 100 percent.";
                                    }

                                    leaf queue-polling-interval {
                                        type types-sros:time-interval;
                                        description "Indicates the queue polling interval.";
                                    }

                                } // container queue-depth

                            } // list queue

                            list policer {
                                key "policer-id";
                                description "Enter the policer list instance";

                                leaf policer-id {
                                    type types-qos:ingress-policer-id;
                                    description "The unique identifier for the policer.";
                                }

                                container statistics {
                                    description "Enter the statistics context";

                                    choice stat-mode {
                                        case minimal {

                                            container minimal {
                                                description "Enter the minimal context";

                                                leaf all-offered-packets {
                                                    type yang:counter64;
                                                    description "The number of all the priority packets offered by the packet processor to traffic manager";
                                                }

                                                leaf all-offered-octets {
                                                    type yang:counter64;
                                                    description "The number of all the priority octets offered by the packet processor to traffic manager";
                                                }

                                                leaf all-dropped-packets {
                                                    type yang:counter64;
                                                    description "The number of all the priority packets dropped by the packet processor to traffic manager";
                                                }

                                                leaf all-dropped-octets {
                                                    type yang:counter64;
                                                    description "The number of all the priority octets dropped by the packet processor to traffic manager";
                                                }

                                                leaf all-forwarded-packets {
                                                    type yang:counter64;
                                                    description "The number of all the priority packets forwarded by the packet processor to traffic manager";
                                                }

                                                leaf all-forwarded-octets {
                                                    type yang:counter64;
                                                    description "The number of all the priority octets forwarded by the packet processor to traffic manager";
                                                }

                                            } // container minimal

                                        }
                                        case offered-profile-no-cir {

                                            container offered-profile-no-cir {
                                                description "Enter the offered-profile-no-cir context";

                                                leaf in-profile-offered-packets {
                                                    type yang:counter64;
                                                    description "The number of in-profile packets offered by the packet processor to traffic manager";
                                                }

                                                leaf in-profile-offered-octets {
                                                    type yang:counter64;
                                                    description "The number of in-profile octets offered by the packet processor to traffic manager";
                                                }

                                                leaf out-profile-offered-packets {
                                                    type yang:counter64;
                                                    description "The number of out-of-profile packets offered by the packet processor to traffic manager";
                                                }

                                                leaf out-profile-offered-octets {
                                                    type yang:counter64;
                                                    description "The number of out-of-profile octets offered by the packet processor to traffic manager";
                                                }

                                                leaf in-profile-dropped-packets {
                                                    type yang:counter64;
                                                    description "The number of in-profile packets dropped by the packet processor to traffic manager";
                                                }

                                                leaf in-profile-dropped-octets {
                                                    type yang:counter64;
                                                    description "The number of in-profile octets dropped by the packet processor to traffic manager";
                                                }

                                                leaf out-profile-dropped-packets {
                                                    type yang:counter64;
                                                    description "The number of out-of-profile packets dropped by the packet processor to traffic manager";
                                                }

                                                leaf out-profile-dropped-octets {
                                                    type yang:counter64;
                                                    description "The number of out-of-profile octets dropped by the packet processor to traffic manager";
                                                }

                                                leaf in-profile-forwarded-packets {
                                                    type yang:counter64;
                                                    description "The number of in-profile packets forwarded by the packet processor to traffic manager";
                                                }

                                                leaf in-profile-forwarded-octets {
                                                    type yang:counter64;
                                                    description "The number of in-profile octets forwarded by the packet processor to traffic manager";
                                                }

                                                leaf out-profile-forwarded-packets {
                                                    type yang:counter64;
                                                    description "The number of out-of-profile packets forwarded by the packet processor to traffic manager";
                                                }

                                                leaf out-profile-forwarded-octets {
                                                    type yang:counter64;
                                                    description "The number of out-of-profile octets forwarded by the packet processor to traffic manager";
                                                }

                                            } // container offered-profile-no-cir

                                        }
                                        case offered-priority-no-cir {

                                            container offered-priority-no-cir {
                                                description "Enter the offered-priority-no-cir context";

                                                leaf high-priority-offered-packets {
                                                    type yang:counter64;
                                                    description "The number of high-priority packets offered by the packet processor to traffic manager";
                                                }

                                                leaf high-priority-offered-octets {
                                                    type yang:counter64;
                                                    description "The number of high-priority octets offered by the packet processor to traffic manager";
                                                }

                                                leaf low-priority-offered-packets {
                                                    type yang:counter64;
                                                    description "The number of low-priority packets offered by the packet processor to traffic manager";
                                                }

                                                leaf low-priority-offered-octets {
                                                    type yang:counter64;
                                                    description "The number of low-priority octets offered by the packet processor to traffic manager";
                                                }

                                                leaf high-priority-dropped-packets {
                                                    type yang:counter64;
                                                    description "The number of high-priority packets dropped by the packet processor to traffic manager";
                                                }

                                                leaf high-priority-dropped-octets {
                                                    type yang:counter64;
                                                    description "The number of high-priority octets dropped by the packet processor to traffic manager";
                                                }

                                                leaf low-priority-dropped-packets {
                                                    type yang:counter64;
                                                    description "The number of low-priority packets dropped by the packet processor to traffic manager";
                                                }

                                                leaf low-priority-dropped-octets {
                                                    type yang:counter64;
                                                    description "The number of low-priority octets dropped by the packet processor to traffic manager";
                                                }

                                                leaf high-priority-forwarded-packets {
                                                    type yang:counter64;
                                                    description "The number of high-priority packets forwarded by the packet processor to traffic manager";
                                                }

                                                leaf high-priority-forwarded-octets {
                                                    type yang:counter64;
                                                    description "The number of high-priority octets forwarded by the packet processor to traffic manager";
                                                }

                                                leaf low-priority-forwarded-packets {
                                                    type yang:counter64;
                                                    description "The number of low-priority packets forwarded by the packet processor to traffic manager";
                                                }

                                                leaf low-priority-forwarded-octets {
                                                    type yang:counter64;
                                                    description "The number of low-priority octets forwarded by the packet processor to traffic manager";
                                                }

                                            } // container offered-priority-no-cir

                                        }
                                        case offered-profile-cir {

                                            container offered-profile-cir {
                                                description "Enter the offered-profile-cir context";

                                                leaf in-profile-offered-packets {
                                                    type yang:counter64;
                                                    description "The number of in-profile packets offered by the packet processor to traffic manager";
                                                }

                                                leaf in-profile-offered-octets {
                                                    type yang:counter64;
                                                    description "The number of in-profile octets offered by the packet processor to traffic manager";
                                                }

                                                leaf out-profile-offered-packets {
                                                    type yang:counter64;
                                                    description "The number of out-of-profile packets offered by the packet processor to traffic manager";
                                                }

                                                leaf out-profile-offered-octets {
                                                    type yang:counter64;
                                                    description "The number of out-of-profile octets offered by the packet processor to traffic manager";
                                                }

                                                leaf uncolor-offered-packets {
                                                    type yang:counter64;
                                                    description "The number of uncolor packets offered by the packet processor to traffic manager";
                                                }

                                                leaf uncolor-offered-octets {
                                                    type yang:counter64;
                                                    description "The number of uncolor octets offered by the packet processor to traffic manager";
                                                }

                                                leaf in-profile-dropped-packets {
                                                    type yang:counter64;
                                                    description "The number of in-profile packets dropped by the packet processor to traffic manager";
                                                }

                                                leaf in-profile-dropped-octets {
                                                    type yang:counter64;
                                                    description "The number of in-profile octets dropped by the packet processor to traffic manager";
                                                }

                                                leaf out-profile-dropped-packets {
                                                    type yang:counter64;
                                                    description "The number of out-of-profile packets dropped by the packet processor to traffic manager";
                                                }

                                                leaf out-profile-dropped-octets {
                                                    type yang:counter64;
                                                    description "The number of out-of-profile octets dropped by the packet processor to traffic manager";
                                                }

                                                leaf in-profile-forwarded-packets {
                                                    type yang:counter64;
                                                    description "The number of in-profile packets forwarded by the packet processor to traffic manager";
                                                }

                                                leaf in-profile-forwarded-octets {
                                                    type yang:counter64;
                                                    description "The number of in-profile octets forwarded by the packet processor to traffic manager";
                                                }

                                                leaf out-profile-forwarded-packets {
                                                    type yang:counter64;
                                                    description "The number of out-of-profile packets forwarded by the packet processor to traffic manager";
                                                }

                                                leaf out-profile-forwarded-octets {
                                                    type yang:counter64;
                                                    description "The number of out-of-profile octets forwarded by the packet processor to traffic manager";
                                                }

                                            } // container offered-profile-cir

                                        }
                                        case offered-priority-cir {

                                            container offered-priority-cir {
                                                description "Enter the offered-priority-cir context";

                                                leaf high-priority-offered-packets {
                                                    type yang:counter64;
                                                    description "The number of high-priority packets offered by the packet processor to traffic manager";
                                                }

                                                leaf high-priority-offered-octets {
                                                    type yang:counter64;
                                                    description "The number of high-priority octets offered by the packet processor to traffic manager";
                                                }

                                                leaf low-priority-offered-packets {
                                                    type yang:counter64;
                                                    description "The number of low-priority packets offered by the packet processor to traffic manager";
                                                }

                                                leaf low-priority-offered-octets {
                                                    type yang:counter64;
                                                    description "The number of low-priority octets offered by the packet processor to traffic manager";
                                                }

                                                leaf in-profile-dropped-packets {
                                                    type yang:counter64;
                                                    description "The number of in-profile packets dropped by the packet processor to traffic manager";
                                                }

                                                leaf in-profile-dropped-octets {
                                                    type yang:counter64;
                                                    description "The number of in-profile octets dropped by the packet processor to traffic manager";
                                                }

                                                leaf out-profile-dropped-packets {
                                                    type yang:counter64;
                                                    description "The number of out-of-profile packets dropped by the packet processor to traffic manager";
                                                }

                                                leaf out-profile-dropped-octets {
                                                    type yang:counter64;
                                                    description "The number of out-of-profile octets dropped by the packet processor to traffic manager";
                                                }

                                                leaf in-profile-forwarded-packets {
                                                    type yang:counter64;
                                                    description "The number of in-profile packets forwarded by the packet processor to traffic manager";
                                                }

                                                leaf in-profile-forwarded-octets {
                                                    type yang:counter64;
                                                    description "The number of in-profile octets forwarded by the packet processor to traffic manager";
                                                }

                                                leaf out-profile-forwarded-packets {
                                                    type yang:counter64;
                                                    description "The number of out-of-profile packets forwarded by the packet processor to traffic manager";
                                                }

                                                leaf out-profile-forwarded-octets {
                                                    type yang:counter64;
                                                    description "The number of out-of-profile octets forwarded by the packet processor to traffic manager";
                                                }

                                            } // container offered-priority-cir

                                        }
                                        case offered-total-cir {

                                            container offered-total-cir {
                                                description "Enter the offered-total-cir context";

                                                leaf all-offered-packets {
                                                    type yang:counter64;
                                                    description "The number of all the priority packets offered by the packet processor to traffic manager";
                                                }

                                                leaf all-offered-octets {
                                                    type yang:counter64;
                                                    description "The number of all the priority octets offered by the packet processor to traffic manager";
                                                }

                                                leaf in-profile-dropped-packets {
                                                    type yang:counter64;
                                                    description "The number of in-profile packets dropped by the packet processor to traffic manager";
                                                }

                                                leaf in-profile-dropped-octets {
                                                    type yang:counter64;
                                                    description "The number of in-profile octets dropped by the packet processor to traffic manager";
                                                }

                                                leaf out-profile-dropped-packets {
                                                    type yang:counter64;
                                                    description "The number of out-of-profile packets dropped by the packet processor to traffic manager";
                                                }

                                                leaf out-profile-dropped-octets {
                                                    type yang:counter64;
                                                    description "The number of out-of-profile octets dropped by the packet processor to traffic manager";
                                                }

                                                leaf in-profile-forwarded-packets {
                                                    type yang:counter64;
                                                    description "The number of in-profile packets forwarded by the packet processor to traffic manager";
                                                }

                                                leaf in-profile-forwarded-octets {
                                                    type yang:counter64;
                                                    description "The number of in-profile octets forwarded by the packet processor to traffic manager";
                                                }

                                                leaf out-profile-forwarded-packets {
                                                    type yang:counter64;
                                                    description "The number of out-of-profile packets forwarded by the packet processor to traffic manager";
                                                }

                                                leaf out-profile-forwarded-octets {
                                                    type yang:counter64;
                                                    description "The number of out-of-profile octets forwarded by the packet processor to traffic manager";
                                                }

                                            } // container offered-total-cir

                                        }
                                        case offered-limited-profile-cir {

                                            container offered-limited-profile-cir {
                                                description "Enter the offered-limited-profile-cir context";

                                                leaf out-profile-offered-packets {
                                                    type yang:counter64;
                                                    description "The number of out-of-profile packets offered by the packet processor to traffic manager";
                                                }

                                                leaf out-profile-offered-octets {
                                                    type yang:counter64;
                                                    description "The number of out-of-profile octets offered by the packet processor to traffic manager";
                                                }

                                                leaf uncolor-offered-packets {
                                                    type yang:counter64;
                                                    description "The number of uncolor packets offered by the packet processor to traffic manager";
                                                }

                                                leaf uncolor-offered-octets {
                                                    type yang:counter64;
                                                    description "The number of uncolor octets offered by the packet processor to traffic manager";
                                                }

                                                leaf in-profile-dropped-packets {
                                                    type yang:counter64;
                                                    description "The number of in-profile packets dropped by the packet processor to traffic manager";
                                                }

                                                leaf in-profile-dropped-octets {
                                                    type yang:counter64;
                                                    description "The number of in-profile octets dropped by the packet processor to traffic manager";
                                                }

                                                leaf out-profile-dropped-packets {
                                                    type yang:counter64;
                                                    description "The number of out-of-profile packets dropped by the packet processor to traffic manager";
                                                }

                                                leaf out-profile-dropped-octets {
                                                    type yang:counter64;
                                                    description "The number of out-of-profile octets dropped by the packet processor to traffic manager";
                                                }

                                                leaf in-profile-forwarded-packets {
                                                    type yang:counter64;
                                                    description "The number of in-profile packets forwarded by the packet processor to traffic manager";
                                                }

                                                leaf in-profile-forwarded-octets {
                                                    type yang:counter64;
                                                    description "The number of in-profile octets forwarded by the packet processor to traffic manager";
                                                }

                                                leaf out-profile-forwarded-packets {
                                                    type yang:counter64;
                                                    description "The number of out-of-profile packets forwarded by the packet processor to traffic manager";
                                                }

                                                leaf out-profile-forwarded-octets {
                                                    type yang:counter64;
                                                    description "The number of out-of-profile octets forwarded by the packet processor to traffic manager";
                                                }

                                            } // container offered-limited-profile-cir

                                        }
                                        case offered-profile-capped-cir {

                                            container offered-profile-capped-cir {
                                                description "Enter the offered-profile-capped-cir context";

                                                leaf in-profile-offered-packets {
                                                    type yang:counter64;
                                                    description "The number of in-profile packets offered by the packet processor to traffic manager";
                                                }

                                                leaf in-profile-offered-octets {
                                                    type yang:counter64;
                                                    description "The number of in-profile octets offered by the packet processor to traffic manager";
                                                }

                                                leaf out-profile-offered-packets {
                                                    type yang:counter64;
                                                    description "The number of out-of-profile packets offered by the packet processor to traffic manager";
                                                }

                                                leaf out-profile-offered-octets {
                                                    type yang:counter64;
                                                    description "The number of out-of-profile octets offered by the packet processor to traffic manager";
                                                }

                                                leaf uncolor-offered-packets {
                                                    type yang:counter64;
                                                    description "The number of uncolor packets offered by the packet processor to traffic manager";
                                                }

                                                leaf uncolor-offered-octets {
                                                    type yang:counter64;
                                                    description "The number of uncolor octets offered by the packet processor to traffic manager";
                                                }

                                                leaf in-profile-dropped-packets {
                                                    type yang:counter64;
                                                    description "The number of in-profile packets dropped by the packet processor to traffic manager";
                                                }

                                                leaf in-profile-dropped-octets {
                                                    type yang:counter64;
                                                    description "The number of in-profile octets dropped by the packet processor to traffic manager";
                                                }

                                                leaf out-profile-dropped-packets {
                                                    type yang:counter64;
                                                    description "The number of out-of-profile packets dropped by the packet processor to traffic manager";
                                                }

                                                leaf out-profile-dropped-octets {
                                                    type yang:counter64;
                                                    description "The number of out-of-profile octets dropped by the packet processor to traffic manager";
                                                }

                                                leaf in-profile-forwarded-packets {
                                                    type yang:counter64;
                                                    description "The number of in-profile packets forwarded by the packet processor to traffic manager";
                                                }

                                                leaf in-profile-forwarded-octets {
                                                    type yang:counter64;
                                                    description "The number of in-profile octets forwarded by the packet processor to traffic manager";
                                                }

                                                leaf out-profile-forwarded-packets {
                                                    type yang:counter64;
                                                    description "The number of out-of-profile packets forwarded by the packet processor to traffic manager";
                                                }

                                                leaf out-profile-forwarded-octets {
                                                    type yang:counter64;
                                                    description "The number of out-of-profile octets forwarded by the packet processor to traffic manager";
                                                }

                                            } // container offered-profile-capped-cir

                                        }
                                        case offered-profile-with-discards {

                                            container offered-profile-with-discards {
                                                description "Enter the offered-profile-with-discards context";

                                                leaf in-profile-forwarded-packets {
                                                    type yang:counter64;
                                                    description "The number of in-profile packets forwarded by the packet processor to traffic manager";
                                                }

                                                leaf in-profile-forwarded-octets {
                                                    type yang:counter64;
                                                    description "The number of in-profile octets forwarded by the packet processor to traffic manager";
                                                }

                                                leaf out-profile-forwarded-packets {
                                                    type yang:counter64;
                                                    description "The number of out-profile packets forwarded by the packet processor to traffic manager";
                                                }

                                                leaf out-profile-forwarded-octets {
                                                    type yang:counter64;
                                                    description "The number of out-profile octets forwarded by the packet processor to traffic manager";
                                                }

                                                leaf dropped-exceed-profile-packets {
                                                    type yang:counter64;
                                                    description "The number of dropped-exceed-profile packets by the packet processor to traffic manager";
                                                }

                                                leaf dropped-exceed-profile-octets {
                                                    type yang:counter64;
                                                    description "The number of dropped-exceed-profile octets by the packet processor to traffic manager";
                                                }

                                            } // container offered-profile-with-discards

                                        }
                                        case offered-limited-capped-cir {

                                            container offered-limited-capped-cir {
                                                description "Enter the offered-limited-capped-cir context";

                                                leaf in-profile-offered-packets {
                                                    type yang:counter64;
                                                    description "The number of in-profile packets offered by the packet processor to traffic manager";
                                                }

                                                leaf in-profile-offered-octets {
                                                    type yang:counter64;
                                                    description "The number of in-profile octets offered by the packet processor to traffic manager";
                                                }

                                                leaf in-profile-dropped-packets {
                                                    type yang:counter64;
                                                    description "The number of in-profile packets dropped by the packet processor to traffic manager";
                                                }

                                                leaf in-profile-dropped-octets {
                                                    type yang:counter64;
                                                    description "The number of in-profile octets dropped by the packet processor to traffic manager";
                                                }

                                                leaf out-profile-dropped-packets {
                                                    type yang:counter64;
                                                    description "The number of out-of-profile packets dropped by the packet processor to traffic manager";
                                                }

                                                leaf out-profile-dropped-octets {
                                                    type yang:counter64;
                                                    description "The number of out-of-profile octets dropped by the packet processor to traffic manager";
                                                }

                                                leaf in-profile-forwarded-packets {
                                                    type yang:counter64;
                                                    description "The number of in-profile packets forwarded by the packet processor to traffic manager";
                                                }

                                                leaf in-profile-forwarded-octets {
                                                    type yang:counter64;
                                                    description "The number of in-profile octets forwarded by the packet processor to traffic manager";
                                                }

                                                leaf out-profile-forwarded-packets {
                                                    type yang:counter64;
                                                    description "The number of out-of-profile packets forwarded by the packet processor to traffic manager";
                                                }

                                                leaf out-profile-forwarded-octets {
                                                    type yang:counter64;
                                                    description "The number of out-of-profile octets forwarded by the packet processor to traffic manager";
                                                }

                                                leaf uncolor-offered-packets {
                                                    type yang:counter64;
                                                    description "The number of out-of-rofile packets offered by the packet processor to traffic manager";
                                                }

                                                leaf uncolor-offered-octets {
                                                    type yang:counter64;
                                                    description "The number of out-of-profile octets offered by the packet processor to traffic manager";
                                                }

                                            } // container offered-limited-capped-cir

                                        }
                                        case v4-v6 {

                                            container v4-v6 {
                                                description "Enter the v4-v6 context";

                                                leaf ipv4-offered-packets {
                                                    type yang:counter64;
                                                    description "The number of ipv4 packets offered by the packet processor to traffic manager";
                                                }

                                                leaf ipv4-offered-octets {
                                                    type yang:counter64;
                                                    description "The number of ipv4 octets offered by the packet processor to traffic manager";
                                                }

                                                leaf ipv6-offered-packets {
                                                    type yang:counter64;
                                                    description "The number of ipv6 packets offered by the packet processor to traffic manager";
                                                }

                                                leaf ipv6-offered-octets {
                                                    type yang:counter64;
                                                    description "The number of ipv6 octets offered by the packet processor to traffic manager";
                                                }

                                                leaf ipv4-dropped-packets {
                                                    type yang:counter64;
                                                    description "The number of ipv4 packets dropped by the packet processor to traffic manager";
                                                }

                                                leaf ipv4-dropped-octets {
                                                    type yang:counter64;
                                                    description "The number of ipv4 octets dropped by the packet processor to traffic manager";
                                                }

                                                leaf ipv6-dropped-packets {
                                                    type yang:counter64;
                                                    description "The number of ipv6 packets dropped by the packet processor to traffic manager";
                                                }

                                                leaf ipv6-dropped-octets {
                                                    type yang:counter64;
                                                    description "The number of ipv6 octets dropped by the packet processor to traffic manager";
                                                }

                                                leaf ipv4-forwarded-packets {
                                                    type yang:counter64;
                                                    description "The number of ipv4 packets forwarded by the packet processor to traffic manager";
                                                }

                                                leaf ipv4-forwarded-octets {
                                                    type yang:counter64;
                                                    description "The number of ipv4 octets forwarded by the packet processor to traffic manager";
                                                }

                                                leaf ipv6-forwarded-packets {
                                                    type yang:counter64;
                                                    description "The number of ipv6 packets forwarded by the packet processor to traffic manager";
                                                }

                                                leaf ipv6-forwarded-octets {
                                                    type yang:counter64;
                                                    description "The number of ipv6 octets forwarded by the packet processor to traffic manager";
                                                }

                                            } // container v4-v6

                                        }
                                    }
                                } // container statistics

                                list hardware-policer {
                                    key "hardware-policer-string";
                                    description "Enter the hardware-policer list instance";

                                    leaf hardware-policer-string {
                                        type types-sros:named-item-255;
                                        description "Name of the policer formatted by IOM.";
                                    }

                                    leaf adapted-admin-cbs {
                                        type int64;
                                        units "bytes";
                                        description "Admin CBS.";
                                    }

                                    leaf adapted-admin-mbs {
                                        type int64;
                                        units "bytes";
                                        description "Admin MBS.";
                                    }

                                    leaf adapted-hp-only {
                                        type int64;
                                        units "bytes";
                                        description "Hi Prio Only.";
                                    }

                                    leaf depth {
                                        type int64;
                                        units "bytes";
                                        description "Depth.";
                                    }

                                    leaf operational-cir {
                                        type union {
                                            type enumeration {
                                                enum "max"                          { value -1; }
                                            }
                                            type int64;
                                        }
                                        description "Oper CIR.";
                                    }

                                    leaf operational-fir {
                                        type union {
                                            type enumeration {
                                                enum "max"                          { value -1; }
                                            }
                                            type int64;
                                        }
                                        description "Oper FIR.";
                                    }

                                    leaf operational-pir {
                                        type union {
                                            type enumeration {
                                                enum "max"                          { value -1; }
                                            }
                                            type int64;
                                        }
                                        description "Oper PIR.";
                                    }

                                } // list hardware-policer

                            } // list policer

                        } // container sap-ingress

                        container policer-control-policy {
                            description "Enter the policer-control-policy context";

                            list arbiter {
                                key "arbiter-name";
                                description "Enter the arbiter list instance";

                                leaf arbiter-name {
                                    type types-sros:named-item;
                                    description "Specifies the arbiter name.";
                                }

                                container statistics {
                                    description "Enter the statistics context";

                                    leaf forwarded-packets {
                                        type yang:counter64;
                                        description "The number of forwarded packets.";
                                    }

                                    leaf forwarded-octets {
                                        type yang:counter64;
                                        description "The number of forwarded octets.";
                                    }

                                } // container statistics

                            } // list arbiter

                        } // container policer-control-policy

                        container scheduler-policy {
                            description "Enter the scheduler-policy context";

                            list scheduler {
                                key "scheduler-name";
                                description "Enter the scheduler list instance";

                                leaf scheduler-name {
                                    type types-sros:named-item;
                                    description "Specifies the scheduler name.";
                                }

                                container statistics {
                                    description "Enter the statistics context";

                                    leaf forwarded-packets {
                                        type yang:counter64;
                                        description "The number of forwarded packets.";
                                    }

                                    leaf forwarded-octets {
                                        type yang:counter64;
                                        description "The number of forwarded octets.";
                                    }

                                } // container statistics

                            } // list scheduler

                        } // container scheduler-policy

                    } // container qos

                } // container ingress

                container egress {
                    description "Enter the egress context";

                    container vlan-qos {
                        description "Enter the vlan-qos context";

                        list queue {
                            key "queue-id";
                            description "Enter the queue list instance";

                            leaf queue-id {
                                type types-qos:egress-queue-id;
                                description "The unique identifier for the queue.";
                            }

                            container statistics {
                                description "Enter the statistics context";

                                choice stat-mode {
                                    case enqueued-with-discards {

                                        container enqueued-with-discards {
                                            description "Enter the enqueued-with-discards context";

                                            leaf forwarded-packets {
                                                type yang:counter64;
                                                description "The number of packets (rate below CIR) forwarded.";
                                            }

                                            leaf forwarded-octets {
                                                type yang:counter64;
                                                description "The number of octets (rate below CIR) forwarded.";
                                            }

                                            leaf dropped-packets {
                                                type yang:counter64;
                                                description "The number of packets discarded.";
                                            }

                                            leaf dropped-octets {
                                                type yang:counter64;
                                                description "The number of octets discarded.";
                                            }

                                        } // container enqueued-with-discards

                                    }
                                    case enqueued-4-profile-with-discards {

                                        container enqueued-4-profile-with-discards {
                                            description "Enter the enqueued-4-profile-with-discards context";

                                            leaf inplus-profile-forwarded-packets {
                                                type yang:counter64;
                                                description "The number of in-plus-profile packets (rate below CIR) forwarded.";
                                            }

                                            leaf inplus-profile-forwarded-octets {
                                                type yang:counter64;
                                                description "The number of in-plus-profile octets (rate below CIR) forwarded.";
                                            }

                                            leaf inplus-profile-dropped-packets {
                                                type yang:counter64;
                                                description "The number of in-plus-profile packets discarded.";
                                            }

                                            leaf inplus-profile-dropped-octets {
                                                type yang:counter64;
                                                description "The number of in-plus-profile octets discarded.";
                                            }

                                            leaf in-profile-forwarded-packets {
                                                type yang:counter64;
                                                description "The number of in-profile packets (rate below CIR) forwarded.";
                                            }

                                            leaf in-profile-forwarded-octets {
                                                type yang:counter64;
                                                description "The number of in-profile octets (rate below CIR) forwarded.";
                                            }

                                            leaf in-profile-dropped-packets {
                                                type yang:counter64;
                                                description "The number of in-profile packets discarded.";
                                            }

                                            leaf in-profile-dropped-octets {
                                                type yang:counter64;
                                                description "The number of in-profile octets discarded.";
                                            }

                                            leaf out-profile-forwarded-packets {
                                                type yang:counter64;
                                                description "The number of out-profile packets (rate below CIR) forwarded.";
                                            }

                                            leaf out-profile-forwarded-octets {
                                                type yang:counter64;
                                                description "The number of out-profile octets (rate below CIR) forwarded.";
                                            }

                                            leaf out-profile-dropped-packets {
                                                type yang:counter64;
                                                description "The number of out-profile packets discarded.";
                                            }

                                            leaf out-profile-dropped-octets {
                                                type yang:counter64;
                                                description "The number of out-profile octets discarded.";
                                            }

                                            leaf exceed-profile-forwarded-packets {
                                                type yang:counter64;
                                                description "The number of exceed-profile packets (rate above CIR) forwarded.";
                                            }

                                            leaf exceed-profile-forwarded-octets {
                                                type yang:counter64;
                                                description "The number of exceed-profile octets (rate above CIR) forwarded.";
                                            }

                                            leaf exceed-profile-dropped-packets {
                                                type yang:counter64;
                                                description "The number of exceed-profile packets discarded.";
                                            }

                                            leaf exceed-profile-dropped-octets {
                                                type yang:counter64;
                                                description "The number of exceed-profile octets discarded.";
                                            }

                                        } // container enqueued-4-profile-with-discards

                                    }
                                }
                            } // container statistics

                        } // list queue

                    } // container vlan-qos

                    container qos {
                        description "Enter the qos context";

                        container sap-egress {
                            description "Enter the sap-egress context";

                            container traffic-manager {
                                description "Enter the traffic-manager context";

                                container statistics {
                                    description "Enter the statistics context";

                                    leaf in-inplus-profile-dropped-packets {
                                        type yang:counter64;
                                        description "Policy ID";
                                    }

                                    leaf in-inplus-profile-dropped-octets {
                                        type yang:counter64;
                                        description "The number of in-profile octets discarded by the egress traffic manager due to: MBS exceeded, buffer pool limit exceeded, etc.";
                                    }

                                    leaf out-exceed-profile-dropped-packets {
                                        type yang:counter64;
                                        description "The number of out-of-profile packets discarded by the egress traffic manager due to: MBS exceeded, buffer pool limit exceeded, etc.";
                                    }

                                    leaf out-exceed-profile-dropped-octets {
                                        type yang:counter64;
                                        description "The number of out-of-profile packets discarded by the egress traffic manager due to: MBS exceeded, buffer pool limit exceeded, etc.";
                                    }

                                    leaf in-inplus-profile-forwarded-packets {
                                        type yang:counter64;
                                        description "The number of in-profile packets (rate below CIR) forwarded by the egress traffic manager.";
                                    }

                                    leaf in-inplus-profile-forwarded-octets {
                                        type yang:counter64;
                                        description "The number of in-profile octets (rate below CIR) forwarded by the egress traffic manager.";
                                    }

                                    leaf out-exceed-profile-forwarded-packets {
                                        type yang:counter64;
                                        description "The number of out-of-profile packets (rate above CIR) forwarded by the egress traffic manager.";
                                    }

                                    leaf out-exceed-profile-forwarded-octets {
                                        type yang:counter64;
                                        description "The number of out-of-profile octets (rate above CIR) forwarded by the egress traffic manager.";
                                    }

                                    leaf aggregate-forwarded-packets {
                                        type yang:counter64;
                                        description "The aggregate number of in and out-of profile packets forwarded by the egress traffic manager.";
                                    }

                                    leaf aggregate-forwarded-octets {
                                        type yang:counter64;
                                        description "The aggregate number of in and out-of profile octets forwarded by the egress traffic manager.";
                                    }

                                    leaf aggregate-dropped-packets {
                                        type yang:counter64;
                                        description "The aggregate number of in and out-of profile packets discarded by the egress traffic manager due to: MBS exceeded, buffer pool limit exceeded, etc.";
                                    }

                                    leaf aggregate-dropped-octets {
                                        type yang:counter64;
                                        description "The aggregate number of in and out-of profile octets discarded by the egress traffic manager due to: MBS exceeded, buffer pool limit exceeded, etc.";
                                    }

                                    leaf last-cleared-time {
                                        type yang:date-and-time;
                                        description "Time when the counters in this table were last cleared.";
                                    }

                                } // container statistics

                            } // container traffic-manager

                            container qos-traffic {
                                description "Enter the qos-traffic context";

                                container statistics {
                                    description "Enter the statistics context";

                                    leaf egress-packets {
                                        type yang:counter64;
                                        description "The number of egress packets on this SAP.";
                                    }

                                    leaf egress-octets {
                                        type yang:counter64;
                                        description "The number of egress octets on this SAP.";
                                    }

                                } // container statistics

                            } // container qos-traffic

                            list queue {
                                key "queue-id";
                                description "Enter the queue list instance";

                                leaf queue-id {
                                    type types-qos:egress-queue-id;
                                    description "The unique identifier for the queue.";
                                }

                                container queue-depth {
                                    description "Enter the queue-depth context";

                                    leaf elapsed-time {
                                        type types-sros:time-interval;
                                        description "Indicated the elapsed time.";
                                    }

                                    leaf depth-0-to-10-percent {
                                        type decimal64 {
                                            fraction-digits 2;
                                        }
                                        description "Indicated the depth 0 to 10 percent.";
                                    }

                                    leaf depth-11-to-20-percent {
                                        type decimal64 {
                                            fraction-digits 2;
                                        }
                                        description "Indicated the depth 0 to 20 percent.";
                                    }

                                    leaf depth-21-to-30-percent {
                                        type decimal64 {
                                            fraction-digits 2;
                                        }
                                        description "Indicated the depth 0 to 30 percent.";
                                    }

                                    leaf depth-31-to-40-percent {
                                        type decimal64 {
                                            fraction-digits 2;
                                        }
                                        description "Indicated the depth 0 to 40 percent.";
                                    }

                                    leaf depth-41-to-50-percent {
                                        type decimal64 {
                                            fraction-digits 2;
                                        }
                                        description "Indicated the depth 0 to 50 percent.";
                                    }

                                    leaf depth-51-to-60-percent {
                                        type decimal64 {
                                            fraction-digits 2;
                                        }
                                        description "Indicated the depth 0 to 60 percent.";
                                    }

                                    leaf depth-61-to-70-percent {
                                        type decimal64 {
                                            fraction-digits 2;
                                        }
                                        description "Indicated the depth 0 to 70 percent.";
                                    }

                                    leaf depth-71-to-80-percent {
                                        type decimal64 {
                                            fraction-digits 2;
                                        }
                                        description "Indicated the depth 0 to 80 percent.";
                                    }

                                    leaf depth-81-to-90-percent {
                                        type decimal64 {
                                            fraction-digits 2;
                                        }
                                        description "Indicated the depth 0 to 90 percent.";
                                    }

                                    leaf depth-91-to-100-percent {
                                        type decimal64 {
                                            fraction-digits 2;
                                        }
                                        description "Indicated the depth 0 to 100 percent.";
                                    }

                                    leaf queue-polling-interval {
                                        type types-sros:time-interval;
                                        description "Indicates the queue polling interval.";
                                    }

                                    leaf last-violation {
                                        type yang:date-and-time;
                                        description "Indicates the last violation time.";
                                    }

                                    leaf total-threshold-violations {
                                        type yang:counter32;
                                        description "Indicates the total threshold violations.";
                                    }

                                    leaf high-water-mark-polling-interval {
                                        type types-sros:time-duration;
                                        units "microseconds";
                                        description "Indicates the high water mark polling interval.";
                                    }

                                } // container queue-depth

                                container statistics {
                                    description "Enter the statistics context";

                                    choice stat-mode {
                                        case profile {

                                            container profile {
                                                description "Enter the profile context";

                                                leaf in-inplus-profile-forwarded-packets {
                                                    type yang:counter64;
                                                    description "The number of in-profile/in-plus-profile packets (rate below CIR) forwarded.";
                                                }

                                                leaf in-inplus-profile-forwarded-octets {
                                                    type yang:counter64;
                                                    description "The number of in-profile/in-plus-profile octets (rate below CIR) forwarded.";
                                                }

                                                leaf out-exceed-profile-forwarded-packets {
                                                    type yang:counter64;
                                                    description "The number of out-profile/exceed-profile packets (rate above CIR) forwarded.";
                                                }

                                                leaf out-exceed-profile-forwarded-octets {
                                                    type yang:counter64;
                                                    description "The number of out-profile/exceed-profile octets (rate above CIR) forwarded.";
                                                }

                                                leaf in-inplus-profile-dropped-packets {
                                                    type yang:counter64;
                                                    description "The number of in-profile/in-plus-profile packets discarded.";
                                                }

                                                leaf in-inplus-profile-dropped-octets {
                                                    type yang:counter64;
                                                    description "The number of in-profile/in-plus-profile octets discarded.";
                                                }

                                                leaf out-exceed-profile-dropped-packets {
                                                    type yang:counter64;
                                                    description "The number of out-profile/exceed-profile packets discarded.";
                                                }

                                                leaf out-exceed-profile-dropped-octets {
                                                    type yang:counter64;
                                                    description "The number of out-profile/exceed-profile octets discarded.";
                                                }

                                            } // container profile

                                        }
                                        case v4-v6 {

                                            container v4-v6 {
                                                description "Enter the v4-v6 context";

                                                leaf ipv4-dropped-packets {
                                                    type yang:counter64;
                                                    description "The number of ipv4 packets discarded.";
                                                }

                                                leaf ipv4-dropped-octets {
                                                    type yang:counter64;
                                                    description "The number of ipv4 octets discarded.";
                                                }

                                                leaf ipv6-dropped-packets {
                                                    type yang:counter64;
                                                    description "The number of ipv6 packets discarded.";
                                                }

                                                leaf ipv6-dropped-octets {
                                                    type yang:counter64;
                                                    description "The number of ipv6 octets discarded.";
                                                }

                                                leaf ipv4-forwarded-packets {
                                                    type yang:counter64;
                                                    description "The number of ipv4 packets forwarded.";
                                                }

                                                leaf ipv4-forwarded-octets {
                                                    type yang:counter64;
                                                    description "The number of ipv4 octets forwarded.";
                                                }

                                                leaf ipv6-forwarded-packets {
                                                    type yang:counter64;
                                                    description "The number of ipv6 packets forwarded.";
                                                }

                                                leaf ipv6-forwarded-octets {
                                                    type yang:counter64;
                                                    description "The number of ipv6 octets forwarded.";
                                                }

                                            } // container v4-v6

                                        }
                                    }
                                } // container statistics

                            } // list queue

                            list policer {
                                key "policer-id";
                                description "Enter the policer list instance";

                                leaf policer-id {
                                    type types-qos:sap-egress-policer-id;
                                    description "The unique identifier for the policer.";
                                }

                                container statistics {
                                    description "Enter the statistics context";

                                    choice stat-mode {
                                        case minimal {

                                            container minimal {
                                                description "Enter the minimal context";

                                                leaf all-offered-packets {
                                                    type yang:counter64;
                                                    description "The number of all the priority packets offered by the packet processor to traffic manager";
                                                }

                                                leaf all-offered-octets {
                                                    type yang:counter64;
                                                    description "The number of all the priority octets offered by the packet processor to traffic manager";
                                                }

                                                leaf all-dropped-packets {
                                                    type yang:counter64;
                                                    description "The number of all the priority packets dropped by the packet processor to traffic manager";
                                                }

                                                leaf all-dropped-octets {
                                                    type yang:counter64;
                                                    description "The number of all the priority octets dropped by the packet processor to traffic manager";
                                                }

                                                leaf all-forwarded-packets {
                                                    type yang:counter64;
                                                    description "The number of all the priority packets forwarded by the packet processor to traffic manager";
                                                }

                                                leaf all-forwarded-octets {
                                                    type yang:counter64;
                                                    description "The number of all the priority octets forwarded by the packet processor to traffic manager";
                                                }

                                            } // container minimal

                                        }
                                        case offered-profile-no-cir {

                                            container offered-profile-no-cir {
                                                description "Enter the offered-profile-no-cir context";

                                                leaf in-profile-offered-packets {
                                                    type yang:counter64;
                                                    description "The number of in-profile packets offered by the packet processor to traffic manager";
                                                }

                                                leaf in-profile-offered-octets {
                                                    type yang:counter64;
                                                    description "The number of in-profile octets offered by the packet processor to traffic manager";
                                                }

                                                leaf out-profile-offered-packets {
                                                    type yang:counter64;
                                                    description "The number of out-of-profile packets offered by the packet processor to traffic manager";
                                                }

                                                leaf out-profile-offered-octets {
                                                    type yang:counter64;
                                                    description "The number of out-of-profile octets offered by the packet processor to traffic manager";
                                                }

                                                leaf in-profile-dropped-packets {
                                                    type yang:counter64;
                                                    description "The number of in-profile packets dropped by the packet processor to traffic manager";
                                                }

                                                leaf in-profile-dropped-octets {
                                                    type yang:counter64;
                                                    description "The number of in-profile octets dropped by the packet processor to traffic manager";
                                                }

                                                leaf out-profile-dropped-packets {
                                                    type yang:counter64;
                                                    description "The number of out-of-profile packets dropped by the packet processor to traffic manager";
                                                }

                                                leaf out-profile-dropped-octets {
                                                    type yang:counter64;
                                                    description "The number of out-of-profile octets dropped by the packet processor to traffic manager";
                                                }

                                                leaf in-profile-forwarded-packets {
                                                    type yang:counter64;
                                                    description "The number of in-profile packets forwarded by the packet processor to traffic manager";
                                                }

                                                leaf in-profile-forwarded-octets {
                                                    type yang:counter64;
                                                    description "The number of in-profile octets forwarded by the packet processor to traffic manager";
                                                }

                                                leaf out-profile-forwarded-packets {
                                                    type yang:counter64;
                                                    description "The number of out-of-profile packets forwarded by the packet processor to traffic manager";
                                                }

                                                leaf out-profile-forwarded-octets {
                                                    type yang:counter64;
                                                    description "The number of out-of-profile octets forwarded by the packet processor to traffic manager";
                                                }

                                            } // container offered-profile-no-cir

                                        }
                                        case offered-profile-cir {

                                            container offered-profile-cir {
                                                description "Enter the offered-profile-cir context";

                                                leaf in-profile-offered-packets {
                                                    type yang:counter64;
                                                    description "The number of in-profile packets offered by the packet processor to traffic manager";
                                                }

                                                leaf in-profile-offered-octets {
                                                    type yang:counter64;
                                                    description "The number of in-profile octets offered by the packet processor to traffic manager";
                                                }

                                                leaf out-profile-offered-packets {
                                                    type yang:counter64;
                                                    description "The number of out-of-profile packets offered by the packet processor to traffic manager";
                                                }

                                                leaf out-profile-offered-octets {
                                                    type yang:counter64;
                                                    description "The number of out-of-profile octets offered by the packet processor to traffic manager";
                                                }

                                                leaf uncolor-offered-packets {
                                                    type yang:counter64;
                                                    description "The number of uncolor packets offered by the packet processor to traffic manager";
                                                }

                                                leaf uncolor-offered-octets {
                                                    type yang:counter64;
                                                    description "The number of uncolor octets offered by the packet processor to traffic manager";
                                                }

                                                leaf in-profile-dropped-packets {
                                                    type yang:counter64;
                                                    description "The number of in-profile packets dropped by the packet processor to traffic manager";
                                                }

                                                leaf in-profile-dropped-octets {
                                                    type yang:counter64;
                                                    description "The number of in-profile octets dropped by the packet processor to traffic manager";
                                                }

                                                leaf out-profile-dropped-packets {
                                                    type yang:counter64;
                                                    description "The number of out-of-profile packets dropped by the packet processor to traffic manager";
                                                }

                                                leaf out-profile-dropped-octets {
                                                    type yang:counter64;
                                                    description "The number of out-of-profile octets dropped by the packet processor to traffic manager";
                                                }

                                                leaf in-profile-forwarded-packets {
                                                    type yang:counter64;
                                                    description "The number of in-profile packets forwarded by the packet processor to traffic manager";
                                                }

                                                leaf in-profile-forwarded-octets {
                                                    type yang:counter64;
                                                    description "The number of in-profile octets forwarded by the packet processor to traffic manager";
                                                }

                                                leaf out-profile-forwarded-packets {
                                                    type yang:counter64;
                                                    description "The number of out-of-profile packets forwarded by the packet processor to traffic manager";
                                                }

                                                leaf out-profile-forwarded-octets {
                                                    type yang:counter64;
                                                    description "The number of out-of-profile octets forwarded by the packet processor to traffic manager";
                                                }

                                            } // container offered-profile-cir

                                        }
                                        case offered-total-cir {

                                            container offered-total-cir {
                                                description "Enter the offered-total-cir context";

                                                leaf all-offered-packets {
                                                    type yang:counter64;
                                                    description "The number of all the priority packets offered by the packet processor to traffic manager";
                                                }

                                                leaf all-offered-octets {
                                                    type yang:counter64;
                                                    description "The number of all the priority octets offered by the packet processor to traffic manager";
                                                }

                                                leaf in-profile-dropped-packets {
                                                    type yang:counter64;
                                                    description "The number of in-profile packets dropped by the packet processor to traffic manager";
                                                }

                                                leaf in-profile-dropped-octets {
                                                    type yang:counter64;
                                                    description "The number of in-profile octets dropped by the packet processor to traffic manager";
                                                }

                                                leaf out-profile-dropped-packets {
                                                    type yang:counter64;
                                                    description "The number of out-of-profile packets dropped by the packet processor to traffic manager";
                                                }

                                                leaf out-profile-dropped-octets {
                                                    type yang:counter64;
                                                    description "The number of out-of-profile octets dropped by the packet processor to traffic manager";
                                                }

                                                leaf in-profile-forwarded-packets {
                                                    type yang:counter64;
                                                    description "The number of in-profile packets forwarded by the packet processor to traffic manager";
                                                }

                                                leaf in-profile-forwarded-octets {
                                                    type yang:counter64;
                                                    description "The number of in-profile octets forwarded by the packet processor to traffic manager";
                                                }

                                                leaf out-profile-forwarded-packets {
                                                    type yang:counter64;
                                                    description "The number of out-of-profile packets forwarded by the packet processor to traffic manager";
                                                }

                                                leaf out-profile-forwarded-octets {
                                                    type yang:counter64;
                                                    description "The number of out-of-profile octets forwarded by the packet processor to traffic manager";
                                                }

                                            } // container offered-total-cir

                                        }
                                        case offered-limited-capped-cir {

                                            container offered-limited-capped-cir {
                                                description "Enter the offered-limited-capped-cir context";

                                                leaf in-profile-offered-packets {
                                                    type yang:counter64;
                                                    description "The number of in-profile packets offered by the packet processor to traffic manager";
                                                }

                                                leaf in-profile-offered-octets {
                                                    type yang:counter64;
                                                    description "The number of in-profile octets offered by the packet processor to traffic manager";
                                                }

                                                leaf in-profile-dropped-packets {
                                                    type yang:counter64;
                                                    description "The number of in-profile packets dropped by the packet processor to traffic manager";
                                                }

                                                leaf in-profile-dropped-octets {
                                                    type yang:counter64;
                                                    description "The number of in-profile octets dropped by the packet processor to traffic manager";
                                                }

                                                leaf out-profile-dropped-packets {
                                                    type yang:counter64;
                                                    description "The number of out-of-profile packets dropped by the packet processor to traffic manager";
                                                }

                                                leaf out-profile-dropped-octets {
                                                    type yang:counter64;
                                                    description "The number of out-of-profile octets dropped by the packet processor to traffic manager";
                                                }

                                                leaf in-profile-forwarded-packets {
                                                    type yang:counter64;
                                                    description "The number of in-profile packets forwarded by the packet processor to traffic manager";
                                                }

                                                leaf in-profile-forwarded-octets {
                                                    type yang:counter64;
                                                    description "The number of in-profile octets forwarded by the packet processor to traffic manager";
                                                }

                                                leaf out-profile-forwarded-packets {
                                                    type yang:counter64;
                                                    description "The number of out-of-profile packets forwarded by the packet processor to traffic manager";
                                                }

                                                leaf out-profile-forwarded-octets {
                                                    type yang:counter64;
                                                    description "The number of out-of-profile octets forwarded by the packet processor to traffic manager";
                                                }

                                                leaf out-profile-offered-packets {
                                                    type yang:counter64;
                                                    description "The number of out-of-rofile packets offered by the packet processor to traffic manager";
                                                }

                                                leaf out-profile-offered-octets {
                                                    type yang:counter64;
                                                    description "The number of out-of-profile octets offered by the packet processor to traffic manager";
                                                }

                                            } // container offered-limited-capped-cir

                                        }
                                        case offered-profile-capped-cir {

                                            container offered-profile-capped-cir {
                                                description "Enter the offered-profile-capped-cir context";

                                                leaf in-profile-offered-packets {
                                                    type yang:counter64;
                                                    description "The number of in-profile packets offered by the packet processor to traffic manager";
                                                }

                                                leaf in-profile-offered-octets {
                                                    type yang:counter64;
                                                    description "The number of in-profile octets offered by the packet processor to traffic manager";
                                                }

                                                leaf out-profile-offered-packets {
                                                    type yang:counter64;
                                                    description "The number of out-of-profile packets offered by the packet processor to traffic manager";
                                                }

                                                leaf out-profile-offered-octets {
                                                    type yang:counter64;
                                                    description "The number of out-of-profile octets offered by the packet processor to traffic manager";
                                                }

                                                leaf uncolor-offered-packets {
                                                    type yang:counter64;
                                                    description "The number of uncolor packets offered by the packet processor to traffic manager";
                                                }

                                                leaf uncolor-offered-octets {
                                                    type yang:counter64;
                                                    description "The number of uncolor octets offered by the packet processor to traffic manager";
                                                }

                                                leaf in-profile-dropped-packets {
                                                    type yang:counter64;
                                                    description "The number of in-profile packets dropped by the packet processor to traffic manager";
                                                }

                                                leaf in-profile-dropped-octets {
                                                    type yang:counter64;
                                                    description "The number of in-profile octets dropped by the packet processor to traffic manager";
                                                }

                                                leaf out-profile-dropped-packets {
                                                    type yang:counter64;
                                                    description "The number of out-of-profile packets dropped by the packet processor to traffic manager";
                                                }

                                                leaf out-profile-dropped-octets {
                                                    type yang:counter64;
                                                    description "The number of out-of-profile octets dropped by the packet processor to traffic manager";
                                                }

                                                leaf in-profile-forwarded-packets {
                                                    type yang:counter64;
                                                    description "The number of in-profile packets forwarded by the packet processor to traffic manager";
                                                }

                                                leaf in-profile-forwarded-octets {
                                                    type yang:counter64;
                                                    description "The number of in-profile octets forwarded by the packet processor to traffic manager";
                                                }

                                                leaf out-profile-forwarded-packets {
                                                    type yang:counter64;
                                                    description "The number of out-of-profile packets forwarded by the packet processor to traffic manager";
                                                }

                                                leaf out-profile-forwarded-octets {
                                                    type yang:counter64;
                                                    description "The number of out-of-profile octets forwarded by the packet processor to traffic manager";
                                                }

                                            } // container offered-profile-capped-cir

                                        }
                                        case offered-total-cir-exceed {

                                            container offered-total-cir-exceed {
                                                description "Enter the offered-total-cir-exceed context";

                                                leaf all-offered-packets {
                                                    type yang:counter64;
                                                    description "The number of all the priority packets offered by the packet processor to traffic manager";
                                                }

                                                leaf all-offered-octets {
                                                    type yang:counter64;
                                                    description "The number of all the priority octets offered by the packet processor to traffic manager";
                                                }

                                                leaf in-profile-dropped-packets {
                                                    type yang:counter64;
                                                    description "The number of in-profile packets dropped by the packet processor to traffic manager";
                                                }

                                                leaf in-profile-dropped-octets {
                                                    type yang:counter64;
                                                    description "The number of in-profile octets dropped by the packet processor to traffic manager";
                                                }

                                                leaf out-profile-dropped-packets {
                                                    type yang:counter64;
                                                    description "The number of out-of-profile packets dropped by the packet processor to traffic manager";
                                                }

                                                leaf out-profile-dropped-octets {
                                                    type yang:counter64;
                                                    description "The number of out-of-profile octets dropped by the packet processor to traffic manager";
                                                }

                                                leaf exceed-profile-dropped-packets {
                                                    type yang:counter64;
                                                    description "The number of exceed-profile packets dropped by the packet processor to traffic manager";
                                                }

                                                leaf exceed-profile-dropped-octets {
                                                    type yang:counter64;
                                                    description "The number of exceed-profile octets dropped by the packet processor to traffic manager";
                                                }

                                                leaf in-profile-forwarded-packets {
                                                    type yang:counter64;
                                                    description "The number of in-profile packets forwarded by the packet processor to traffic manager";
                                                }

                                                leaf in-profile-forwarded-octets {
                                                    type yang:counter64;
                                                    description "The number of in-profile octets forwarded by the packet processor to traffic manager";
                                                }

                                                leaf out-profile-forwarded-packets {
                                                    type yang:counter64;
                                                    description "The number of out-of-profile packets forwarded by the packet processor to traffic manager";
                                                }

                                                leaf out-profile-forwarded-octets {
                                                    type yang:counter64;
                                                    description "The number of out-of-profile octets forwarded by the packet processor to traffic manager";
                                                }

                                                leaf exceed-profile-forwarded-packets {
                                                    type yang:counter64;
                                                    description "The number of exceed-profile packets forwarded by the packet processor to traffic manager";
                                                }

                                                leaf exceed-profile-forwarded-octets {
                                                    type yang:counter64;
                                                    description "The number of exceed-profile octets forwarded by the packet processor to traffic manager";
                                                }

                                            } // container offered-total-cir-exceed

                                        }
                                        case offered-four-profile-no-cir {

                                            container offered-four-profile-no-cir {
                                                description "Enter the offered-four-profile-no-cir context";

                                                leaf inplus-profile-offered-packets {
                                                    type yang:counter64;
                                                    description "The number of inplus-profile packets offered by the packet processor to traffic manager";
                                                }

                                                leaf inplus-profile-offered-octets {
                                                    type yang:counter64;
                                                    description "The number of inplus-profile octets offered by the packet processor to traffic manager";
                                                }

                                                leaf in-profile-offered-packets {
                                                    type yang:counter64;
                                                    description "The number of in-profile packets offered by the packet processor to traffic manager";
                                                }

                                                leaf in-profile-offered-octets {
                                                    type yang:counter64;
                                                    description "The number of in-profile octets offered by the packet processor to traffic manager";
                                                }

                                                leaf out-profile-offered-packets {
                                                    type yang:counter64;
                                                    description "The number of out-of-profile packets offered by the packet processor to traffic manager";
                                                }

                                                leaf out-profile-offered-octets {
                                                    type yang:counter64;
                                                    description "The number of out-of-profile octets offered by the packet processor to traffic manager";
                                                }

                                                leaf exceed-profile-offered-packets {
                                                    type yang:counter64;
                                                    description "The number of exceed-profile packets offered by the packet processor to traffic manager";
                                                }

                                                leaf exceed-profile-offered-octets {
                                                    type yang:counter64;
                                                    description "The number of exceed-profile octets offered by the packet processor to traffic manager";
                                                }

                                                leaf inplus-profile-dropped-packets {
                                                    type yang:counter64;
                                                    description "The number of inplus-profile packets dropped by the packet processor to traffic manager";
                                                }

                                                leaf inplus-profile-dropped-octets {
                                                    type yang:counter64;
                                                    description "The number of inplus-profile octets dropped by the packet processor to traffic manager";
                                                }

                                                leaf in-profile-dropped-packets {
                                                    type yang:counter64;
                                                    description "The number of in-profile packets dropped by the packet processor to traffic manager";
                                                }

                                                leaf in-profile-dropped-octets {
                                                    type yang:counter64;
                                                    description "The number of in-profile octets dropped by the packet processor to traffic manager";
                                                }

                                                leaf out-profile-dropped-packets {
                                                    type yang:counter64;
                                                    description "The number of out-of-profile packets dropped by the packet processor to traffic manager";
                                                }

                                                leaf out-profile-dropped-octets {
                                                    type yang:counter64;
                                                    description "The number of out-of-profile octets dropped by the packet processor to traffic manager";
                                                }

                                                leaf exceed-profile-dropped-packets {
                                                    type yang:counter64;
                                                    description "The number of exceed-profile packets dropped by the packet processor to traffic manager";
                                                }

                                                leaf exceed-profile-dropped-octets {
                                                    type yang:counter64;
                                                    description "The number of exceed-profile octets dropped by the packet processor to traffic manager";
                                                }

                                                leaf inplus-profile-forwarded-packets {
                                                    type yang:counter64;
                                                    description "The number of inplus-profile packets forwarded by the packet processor to traffic manager";
                                                }

                                                leaf inplus-profile-forwarded-octets {
                                                    type yang:counter64;
                                                    description "The number of inplus-profile octets forwarded by the packet processor to traffic manager";
                                                }

                                                leaf in-profile-forwarded-packets {
                                                    type yang:counter64;
                                                    description "The number of in-profile packets forwarded by the packet processor to traffic manager";
                                                }

                                                leaf in-profile-forwarded-octets {
                                                    type yang:counter64;
                                                    description "The number of in-profile octets forwarded by the packet processor to traffic manager";
                                                }

                                                leaf out-profile-forwarded-packets {
                                                    type yang:counter64;
                                                    description "The number of out-of-profile packets forwarded by the packet processor to traffic manager";
                                                }

                                                leaf out-profile-forwarded-octets {
                                                    type yang:counter64;
                                                    description "The number of out-of-profile octets forwarded by the packet processor to traffic manager";
                                                }

                                                leaf exceed-profile-forwarded-packets {
                                                    type yang:counter64;
                                                    description "The number of exceed-profile packets forwarded by the packet processor to traffic manager";
                                                }

                                                leaf exceed-profile-forwarded-octets {
                                                    type yang:counter64;
                                                    description "The number of exceed-profile octets forwarded by the packet processor to traffic manager";
                                                }

                                            } // container offered-four-profile-no-cir

                                        }
                                        case offered-total-cir-four-profile {

                                            container offered-total-cir-four-profile {
                                                description "Enter the offered-total-cir-four-profile context";

                                                leaf all-offered-packets {
                                                    type yang:counter64;
                                                    description "The number of all the priority packets offered by the packet processor to traffic manager";
                                                }

                                                leaf all-offered-octets {
                                                    type yang:counter64;
                                                    description "The number of all the priority octets offered by the packet processor to traffic manager";
                                                }

                                                leaf inplus-profile-dropped-packets {
                                                    type yang:counter64;
                                                    description "The number of inplus-profile packets dropped by the packet processor to traffic manager";
                                                }

                                                leaf inplus-profile-dropped-octets {
                                                    type yang:counter64;
                                                    description "The number of inplus-profile octets dropped by the packet processor to traffic manager";
                                                }

                                                leaf in-profile-dropped-packets {
                                                    type yang:counter64;
                                                    description "The number of in-profile packets dropped by the packet processor to traffic manager";
                                                }

                                                leaf in-profile-dropped-octets {
                                                    type yang:counter64;
                                                    description "The number of in-profile octets dropped by the packet processor to traffic manager";
                                                }

                                                leaf out-profile-dropped-packets {
                                                    type yang:counter64;
                                                    description "The number of out-of-profile packets dropped by the packet processor to traffic manager";
                                                }

                                                leaf out-profile-dropped-octets {
                                                    type yang:counter64;
                                                    description "The number of out-of-profile octets dropped by the packet processor to traffic manager";
                                                }

                                                leaf exceed-profile-dropped-packets {
                                                    type yang:counter64;
                                                    description "The number of exceed-profile packets dropped by the packet processor to traffic manager";
                                                }

                                                leaf exceed-profile-dropped-octets {
                                                    type yang:counter64;
                                                    description "The number of exceed-profile octets dropped by the packet processor to traffic manager";
                                                }

                                                leaf inplus-profile-forwarded-packets {
                                                    type yang:counter64;
                                                    description "The number of inplus-profile packets forwarded by the packet processor to traffic manager";
                                                }

                                                leaf inplus-profile-forwarded-octets {
                                                    type yang:counter64;
                                                    description "The number of inplus-profile octets forwarded by the packet processor to traffic manager";
                                                }

                                                leaf in-profile-forwarded-packets {
                                                    type yang:counter64;
                                                    description "The number of in-profile packets forwarded by the packet processor to traffic manager";
                                                }

                                                leaf in-profile-forwarded-octets {
                                                    type yang:counter64;
                                                    description "The number of in-profile octets forwarded by the packet processor to traffic manager";
                                                }

                                                leaf out-profile-forwarded-packets {
                                                    type yang:counter64;
                                                    description "The number of out-of-profile packets forwarded by the packet processor to traffic manager";
                                                }

                                                leaf out-profile-forwarded-octets {
                                                    type yang:counter64;
                                                    description "The number of out-of-profile octets forwarded by the packet processor to traffic manager";
                                                }

                                                leaf exceed-profile-forwarded-packets {
                                                    type yang:counter64;
                                                    description "The number of exceed-profile packets forwarded by the packet processor to traffic manager";
                                                }

                                                leaf exceed-profile-forwarded-octets {
                                                    type yang:counter64;
                                                    description "The number of exceed-profile octets forwarded by the packet processor to traffic manager";
                                                }

                                            } // container offered-total-cir-four-profile

                                        }
                                        case v4-v6 {

                                            container v4-v6 {
                                                description "Enter the v4-v6 context";

                                                leaf ipv4-offered-packets {
                                                    type yang:counter64;
                                                    description "The number of ipv4 packets offered by the packet processor to traffic manager";
                                                }

                                                leaf ipv4-offered-octets {
                                                    type yang:counter64;
                                                    description "The number of ipv4 octets offered by the packet processor to traffic manager";
                                                }

                                                leaf ipv6-offered-packets {
                                                    type yang:counter64;
                                                    description "The number of ipv6 packets offered by the packet processor to traffic manager";
                                                }

                                                leaf ipv6-offered-octets {
                                                    type yang:counter64;
                                                    description "The number of ipv6 octets offered by the packet processor to traffic manager";
                                                }

                                                leaf ipv4-dropped-packets {
                                                    type yang:counter64;
                                                    description "The number of ipv4 packets dropped by the packet processor to traffic manager";
                                                }

                                                leaf ipv4-dropped-octets {
                                                    type yang:counter64;
                                                    description "The number of ipv4 octets dropped by the packet processor to traffic manager";
                                                }

                                                leaf ipv6-dropped-packets {
                                                    type yang:counter64;
                                                    description "The number of ipv6 packets dropped by the packet processor to traffic manager";
                                                }

                                                leaf ipv6-dropped-octets {
                                                    type yang:counter64;
                                                    description "The number of ipv6 octets dropped by the packet processor to traffic manager";
                                                }

                                                leaf ipv4-forwarded-packets {
                                                    type yang:counter64;
                                                    description "The number of ipv4 packets forwarded by the packet processor to traffic manager";
                                                }

                                                leaf ipv4-forwarded-octets {
                                                    type yang:counter64;
                                                    description "The number of ipv4 octets forwarded by the packet processor to traffic manager";
                                                }

                                                leaf ipv6-forwarded-packets {
                                                    type yang:counter64;
                                                    description "The number of ipv6 packets forwarded by the packet processor to traffic manager";
                                                }

                                                leaf ipv6-forwarded-octets {
                                                    type yang:counter64;
                                                    description "The number of ipv6 octets forwarded by the packet processor to traffic manager";
                                                }

                                            } // container v4-v6

                                        }
                                        case bonding {

                                            container bonding {
                                                description "Enter the bonding context";

                                                leaf connection-1-offered-packets {
                                                    type yang:counter64;
                                                    description "The number of connection-1 packets offered by the packet processor to traffic manager";
                                                }

                                                leaf connection-1-offered-octets {
                                                    type yang:counter64;
                                                    description "The number of connection-1 octets offered by the packet processor to traffic manager";
                                                }

                                                leaf connection-2-offered-packets {
                                                    type yang:counter64;
                                                    description "The number of connection-2 packets offered by the packet processor to traffic manager";
                                                }

                                                leaf connection-2-offered-octets {
                                                    type yang:counter64;
                                                    description "The number of connection-2 octets offered by the packet processor to traffic manager";
                                                }

                                                leaf connection-1-dropped-packets {
                                                    type yang:counter64;
                                                    description "The number of connection-1 packets dropped by the packet processor to traffic manager";
                                                }

                                                leaf connection-1-dropped-octets {
                                                    type yang:counter64;
                                                    description "The number of connection-1 octets dropped by the packet processor to traffic manager";
                                                }

                                                leaf connection-2-dropped-packets {
                                                    type yang:counter64;
                                                    description "The number of connection-2 packets dropped by the packet processor to traffic manager";
                                                }

                                                leaf connection-2-dropped-octets {
                                                    type yang:counter64;
                                                    description "The number of connection-2 octets dropped by the packet processor to traffic manager";
                                                }

                                                leaf connection-1-forwarded-packets {
                                                    type yang:counter64;
                                                    description "The number of connection-1 packets forwarded by the packet processor to traffic manager";
                                                }

                                                leaf connection-1-forwarded-octets {
                                                    type yang:counter64;
                                                    description "The number of connection-1 octets forwarded by the packet processor to traffic manager";
                                                }

                                                leaf connection-2-forwarded-packets {
                                                    type yang:counter64;
                                                    description "The number of connection-2 packets forwarded by the packet processor to traffic manager";
                                                }

                                                leaf connection-2-forwarded-octets {
                                                    type yang:counter64;
                                                    description "The number of connection-2 octets forwarded by the packet processor to traffic manager";
                                                }

                                            } // container bonding

                                        }
                                    }
                                } // container statistics

                                list hardware-policer {
                                    key "hardware-policer-string";
                                    description "Enter the hardware-policer list instance";

                                    leaf hardware-policer-string {
                                        type types-sros:named-item-255;
                                        description "Name of the policer formatted by IOM.";
                                    }

                                    leaf adapted-admin-cbs {
                                        type int64;
                                        units "bytes";
                                        description "Admin CBS.";
                                    }

                                    leaf adapted-admin-mbs {
                                        type int64;
                                        units "bytes";
                                        description "Admin MBS.";
                                    }

                                    leaf adapted-hp-only {
                                        type int64;
                                        units "bytes";
                                        description "Hi Prio Only.";
                                    }

                                    leaf depth {
                                        type int64;
                                        units "bytes";
                                        description "Depth.";
                                    }

                                    leaf operational-cir {
                                        type union {
                                            type enumeration {
                                                enum "max"                          { value -1; }
                                            }
                                            type int64;
                                        }
                                        description "Oper CIR.";
                                    }

                                    leaf operational-fir {
                                        type union {
                                            type enumeration {
                                                enum "max"                          { value -1; }
                                            }
                                            type int64;
                                        }
                                        description "Oper FIR.";
                                    }

                                    leaf operational-pir {
                                        type union {
                                            type enumeration {
                                                enum "max"                          { value -1; }
                                            }
                                            type int64;
                                        }
                                        description "Oper PIR.";
                                    }

                                } // list hardware-policer

                            } // list policer

                        } // container sap-egress

                        container policer-control-policy {
                            description "Enter the policer-control-policy context";

                            list arbiter {
                                key "arbiter-name";
                                description "Enter the arbiter list instance";

                                leaf arbiter-name {
                                    type types-sros:named-item;
                                    description "Specifies the arbiter name.";
                                }

                                container statistics {
                                    description "Enter the statistics context";

                                    leaf forwarded-packets {
                                        type yang:counter64;
                                        description "The number of forwarded packets.";
                                    }

                                    leaf forwarded-octets {
                                        type yang:counter64;
                                        description "The number of forwarded octets.";
                                    }

                                } // container statistics

                            } // list arbiter

                        } // container policer-control-policy

                        container scheduler-policy {
                            description "Enter the scheduler-policy context";

                            list scheduler {
                                key "scheduler-name";
                                description "Enter the scheduler list instance";

                                leaf scheduler-name {
                                    type types-sros:named-item;
                                    description "Specifies the scheduler name.";
                                }

                                container statistics {
                                    description "Enter the statistics context";

                                    leaf forwarded-packets {
                                        type yang:counter64;
                                        description "The number of forwarded packets.";
                                    }

                                    leaf forwarded-octets {
                                        type yang:counter64;
                                        description "The number of forwarded octets.";
                                    }

                                } // container statistics

                            } // list scheduler

                        } // container scheduler-policy

                    } // container qos

                } // container egress

                container lag {
                    description "Enter the lag context";

                    leaf active-port {
                        type types-sros:port;
                        description "Port on the lag associated with this SAP, that is used when lag-per-link-hash is enabled on the lag or when lag-link-map-profile is configured on this SAP.";
                    }

                    container per-link-hash-oper {
                        description "Enter the per-link-hash-oper context";

                        leaf class {
                            type int32;
                            description "Operational value for class associated with this SAP.";
                        }

                        leaf weight {
                            type int32;
                            description "Operational value used for weight associated with this SAP.";
                        }

                        leaf is-overriden {
                            type boolean;
                            description "Whether administrative values, subscriber management determined operational weight and class are used for this SAP.";
                        }

                    } // container per-link-hash-oper

                } // container lag

                container l2tpv3-session {
                    description "Enter the l2tpv3-session context";

                    leaf oper-state {
                        type types-sros:oper-state;
                        description "Operational status of this entry.";
                    }

                    leaf tunnel-status {
                        type enumeration {
                            enum "down"                         { value 1; }
                            enum "inprogress"                   { value 2; }
                            enum "connected"                    { value 3; }
                        }
                        description "State of the L2tpv3 tunnel.";
                    }

                    leaf oper-flags {
                        type bits {
                            bit sap-down                       { position 0; }
                            bit router-unreachable             { position 1; }
                            bit admin-down                     { position 2; }
                            bit tunnel-not-unique              { position 3; }
                        }
                        description "Reason why the L2tpv3 tunnel is operationally down.";
                    }

                    leaf last-oper-changed {
                        type yang:date-and-time;
                        description "Uptime at the time of the last operational status change of this l2tpv3 tunnel.";
                    }

                } // container l2tpv3-session

                container distributed-cpu-protection {
                    description "Enter the distributed-cpu-protection context";

                    list static-policer {
                        key "name card fp-number";
                        description "Enter the static-policer list instance";

                        leaf name {
                            type types-sros:named-item;
                            description "Name of static policer.";
                        }

                        leaf card {
                            type types-card:iom-card-slot;
                            description "IOM card within a chassis in the system.";
                        }

                        leaf fp-number {
                            type uint32 {
                                range "1..12";
                            }
                            description "Forwarding plane within a specific IOM card in the system.";
                        }

                        leaf state {
                            type types-services:dist-cpu-prot-policer-state;
                            description "State of the policer configured on Distributed CPU Protection Policy.";
                        }

                        leaf exceed-count {
                            type uint64;
                            description "Number of packets exceeding the policing parameters since the given policer was previously declared as conformant or newly instantiated.";
                        }

                        leaf hold-down-remain {
                            type types-services:dist-cpu-prot-action-duration;
                            units "seconds";
                            description "Remaining hold-down period for a given policer.";
                        }

                        leaf detection-time-remain {
                            type uint32;
                            units "seconds";
                            description "Detection time remaining for a given policer.";
                        }

                    } // list static-policer

                    list local-monitor-policer {
                        key "name card fp-number";
                        description "Enter the local-monitor-policer list instance";

                        leaf name {
                            type types-sros:named-item;
                            description "Name of local-monitor policer.";
                        }

                        leaf card {
                            type types-card:iom-card-slot;
                            description "IOM card within a chassis in the system.";
                        }

                        leaf fp-number {
                            type uint32 {
                                range "1..12";
                            }
                            description "Forwarding plane within a specific IOM card in the system.";
                        }

                        leaf state {
                            type types-services:dist-cpu-prot-policer-state;
                            description "State of the policer configured on Distributed CPU Protection Policy.";
                        }

                        leaf exceed-count {
                            type uint64;
                            description "Number of packets exceeding the policing parameters since the given policer was previously declared as conformant or newly instantiated.";
                        }

                        leaf all-dynamic-policer-allocation {
                            type boolean;
                            description "All dynamic-policers allocation status";
                        }

                    } // list local-monitor-policer

                    list dynamic-policer {
                        key "protocol card fp-number";
                        description "Enter the dynamic-policer list instance";

                        leaf protocol {
                            type types-sros:dist-cpu-protection-protocol;
                            description "Dynamic policer protocol.";
                        }

                        leaf card {
                            type types-card:iom-card-slot;
                            description "IOM card within a chassis in the system.";
                        }

                        leaf fp-number {
                            type uint32 {
                                range "1..12";
                            }
                            description "Forwarding plane within a specific IOM card in the system.";
                        }

                        leaf state {
                            type types-services:dist-cpu-prot-policer-state;
                            description "State of the policer configured on Distributed CPU Protection Policy.";
                        }

                        leaf exceed-count {
                            type uint64;
                            description "Number of packets exceeding the policing parameters since the given policer was previously declared as conformant or newly instantiated.";
                        }

                        leaf hold-down-remain {
                            type types-services:dist-cpu-prot-action-duration;
                            units "seconds";
                            description "Remaining hold-down period for a given policer.";
                        }

                        leaf detection-time-remain {
                            type uint32;
                            units "seconds";
                            description "Detection time remaining for a given policer.";
                        }

                        leaf dynamic-policer-allocation {
                            type boolean;
                            description "Dynamic-policer allocation status";
                        }

                    } // list dynamic-policer

                } // container distributed-cpu-protection

                container ethernet-segment {
                    description "Enter the ethernet-segment context";

                    leaf name {
                        type types-sros:named-item-or-empty;
                        description "Ethernet segment name.";
                    }

                    leaf oper-state {
                        type types-services:evpn-mh-es-status;
                        description "Operational status of the ethernet-segment.";
                    }

                } // container ethernet-segment

                container eth-cfm {
                    description "Enter the eth-cfm context";

                    list mep {
                        key "md-admin-name ma-admin-name mep-id";
                        description "Enter the mep list instance";

                        leaf md-admin-name {
                            type leafref {
                                path "../../../../../../eth-cfm/domain/md-admin-name";
                            }
                            description "Maintenance Domain (MD) name";
                        }

                        leaf ma-admin-name {
                            type leafref {
                                path "../../../../../../eth-cfm/domain[md-admin-name=current()/../md-admin-name]/association/ma-admin-name";
                            }
                            description "Maintenance Association (MA) name";
                        }

                        leaf mep-id {
                            type types-eth-cfm:mep-id-type;
                            description "Maintenance Endpoint (MEP) ID";
                        }

                        leaf if-index {
                            type uint32;
                            description "Port ID of the MEP.";
                        }

                        leaf oper-mac-address {
                            type yang:mac-address;
                            description "Operational MAC address of the MEP.";
                        }

                        container ais {
                            description "Enter the ais context";

                            container received {
                                description "Enter the received context";

                                leaf ais-packet {
                                    type boolean;
                                    description "Indicates if the MEP is receiving AIS test frames from one or more of its sub-layer MEPs.";
                                }

                                leaf interval {
                                    type uint32 {
                                        range "1|60";
                                    }
                                    units "seconds";
                                    description "Indicates the AIS Interval received in the last AIS Frame.";
                                }

                            } // container received

                            container transmitted {
                                description "Enter the transmitted context";

                                leaf ais-packet {
                                    type enumeration {
                                        enum "no-transmit"                  { value 0; }
                                        enum "transmit"                     { value 1; }
                                        enum "pending"                      { value 2; }
                                    }
                                    description "Indicates if the MEP is transmitting AIS test frames from one or more of its sub-layer MEPs.";
                                }

                            } // container transmitted

                        } // container ais

                        container csf {
                            description "Enter the csf context";

                            container received {
                                description "Enter the received context";

                                leaf state {
                                    type enumeration {
                                        enum "los"                          { value 0; }
                                        enum "ais"                          { value 1; }
                                        enum "rdi"                          { value 2; }
                                        enum "dci"                          { value 3; }
                                    }
                                    description "Indicates the state of the received CSF frames for the MEP. los (0) - Client Loss of Signal ais (1) - Client Forward Defect Indication rdi (2) - Client Reverse Defect Indication dci (3) - Client Defect Clear Indication.";
                                }

                                leaf interval {
                                    type uint32 {
                                        range "1|60";
                                    }
                                    units "seconds";
                                    description "Indicates the CSF Interval received in the most recent CSF frame.";
                                }

                            } // container received

                        } // container csf

                        container grace {
                            description "Enter the grace context";

                            container transmitted {
                                description "Enter the transmitted context";

                                leaf grace-notification {
                                    type enumeration {
                                        enum "no-transmit"                  { value 0; }
                                        enum "grace"                        { value 1; }
                                        enum "eth-ed"                       { value 2; }
                                    }
                                    description "Indicates the state of the MEP grace period PDU transmission.";
                                }

                            } // container transmitted

                            container received {
                                description "Enter the received context";

                                leaf process-grace-notification {
                                    type boolean;
                                    description "Indicates whether the local MEP is receiving and processing grace notifications from one or more peer MEPs. A value of 'true ' indicates the local MEP is receiving and processing grace from at least one peer MEP. A value of 'false' indicates that no peer grace notifications are being received and processed.";
                                }

                            } // container received

                        } // container grace

                        container ccm-states {
                            description "Enter the ccm-states context";

                            leaf transmit-status {
                                type enumeration {
                                    enum "no-transmit"                  { value 0; }
                                    enum "transmit"                     { value 1; }
                                    enum "suppressed"                   { value 2; }
                                }
                                description "Indicates the state of the MEP CCM PDU transmission. Values: noTransmit (0) - no CCM PDUs are being transmitted by the MEP transmit (1) - MEP is currently transmitting CCM PDUs suppressed (2) - MEP should be transmitting CCM PDUs but is suppressing them due to an internal condition";
                            }

                            leaf sequence-error {
                                type yang:counter32;
                                description "The total number of out-of-sequence CCMs received from all remote MEPs.";
                            }

                            leaf fng-state {
                                type types-eth-cfm:fng-state-type;
                                description "Current state of the MEP Fault Notification Generator State Machine.";
                            }

                            container transmitted {
                                description "Enter the transmitted context";

                                leaf count {
                                    type yang:counter32;
                                    description "Total number of CCMs transmitted.";
                                }

                                leaf interface-status {
                                    type types-eth-cfm:interface-status;
                                    description "Indicates the interface status TLV information included in the most recent Connectivity Check Message (CCM) transmission from the local MEP. If the local MEP CCM transmissions are not enabled, or if no interface status TLV was included in the most recent transmission, then ccm-tx-if-status will return a value of is-no-interface-status-tlv (0).";
                                }

                                leaf port-status {
                                    type types-eth-cfm:port-status;
                                    description "Indicates the port status TLV information included in the most recent Connectivity Check Message (CCM) transmission from the local MEP. If the local MEP CCM transmissions are not enabled, or if no port status TLV was included in the most recent transmission, then ccm-tx-port-status will return a value of ps-no-port-state-tlv (0).";
                                }

                                leaf remote-defect-indicator {
                                    type boolean;
                                    description "Indicates whether or not the Remote Defect Indication (RDI) bit was set on the most recent Connectivity Check Message (CCM) transmission from the local MEP. If the local MEP CCM transmissions are not eanbled, or if the RDI bit was not set in the most recent transmission, then ccm-tx-rdi will return a value of 'false (2)'.";
                                }

                            } // container transmitted

                            container received {
                                description "Enter the received context";

                                leaf highest-priority-defect {
                                    type types-eth-cfm:highest-priority-defect-type;
                                    description "The highest priority defect that has been present since the MEPs Fault Notification Generator State Machine was last in the reset state.";
                                }

                                leaf defect-flags {
                                    type types-eth-cfm:mep-defect-flags;
                                    description "A vector of boolean error conditions, any of which may be true.";
                                }

                                list remote-mep-peer {
                                    key "remote-mep-id";
                                    description "Enter the remote-mep-peer list instance";

                                    leaf remote-mep-id {
                                        type types-eth-cfm:mep-id-type;
                                        description "The Remote MEP ID within the same Maintenance Association.";
                                    }

                                    leaf auto-discovered {
                                        type boolean;
                                        description "Specifies whether or not the remote peer was automatically discovered ('true') or not. Auto-discovered remote peers are created by the system only, and are of a 'volatile' storage type. Specifying the value of 'false' will mark an auto-discovered remote peer as permanently configured.";
                                    }

                                    leaf receiving-ccm {
                                        type types-eth-cfm:remote-mep-state-type;
                                        description "The operational CCM receiving state of the remote MEP.";
                                    }

                                    leaf ccm-status-since {
                                        type yang:date-and-time;
                                        description "The time at which the Remote MEP last entered either the mep-failed or mep-ok state.";
                                    }

                                    leaf peer-mac-address {
                                        type yang:mac-address;
                                        description "The MAC address of the remote MEP.";
                                    }

                                    leaf receiving-remote-defect-indicator {
                                        type boolean;
                                        description "State of the RDI bit in the last received CCM (true for rdi=1), or false if none has been received.";
                                    }

                                    leaf port-status-tlv {
                                        type types-eth-cfm:port-status;
                                        description "An enumerated value of the Port status TLV received in the last CCM from the remote MEP or the default value ps-no-port-state-tlv indicating either no CCM has been received, or that no port status TLV was received in the last CCM.";
                                    }

                                    leaf interface-status-tlv {
                                        type types-eth-cfm:interface-status;
                                        description "An enumerated value of the Interface status TLV received in the last CCM from the remote MEP or the default value is-no-interface-status-tlv indicating either no CCM has been received, or that no interface status TLV was received in the last CCM.";
                                    }

                                } // list remote-mep-peer

                            } // container received

                        } // container ccm-states

                        container mc-lag {
                            description "Enter the mc-lag context";

                            leaf inactive-state {
                                type enumeration {
                                    enum "not-applicable"               { value 0; }
                                    enum "standby"                      { value 1; }
                                    enum "active"                       { value 2; }
                                }
                                description "Indicates the MC-LAG inactive state of the mep. The value of system/eth-cfm/redundancy/mc-lag/standby-mep must be 'true (1)' on the node for this leaf to have meaning.";
                            }

                        } // container mc-lag

                        container statistics {
                            description "Enter the statistics context";

                            list opcode {
                                key "opcode-name";
                                description "Enter the opcode list instance";

                                leaf opcode-name {
                                    type types-eth-cfm:statistics-opcode-name;
                                    description "Integer that defines which CFM PDU Opcode the statictics refer to.";
                                }

                                leaf transmitted {
                                    type yang:counter32;
                                    description "The total number of PDUs transmitted from the node with the specified Opcode.";
                                }

                                leaf received {
                                    type yang:counter32;
                                    description "The total number of PDUs received on the node with the specified Opcode.";
                                }

                            } // list opcode

                        } // container statistics

                    } // list mep

                    list mip {
                        key "primary-vlan";
                        description "Enter the mip list instance";

                        leaf primary-vlan {
                            type types-eth-cfm:vlan-id-or-none;
                            description "VLAN ID to which the MIP is attached";
                        }

                        leaf instantiated {
                            type boolean;
                            description "Indicates if the MIP is instanstiated or not.";
                        }

                        leaf direction {
                            type enumeration {
                                enum "both"                         { value 0; }
                            }
                            description "Indicates the direction in which the MIP faces on the Bridge Port.";
                        }

                        leaf level {
                            type types-eth-cfm:mp-level;
                            description "Indicate the MD (Maintenance Domain) Level at which MHFs (MIP Half Function) are created.";
                        }

                        leaf level-authority {
                            type types-eth-cfm:mip-authority;
                            description "Indicates the authority context used for leaf level of the instatiated MIP.";
                        }

                        leaf mhf-creation {
                            type enumeration {
                                enum "none"                         { value 1; }
                                enum "default"                      { value 2; }
                                enum "explicit"                     { value 3; }
                                enum "defer"                        { value 4; }
                                enum "static"                       { value 32; }
                            }
                            description "A value indicating if the Management entity can create MHFs (MIP Half Function).";
                        }

                        leaf mhf-creation-authority {
                            type types-eth-cfm:mip-authority;
                            description "Indicates the authority context used for leaf mhf-creation of the instatiated MIP.";
                        }

                        leaf id-permission {
                            type types-eth-cfm:permission-type;
                            description "Indicates the sender ID TLV permissions for the instantiated MIP.";
                        }

                        leaf id-permission-authority {
                            type types-eth-cfm:mip-authority;
                            description "Indicates the authority context used for leaf id-permission of the instatiated MIP.";
                        }

                        leaf mip-ltr-priority {
                            type types-eth-cfm:frame-priority;
                            description "Indicates the priority to use in linktrace response frames to be transmitted for this MIP.";
                        }

                        leaf mip-ltr-priority-authority {
                            type types-eth-cfm:mip-authority;
                            description "Indicates the authority context used for leaf mip-ltr-priority of the instatiated MIP.";
                        }

                    } // list mip

                } // container eth-cfm

                container ethernet {
                    description "Enter the ethernet context";

                    container llf {
                        description "Enter the llf context";

                        leaf oper-state {
                            type types-services:epipe-sap-ethernet-llf-oper-status-type;
                            description "Operational State of the LLF entry.";
                        }

                    } // container llf

                } // container ethernet

            } // list sap

            container vxlan {
                description "Enter the vxlan context";

                list instance {
                    key "vxlan-instance";
                    description "Enter the instance list instance";

                    leaf vxlan-instance {
                        type uint32 {
                            range "1";
                        }
                        description "VXLAN instance";
                    }

                    container destinations {
                        description "Enter the destinations context";

                        list non-ethernet-segment-destination {
                            key "ip-address vni";
                            description "Enter the non-ethernet-segment-destination list instance";

                            leaf ip-address {
                                type types-sros:ip-address;
                                description "IP address of the tunnel endpoint";
                            }

                            leaf vni {
                                type types-services:vxlan-vni;
                                description "VNI of the vxlan";
                            }

                            leaf oper-state {
                                type types-sros:oper-state;
                                description "Operational status of the VTEP-Egress VNI";
                            }

                            leaf type {
                                type enumeration {
                                    enum "none"                         { value 0; }
                                    enum "static"                       { value 1; }
                                    enum "evpn"                         { value 2; }
                                }
                                description "Type of vxlan instance created on this Epipe service.";
                            }

                        } // list non-ethernet-segment-destination

                        list ethernet-segment-destination {
                            key "esi";
                            description "Enter the ethernet-segment-destination list instance";

                            leaf esi {
                                type string;
                                description "Ethernet segment identifier";
                            }

                            leaf mac-count {
                                type uint32;
                                description "Number of MAC addresses";
                            }

                            list tep {
                                key "ip-address vni";
                                description "Enter the tep list instance";

                                leaf ip-address {
                                    type types-sros:ip-address;
                                    description "IP address of the tunnel endpoint";
                                }

                                leaf vni {
                                    type types-services:vxlan-vni;
                                    description "VNI of the vxlan";
                                }

                            } // list tep

                        } // list ethernet-segment-destination

                    } // container destinations

                    container ethernet-segment {
                        description "Enter the ethernet-segment context";

                        leaf name {
                            type types-sros:named-item-or-empty;
                            description "Ethernet segment name";
                        }

                        leaf oper-state {
                            type types-services:evpn-mh-es-status;
                            description "Operational status of the ethernet-segment";
                        }

                    } // container ethernet-segment

                } // list instance

            } // container vxlan

            container bgp-evpn {
                description "Enter the bgp-evpn context";

                leaf creation-origin {
                    type types-sros:creation-origin;
                    description "Creation origin of BGP-EVPN in the service";
                }

                list local-attachment-circuit {
                    key "name";
                    description "Enter the local-attachment-circuit list instance";

                    leaf name {
                        type types-sros:named-item;
                        description "Attachment circuit name";
                    }

                    leaf ingress-label {
                        type int32;
                        description "Label advertised for the local attachment circuit for ingress traffic in the EVPN-VPWS MPLS instance.";
                    }

                } // list local-attachment-circuit

                list mpls {
                    key "bgp-instance";
                    description "Enter the mpls list instance";

                    leaf bgp-instance {
                        type int32 {
                            range "1";
                        }
                        description "BGP instance";
                    }

                    container ingress {
                        description "Enter the ingress context";

                        leaf unicast-label {
                            type int32;
                            description "Label advertised for ingress unicast traffic";
                        }

                        leaf bum-label {
                            type int32;
                            description "Label advertised for ingress BUM traffic";
                        }

                    } // container ingress

                    container destinations {
                        description "Enter the destinations context";

                        list non-ethernet-segment-destination {
                            key "ip-address label";
                            description "Enter the non-ethernet-segment-destination list instance";

                            leaf ip-address {
                                type types-sros:ip-address;
                                description "IP address of Tunnel Endpoint";
                            }

                            leaf label {
                                type uint32;
                                description "Label associated with Tunnel Endpoint";
                            }

                            list tunnel-id {
                                key "tunnel-id";
                                description "Enter the tunnel-id list instance";

                                leaf tunnel-id {
                                    type uint32;
                                    description "Tunnel identifier associated with Tunnel Endpoint";
                                }

                                leaf transport-type {
                                    type types-mpls:mpls-transport-type;
                                    description "Indicates transport type associated with Tunnel Endpoint";
                                }

                            } // list tunnel-id

                        } // list non-ethernet-segment-destination

                        list ethernet-segment-destination {
                            key "esi";
                            description "Enter the ethernet-segment-destination list instance";

                            leaf esi {
                                type string;
                                description "Ethernet segment identifier";
                            }

                            list tep {
                                key "ip-address label";
                                description "Enter the tep list instance";

                                leaf ip-address {
                                    type types-sros:ip-address;
                                    description "IP address of Tunnel Endpoint";
                                }

                                leaf label {
                                    type uint32;
                                    description "Label associated with Tunnel Endpoint";
                                }

                                leaf transport-type {
                                    type types-mpls:mpls-transport-type;
                                    description "Indicates transport type associated with Tunnel Endpoint";
                                }

                                leaf tunnel-id {
                                    type uint32;
                                    description "Indicates tunnel identifier associated with Tunnel Endpoint";
                                }

                            } // list tep

                        } // list ethernet-segment-destination

                    } // container destinations

                } // list mpls

                list segment-routing-v6 {
                    key "bgp-instance";
                    description "Enter the segment-routing-v6 list instance";

                    leaf bgp-instance {
                        type int32 {
                            range "1";
                        }
                        description "BGP instance";
                    }

                    container destinations {
                        description "Enter the destinations context";

                        list ethernet-segment-destination {
                            key "esi";
                            description "Enter the ethernet-segment-destination list instance";

                            leaf esi {
                                type string;
                                description "Ethernet segment identifier";
                            }

                            leaf last-update {
                                type types-sros:date-time;
                                description "Time this entry was last updated.";
                            }

                            list tep {
                                key "tep-address sid-address";
                                description "Enter the tep list instance";

                                leaf tep-address {
                                    type types-sros:ip-address;
                                    description "Tunnel endpoint ip-address";
                                }

                                leaf sid-address {
                                    type types-sros:ipv6-address;
                                    description "SID ip-address";
                                }

                                leaf last-update {
                                    type types-sros:date-time;
                                    description "Time this entry was last updated.";
                                }

                            } // list tep

                        } // list ethernet-segment-destination

                        list non-ethernet-segment-destination {
                            key "tep-address sid-address";
                            description "Enter the non-ethernet-segment-destination list instance";

                            leaf tep-address {
                                type types-sros:ip-address;
                                description "Tunnel endpoint ip-address";
                            }

                            leaf sid-address {
                                type types-sros:ipv6-address;
                                description "SID ip-address";
                            }

                            leaf srv6-type {
                                type enumeration {
                                    enum "none"                         { value 0; }
                                    enum "static"                       { value 1; }
                                    enum "evpn"                         { value 2; }
                                }
                                description "Type of SRv6 instance created";
                            }

                        } // list non-ethernet-segment-destination

                    } // container destinations

                } // list segment-routing-v6

            } // container bgp-evpn

        } // list epipe

    } // grouping state-svc-epipe

}
