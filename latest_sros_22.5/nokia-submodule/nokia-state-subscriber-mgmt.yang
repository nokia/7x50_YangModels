submodule nokia-state-subscriber-mgmt {

    yang-version "1.1";

    belongs-to nokia-state { prefix "state"; }

    import ietf-yang-types                { prefix "yang"; }
    import nokia-sros-yang-extensions     { prefix "sros-ext"; }
    import nokia-types-filter             { prefix "types-filter"; }
    import nokia-types-qos                { prefix "types-qos"; }
    import nokia-types-services           { prefix "types-services"; }
    import nokia-types-sros               { prefix "types-sros"; }
    import nokia-types-subscriber-mgmt    { prefix "types-submgt"; }

    include nokia-state-aaa;
    include nokia-state-submgt-gtp;
    include nokia-state-submgt-isa-filter;
    include nokia-state-submgt-local-user-db;
    include nokia-state-submgt-service-chaining;
    include nokia-state-submgt-subscriber;
    include nokia-state-submgt-vrgw;
    include nokia-state-submgt-wlangw;


    sros-ext:sros-major-release "rel22";

    organization "Nokia";

    contact
        "Nokia SR OS Support
         Web: <http://www.nokia.com>";

    description
        "Nokia YANG Data model with operational state for subscriber management on SR OS based routers.

         Copyright 2016 Nokia. All rights reserved. Reproduction of this document
         is authorized on the condition that the foregoing copyright notice is included.

         This nokia-state-subscriber-mgmt YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";

    revision "2022-03-22";

    grouping state-subscriber-mgmt {
        container subscriber-mgmt {
            description "Enter the subscriber-mgmt context";

            list diameter-gx-policy {
                key "name";
                description "Enter the diameter-gx-policy list instance";

                leaf name {
                    type types-sros:named-item;
                    description "Diameter application policy name";
                }

                container statistics {
                    description "Enter the statistics context";

                    container messages {
                        description "Enter the messages context";

                        leaf last-cleared {
                            type yang:date-and-time;
                            description "time when statistics were cleared.";
                        }

                        leaf ccr-initials {
                            type uint64;
                            description "The number of Initial Credit-Control-Request messages transmitted.";
                        }

                        leaf cca-initials {
                            type uint64;
                            description "The number of Initial Credit-Control-Answer messages received.";
                        }

                        leaf ccr-updates {
                            type uint64;
                            description "The number of Update Credit-Control-Request messages transmitted.";
                        }

                        leaf cca-updates {
                            type uint64;
                            description "The number of Update Credit-Control-Answer messages received.";
                        }

                        leaf ccr-terminates {
                            type uint64;
                            description "The number of Termination Credit-Control-Request messages transmitted.";
                        }

                        leaf cca-terminates {
                            type uint64;
                            description "The number of Termination Credit-Control-Answer messages received.";
                        }

                        leaf asr-received {
                            type uint64;
                            description "The number of Abort-Session-Request (ASR) messages received.";
                        }

                        leaf asa-transmitted {
                            type uint64;
                            description "The number of Abort-Session-Answer messages transmitted.";
                        }

                        leaf rar-received {
                            type uint64;
                            description "The number of Re-Auth-Request messages received.";
                        }

                        leaf raa-transmitted {
                            type uint64;
                            description "The number of Re-Auth-Answer messages transmitted.";
                        }

                        leaf aar-transmitted {
                            type uint64;
                            description "The number of AA-Request messages transmitted.";
                        }

                        leaf aaa-received {
                            type uint64;
                            description "The number of AA-Answer messages received.";
                        }

                        leaf requests-failed {
                            type uint64;
                            description "The number of Request messages that could not be transmitted.";
                        }

                        leaf requests-retransmitted {
                            type uint64;
                            description "The number of request message retransmitted.";
                        }

                        leaf result-info-transmitted {
                            type uint64;
                            description "The number of answer messages transmitted.";
                        }

                        leaf result-info-received {
                            type uint64;
                            description "The number of answer messages received with Result-Code AVP in the 1xxx range (Informational).";
                        }

                        leaf result-success-transmitted {
                            type uint64;
                            description "The number of answer messages transmitted with Result-Code AVP in the 2xxx range (Success).";
                        }

                        leaf result-success-received {
                            type uint64;
                            description "The number of answer messages received with Result-Code AVP in the 2xxx range (Success).";
                        }

                        leaf result-protocol-error-transmitted {
                            type uint64;
                            description "The number of answer messages transmitted with Result-Code AVP in the 3xxx range (Protocol Errors).";
                        }

                        leaf result-protocol-error-received {
                            type uint64;
                            description "The number of answer messages received with Result-Code AVP in the 3xxx range (Protocol Errors).";
                        }

                        leaf result-transient-error-transmitted {
                            type uint64;
                            description "The number of answer messages transmitted with Result-Code AVP in the 4xxx range (Transient Failures).";
                        }

                        leaf result-transient-error-received {
                            type uint64;
                            description "The number of answer messages received with Result-Code AVP in the 4xxx range (Transient Failures).";
                        }

                        leaf result-permantent-failure-transmitted {
                            type uint64;
                            description "The number of answer messages transmitted with Result-Code AVP in the 5xxx range (Permanent Failures).";
                        }

                        leaf result-permantent-failure-received {
                            type uint64;
                            description "The number of answer messages received with Result-Code AVP in the 5xxx range (Permanent Failures).";
                        }

                    } // container messages

                    container ccrt-replay {
                        description "Enter the ccrt-replay context";

                        leaf last-cleared {
                            type yang:date-and-time;
                            description "time when statistics were cleared.";
                        }

                        leaf replay-active {
                            type uint64;
                            description "the current number of diameter-sessions associated with this diameter-gx-policy or diameter-gy-policy that are in CCR-T replay mode.";
                        }

                        leaf dropped-max-lifetime {
                            type uint64;
                            description "the number of times a session in CCR-T replay mode was dropped because it exceeded the Maximum Life Time";
                        }

                        leaf dropped-max-sessions {
                            type uint64;
                            description "the number of times a session in CCR-T replay mode was dropped to free resources for a new active session.";
                        }

                        leaf dropped-cleared {
                            type uint64;
                            description "the number of times a session in CCR-T replay mode was dropped because of a management request to clear the CCR-t replay mode sessions of an application policy.";
                        }

                        leaf cca-terminate-received {
                            type uint64;
                            description "the number of times a session in CCR-T replay mode was terminated because a CCA(term) message was received";
                        }

                    } // container ccrt-replay

                } // container statistics

            } // list diameter-gx-policy

            list diameter-gy-policy {
                key "name";
                description "Enter the diameter-gy-policy list instance";

                leaf name {
                    type types-sros:named-item;
                    description "Diameter application policy name";
                }

                container statistics {
                    description "Enter the statistics context";

                    container messages {
                        description "Enter the messages context";

                        leaf last-cleared {
                            type yang:date-and-time;
                            description "time when statistics were cleared.";
                        }

                        leaf ccr-initials {
                            type uint64;
                            description "The number of Initial Credit-Control-Request messages transmitted.";
                        }

                        leaf cca-initials {
                            type uint64;
                            description "The number of Initial Credit-Control-Answer messages received.";
                        }

                        leaf ccr-updates {
                            type uint64;
                            description "The number of Update Credit-Control-Request messages transmitted.";
                        }

                        leaf cca-updates {
                            type uint64;
                            description "The number of Update Credit-Control-Answer messages received.";
                        }

                        leaf ccr-terminates {
                            type uint64;
                            description "The number of Termination Credit-Control-Request messages transmitted.";
                        }

                        leaf cca-terminates {
                            type uint64;
                            description "The number of Termination Credit-Control-Answer messages received.";
                        }

                        leaf asr-received {
                            type uint64;
                            description "The number of Abort-Session-Request (ASR) messages received.";
                        }

                        leaf asa-transmitted {
                            type uint64;
                            description "The number of Abort-Session-Answer messages transmitted.";
                        }

                        leaf rar-received {
                            type uint64;
                            description "The number of Re-Auth-Request messages received.";
                        }

                        leaf raa-transmitted {
                            type uint64;
                            description "The number of Re-Auth-Answer messages transmitted.";
                        }

                        leaf aar-transmitted {
                            type uint64;
                            description "The number of AA-Request messages transmitted.";
                        }

                        leaf aaa-received {
                            type uint64;
                            description "The number of AA-Answer messages received.";
                        }

                        leaf requests-failed {
                            type uint64;
                            description "The number of Request messages that could not be transmitted.";
                        }

                        leaf requests-retransmitted {
                            type uint64;
                            description "The number of request message retransmitted.";
                        }

                        leaf result-info-transmitted {
                            type uint64;
                            description "The number of answer messages transmitted.";
                        }

                        leaf result-info-received {
                            type uint64;
                            description "The number of answer messages received with Result-Code AVP in the 1xxx range (Informational).";
                        }

                        leaf result-success-transmitted {
                            type uint64;
                            description "The number of answer messages transmitted with Result-Code AVP in the 2xxx range (Success).";
                        }

                        leaf result-success-received {
                            type uint64;
                            description "The number of answer messages received with Result-Code AVP in the 2xxx range (Success).";
                        }

                        leaf result-protocol-error-transmitted {
                            type uint64;
                            description "The number of answer messages transmitted with Result-Code AVP in the 3xxx range (Protocol Errors).";
                        }

                        leaf result-protocol-error-received {
                            type uint64;
                            description "The number of answer messages received with Result-Code AVP in the 3xxx range (Protocol Errors).";
                        }

                        leaf result-transient-error-transmitted {
                            type uint64;
                            description "The number of answer messages transmitted with Result-Code AVP in the 4xxx range (Transient Failures).";
                        }

                        leaf result-transient-error-received {
                            type uint64;
                            description "The number of answer messages received with Result-Code AVP in the 4xxx range (Transient Failures).";
                        }

                        leaf result-permantent-failure-transmitted {
                            type uint64;
                            description "The number of answer messages transmitted with Result-Code AVP in the 5xxx range (Permanent Failures).";
                        }

                        leaf result-permantent-failure-received {
                            type uint64;
                            description "The number of answer messages received with Result-Code AVP in the 5xxx range (Permanent Failures).";
                        }

                    } // container messages

                    container ccrt-replay {
                        description "Enter the ccrt-replay context";

                        leaf last-cleared {
                            type yang:date-and-time;
                            description "time when statistics were cleared.";
                        }

                        leaf replay-active {
                            type uint64;
                            description "the current number of diameter-sessions associated with this diameter-gx-policy or diameter-gy-policy that are in CCR-T replay mode.";
                        }

                        leaf dropped-max-lifetime {
                            type uint64;
                            description "the number of times a session in CCR-T replay mode was dropped because it exceeded the Maximum Life Time";
                        }

                        leaf dropped-max-sessions {
                            type uint64;
                            description "the number of times a session in CCR-T replay mode was dropped to free resources for a new active session.";
                        }

                        leaf dropped-cleared {
                            type uint64;
                            description "the number of times a session in CCR-T replay mode was dropped because of a management request to clear the CCR-t replay mode sessions of an application policy.";
                        }

                        leaf cca-terminate-received {
                            type uint64;
                            description "the number of times a session in CCR-T replay mode was terminated because a CCA(term) message was received";
                        }

                    } // container ccrt-replay

                } // container statistics

            } // list diameter-gy-policy

            list diameter-nasreq-policy {
                key "name";
                description "Enter the diameter-nasreq-policy list instance";

                leaf name {
                    type types-sros:named-item;
                    description "Diameter application policy name";
                }

                container statistics {
                    description "Enter the statistics context";

                    container messages {
                        description "Enter the messages context";

                        leaf last-cleared {
                            type yang:date-and-time;
                            description "time when statistics were cleared.";
                        }

                        leaf ccr-initials {
                            type uint64;
                            description "The number of Initial Credit-Control-Request messages transmitted.";
                        }

                        leaf cca-initials {
                            type uint64;
                            description "The number of Initial Credit-Control-Answer messages received.";
                        }

                        leaf ccr-updates {
                            type uint64;
                            description "The number of Update Credit-Control-Request messages transmitted.";
                        }

                        leaf cca-updates {
                            type uint64;
                            description "The number of Update Credit-Control-Answer messages received.";
                        }

                        leaf ccr-terminates {
                            type uint64;
                            description "The number of Termination Credit-Control-Request messages transmitted.";
                        }

                        leaf cca-terminates {
                            type uint64;
                            description "The number of Termination Credit-Control-Answer messages received.";
                        }

                        leaf asr-received {
                            type uint64;
                            description "The number of Abort-Session-Request (ASR) messages received.";
                        }

                        leaf asa-transmitted {
                            type uint64;
                            description "The number of Abort-Session-Answer messages transmitted.";
                        }

                        leaf rar-received {
                            type uint64;
                            description "The number of Re-Auth-Request messages received.";
                        }

                        leaf raa-transmitted {
                            type uint64;
                            description "The number of Re-Auth-Answer messages transmitted.";
                        }

                        leaf aar-transmitted {
                            type uint64;
                            description "The number of AA-Request messages transmitted.";
                        }

                        leaf aaa-received {
                            type uint64;
                            description "The number of AA-Answer messages received.";
                        }

                        leaf requests-failed {
                            type uint64;
                            description "The number of Request messages that could not be transmitted.";
                        }

                        leaf requests-retransmitted {
                            type uint64;
                            description "The number of request message retransmitted.";
                        }

                        leaf result-info-transmitted {
                            type uint64;
                            description "The number of answer messages transmitted.";
                        }

                        leaf result-info-received {
                            type uint64;
                            description "The number of answer messages received with Result-Code AVP in the 1xxx range (Informational).";
                        }

                        leaf result-success-transmitted {
                            type uint64;
                            description "The number of answer messages transmitted with Result-Code AVP in the 2xxx range (Success).";
                        }

                        leaf result-success-received {
                            type uint64;
                            description "The number of answer messages received with Result-Code AVP in the 2xxx range (Success).";
                        }

                        leaf result-protocol-error-transmitted {
                            type uint64;
                            description "The number of answer messages transmitted with Result-Code AVP in the 3xxx range (Protocol Errors).";
                        }

                        leaf result-protocol-error-received {
                            type uint64;
                            description "The number of answer messages received with Result-Code AVP in the 3xxx range (Protocol Errors).";
                        }

                        leaf result-transient-error-transmitted {
                            type uint64;
                            description "The number of answer messages transmitted with Result-Code AVP in the 4xxx range (Transient Failures).";
                        }

                        leaf result-transient-error-received {
                            type uint64;
                            description "The number of answer messages received with Result-Code AVP in the 4xxx range (Transient Failures).";
                        }

                        leaf result-permantent-failure-transmitted {
                            type uint64;
                            description "The number of answer messages transmitted with Result-Code AVP in the 5xxx range (Permanent Failures).";
                        }

                        leaf result-permantent-failure-received {
                            type uint64;
                            description "The number of answer messages received with Result-Code AVP in the 5xxx range (Permanent Failures).";
                        }

                    } // container messages

                } // container statistics

            } // list diameter-nasreq-policy

            list diameter-session {
                key "session-id";
                description "Enter the diameter-session list instance";

                leaf session-id {
                    type string;
                    description "the session-id of a diameter-session";
                }

                leaf diameter-gx-policy {
                    type types-sros:named-item;
                    description "the diameter-gx-policy name the session was created in";
                }

                leaf diameter-gy-policy {
                    type types-sros:named-item;
                    description "the diameter-gy-policy name the session was created in";
                }

                leaf diameter-nasreq-policy {
                    type types-sros:named-item;
                    description "the diameter-nasreq- policy name the session was created in";
                }

                leaf ccrt-replay-active {
                    type boolean;
                    description "session is in terminate replay";
                }

                leaf expiry-time {
                    type types-sros:time-duration;
                    description "the time left before stopping to send CCR-T messages for this session";
                }

            } // list diameter-session

            list steering-profile {
                key "name";
                description "Enter the steering-profile list instance";

                leaf name {
                    type types-sros:named-item;
                    description "Steering profile name";
                }

                leaf oper-state {
                    type types-sros:oper-state;
                    description "The operational state of this steering profile.";
                }

                leaf ref-count {
                    type uint32;
                    description "The reference count of this steering profile.";
                }

            } // list steering-profile

            list host-tracking-policy {
                key "name";
                description "Enter the host-tracking-policy list instance";

                leaf name {
                    type types-sros:named-item;
                    description "Host tracking policy name";
                }

                list subscriber {
                    key "subscriber-id";
                    description "Enter the subscriber list instance";

                    leaf subscriber-id {
                        type types-submgt:subscriber-id;
                        description "Subscriber Identification string";
                    }

                } // list subscriber

            } // list host-tracking-policy

            list igmp-policy {
                key "name";
                description "Enter the igmp-policy list instance";

                leaf name {
                    type types-sros:named-item;
                    description "Policy name";
                }

                list subscriber {
                    key "subscriber-id";
                    description "Enter the subscriber list instance";

                    leaf subscriber-id {
                        type types-submgt:subscriber-id;
                        description "Subscriber Identification string";
                    }

                } // list subscriber

            } // list igmp-policy

            list mld-policy {
                key "name";
                description "Enter the mld-policy list instance";

                leaf name {
                    type types-sros:named-item;
                    description "Policy name";
                }

                list subscriber {
                    key "subscriber-id";
                    description "Enter the subscriber list instance";

                    leaf subscriber-id {
                        type types-submgt:subscriber-id;
                        description "Subscriber Identification string";
                    }

                } // list subscriber

            } // list mld-policy

            list sub-mcac-policy {
                key "name";
                description "Enter the sub-mcac-policy list instance";

                leaf name {
                    type types-sros:named-item;
                    description "Policy name";
                }

                list subscriber {
                    key "subscriber-id";
                    description "Enter the subscriber list instance";

                    leaf subscriber-id {
                        type types-submgt:subscriber-id;
                        description "Subscriber Identification string";
                    }

                } // list subscriber

            } // list sub-mcac-policy

            container pfcp {
                description "Enter the pfcp context";

                list association {
                    key "name";
                    description "Enter the association list instance";

                    leaf name {
                        type types-sros:named-item;
                        description "PFCP association name";
                    }

                    leaf oper-state {
                        type enumeration {
                            enum "up"                           { value 1; }
                            enum "down"                         { value 2; }
                            enum "in-setup"                     { value 3; }
                            enum "releasing"                    { value 4; }
                        }
                        description "The operational state of the PFCP association";
                    }

                    leaf peer-address {
                        type types-sros:ip-address;
                        description "The actual IP address of the peer.";
                    }

                    leaf node-address {
                        type types-sros:ip-address;
                        description "The actual IP address of the node.";
                    }

                    leaf release-timer-expiry {
                        type yang:date-and-time;
                        description "Timestamp when the release-timer will expire";
                    }

                    container peer-node-id {
                        description "Enter the peer-node-id context";

                        leaf ip-address {
                            type types-sros:ip-address;
                            description "The actual peer node id ip-adress.";
                        }

                        leaf fqdn {
                            type types-sros:fully-qualified-domain-name;
                            description "The actual peer node id fully qualified domain name.";
                        }

                    } // container peer-node-id

                    container up-features {
                        description "Enter the up-features context";

                        leaf bucp {
                            type boolean;
                            description "Downlink Data Buffering";
                        }

                        leaf ddnd {
                            type boolean;
                            description "Downlink Data Notification Delay";
                        }

                        leaf dlbd {
                            type boolean;
                            description "Downlink Buffering Duration";
                        }

                        leaf trst {
                            type boolean;
                            description "Traffic Steering";
                        }

                        leaf ftup {
                            type boolean;
                            description "F-TEID Allocation/Release";
                        }

                        leaf pfdm {
                            type boolean;
                            description "PFD Management";
                        }

                        leaf heeu {
                            type boolean;
                            description "Header Enrichment of Uplink Traffic";
                        }

                        leaf treu {
                            type boolean;
                            description "Traffic Redirection Enforcement";
                        }

                        leaf empu {
                            type boolean;
                            description "Sending of End Marker Packets";
                        }

                        leaf pdiu {
                            type boolean;
                            description "PDI Optimised Signaling";
                        }

                        leaf udbc {
                            type boolean;
                            description "UL/DL Buffering Control";
                        }

                        leaf quoac {
                            type boolean;
                            description "Quota Action when Reaching Quotas";
                        }

                        leaf trace {
                            type boolean;
                            description "Trace";
                        }

                        leaf frrt {
                            type boolean;
                            description "Framed Routing";
                        }

                        leaf pfde {
                            type boolean;
                            description "PFD Contents";
                        }

                        leaf epfar {
                            type boolean;
                            description "Enhanced PFCP Association Release";
                        }

                        leaf dpdra {
                            type boolean;
                            description "Deferred PDR Activation/Deactivation";
                        }

                        leaf adpdp {
                            type boolean;
                            description "Activation/Deactivation of Pre-defined PDRs";
                        }

                        leaf ueip {
                            type boolean;
                            description "Allocating UE IP Addresses or Prefixes";
                        }

                        leaf sset {
                            type boolean;
                            description "PFCP Sessions controlled by different SMFs of a same SMF Set";
                        }

                        leaf mnop {
                            type boolean;
                            description "Measurement Of Number of Packets";
                        }

                        leaf mte {
                            type boolean;
                            description "Multiple Instances of Traffic Endpoint IDs";
                        }

                        leaf bundl {
                            type boolean;
                            description "PFCP Message Bundling";
                        }

                        leaf gcom {
                            type boolean;
                            description "5G VN Group Communication";
                        }

                        leaf mpas {
                            type boolean;
                            description "Multiple PFCP Associations to the SMFs in an SMF Set";
                        }

                        leaf rttl {
                            type boolean;
                            description "Redundant Transmission at Transport Layer";
                        }

                        leaf vtime {
                            type boolean;
                            description "Quota Validity Time";
                        }

                        leaf norp {
                            type boolean;
                            description "Number of Reports";
                        }

                        leaf iptv {
                            type boolean;
                            description "Supports IPTV Service";
                        }

                        leaf ip6pl {
                            type boolean;
                            description "Supports UE IPv6 addresses allocation";
                        }

                        leaf tscu {
                            type boolean;
                            description "Time Sensitive Communication";
                        }

                    } // container up-features

                    container up-bbf-features {
                        description "Enter the up-bbf-features context";

                        leaf pppoe {
                            type boolean;
                            description "Supports PPPoE";
                        }

                        leaf ipoe {
                            type boolean;
                            description "Supports IPoE";
                        }

                        leaf lac {
                            type boolean;
                            description "Supports LAC";
                        }

                        leaf lns {
                            type boolean;
                            description "Supports LNS";
                        }

                        leaf lcpko {
                            type boolean;
                            description "Supports PPP LCP echo offload";
                        }

                        leaf natcp {
                            type boolean;
                            description "Supports NAT and Port Forwarding - public IP assigment performed by CP";
                        }

                        leaf natup {
                            type boolean;
                            description "Supports NAT and Port Forwarding - public IP assigment performed by UP";
                        }

                    } // container up-bbf-features

                    container up-nokia-features {
                        description "Enter the up-nokia-features context";

                        leaf bulkaudit {
                            type boolean;
                            description "Supports bulk audit feature";
                        }

                        leaf nat {
                            type boolean;
                            description "Supports subscriber aware NAT";
                        }

                        leaf lac {
                            type boolean;
                            description "Supports L2TP LAC";
                        }

                        leaf sssg {
                            type boolean;
                            description "Supports Shared Subnet Signalling";
                        }

                        leaf fsg {
                            type boolean;
                            description "Supports Subscriber Fate Sharing Groups";
                        }

                    } // container up-nokia-features

                    container cp-features {
                        description "Enter the cp-features context";

                        leaf load {
                            type boolean;
                            description "Load Control";
                        }

                        leaf ovrl {
                            type boolean;
                            description "Overload Control";
                        }

                        leaf epfar {
                            type boolean;
                            description "Enhanced PFCP Association Release";
                        }

                        leaf sset {
                            type boolean;
                            description "PFCP Sessions controlled by different SMFs of a same SMF Set";
                        }

                        leaf bundl {
                            type boolean;
                            description "PFCP Message Bundling";
                        }

                        leaf mpas {
                            type boolean;
                            description "Multiple PFCP Associations from an SMF to a single UPF";
                        }

                    } // container cp-features

                    list session {
                        key "local-session-id";
                        description "Enter the session list instance";

                        leaf local-session-id {
                            type types-submgt:pfcp-session-id;
                            description "Local Session Identifier (SE-ID)";
                        }

                        leaf is-default-tunnel {
                            type boolean;
                            description "Indicates if this is UPF session used as default tunnel";
                        }

                        leaf remote-session-id {
                            type types-submgt:pfcp-session-id;
                            description "Remote Session Identifier (SE-ID)";
                        }

                        container local-peer {
                            description "Enter the local-peer context";

                            leaf ip-address {
                                type types-sros:ip-address;
                                description "Local peer address";
                            }

                            leaf router-instance {
                                type types-sros:named-item-64;
                                description "Router instance used for the local peer.";
                            }

                        } // container local-peer

                        container remote-peer {
                            description "Enter the remote-peer context";

                            leaf ip-address {
                                type types-sros:ip-address;
                                description "Remote peer address";
                            }

                        } // container remote-peer

                        container ibcp {
                            description "Enter the ibcp context";

                            leaf upstream-pdr-id {
                                type types-submgt:pfcp-pdr-id;
                                description "Upstream Packet Data Rule Identifier (PDR-ID)";
                            }

                            leaf downstream-pdr-id {
                                type types-submgt:pfcp-pdr-id;
                                description "Downstream stream Packet Data Rule Identifier (PDR-ID)";
                            }

                            leaf local-te-id {
                                type types-submgt:pfcp-te-id;
                                description "Local Traffic Endpoint Identifier (TE-ID)";
                            }

                            leaf remote-te-id {
                                type types-submgt:pfcp-te-id;
                                description "Remote Traffic Endpoint Identifier (TE-ID)";
                            }

                            container protocols {
                                description "Enter the protocols context";

                                leaf ipoedhcp4 {
                                    type boolean;
                                    description "Supports ipoe-dhcpv4";
                                }

                                leaf ipoedhcp6 {
                                    type boolean;
                                    description "Supports ipoe-dhcpv6";
                                }

                                leaf ipoers {
                                    type boolean;
                                    description "Supports ipoe-router-solicit";
                                }

                                leaf pppoedisc {
                                    type boolean;
                                    description "Supports pppoe discovery";
                                }

                            } // container protocols

                        } // container ibcp

                        container data {
                            description "Enter the data context";

                            leaf upstream-pdr-id {
                                type types-submgt:pfcp-pdr-id;
                                description "Upstream Packet Data Rule Identifier (PDR-ID)";
                            }

                            leaf downstream-pdr-id {
                                type types-submgt:pfcp-pdr-id;
                                description "Downstream Packet Data Rule Identifier (PDR-ID)";
                            }

                            leaf session-type {
                                type enumeration {
                                    enum "ppp"                          { value 1; }
                                    enum "ipoe"                         { value 2; }
                                    enum "ppp-lac"                      { value 3; }
                                }
                                description "Type of session";
                            }

                            leaf sap {
                                type types-sros:sap;
                                description "sap used by the session";
                            }

                            leaf mac-address {
                                type yang:mac-address;
                                description "MAC address";
                            }

                            leaf state-id {
                                type types-sros:hex-string {
                                    length "1..128";
                                }
                                description "state id";
                            }

                            leaf pppoe-session-id {
                                type uint32;
                                description "Present if applicable";
                            }

                            container subscriber-spi-session {
                                description "Enter the subscriber-spi-session context";

                                leaf subscriber-id {
                                    type types-submgt:subscriber-id;
                                    description "Subscriber identifier";
                                }

                                leaf sla-profile-instance {
                                    type types-submgt:sla-profile-instance-id;
                                    description "SLA profile instance identifier";
                                }

                                leaf session-type {
                                    type types-submgt:session-type;
                                    description "Session type";
                                }

                                leaf session-id {
                                    type types-submgt:session-id;
                                    description "Session identifier";
                                }

                            } // container subscriber-spi-session

                        } // container data

                    } // list session

                    container statistics {
                        description "Enter the statistics context";

                        leaf last-cleared {
                            type yang:date-and-time;
                            description "time when statistics were cleared.";
                        }

                        container session {
                            description "Enter the session context";

                            leaf establishment-request {
                                type uint32;
                                description "The number of Session Establishment Requests received.";
                            }

                            leaf establishment-response {
                                type uint32;
                                description "The number of Session Establishment Responses accepted transmitted.";
                            }

                            leaf establishment-response-fail {
                                type uint32;
                                description "The number of Session Establishment Responses rejected transmitted.";
                            }

                            leaf modification-request {
                                type uint32;
                                description "The number of Session Modification Requests received.";
                            }

                            leaf modification-response {
                                type uint32;
                                description "The number of Session Modification Responses accepted transmitted.";
                            }

                            leaf modification-response-fail {
                                type uint32;
                                description "The number of Session Modification Responses rejected transmitted.";
                            }

                            leaf deletion-request {
                                type uint32;
                                description "The number of Session Deletion Requests received.";
                            }

                            leaf deletion-response {
                                type uint32;
                                description "The number of Session Deletion Responses accepted transmitted.";
                            }

                            leaf deletion-response-fail {
                                type uint32;
                                description "The number of Session Deletion Responses rejected transmitted.";
                            }

                            leaf report-request {
                                type uint32;
                                description "The number of Session Report Requests received.";
                            }

                            leaf report-response {
                                type uint32;
                                description "The number of Session Report Responses accepted transmitted.";
                            }

                            leaf report-response-fail {
                                type uint32;
                                description "The number of Session Report Responses rejected transmitted.";
                            }

                            leaf downlink-data-report-request {
                                type uint32;
                                description "The number of Session Downlink Data Report Requests received.";
                            }

                            leaf downlink-data-report-response {
                                type uint32;
                                description "The number of Session Downlink Data Report Responses accepted transmitted.";
                            }

                            leaf downlink-data-report-response-fail {
                                type uint32;
                                description "The number of Session Downlink Data Report Responses rejected transmitted.";
                            }

                            leaf usage-report-request {
                                type uint32;
                                description "The number of Session Usage Report Requests received.";
                            }

                            leaf usage-report-response {
                                type uint32;
                                description "The number of Session Usage Report Responses accepted transmitted.";
                            }

                            leaf usage-report-response-fail {
                                type uint32;
                                description "The number of Session Usage Report Responses rejected transmitted.";
                            }

                            leaf error-indication-report-request {
                                type uint32;
                                description "The number of Session Error Indication Report Requests received.";
                            }

                            leaf error-indication-report-response {
                                type uint32;
                                description "The number of Session Error Indication Report Responses accepted transmitted.";
                            }

                            leaf error-indication-report-response-fail {
                                type uint32;
                                description "The number of Session Error Indication Report Responses rejected transmitted.";
                            }

                            leaf user-plane-inactivity-report-request {
                                type uint32;
                                description "The number of Session User Plane Inactivity Report Requests received.";
                            }

                            leaf user-plane-inactivity-report-response {
                                type uint32;
                                description "The number of Session User Plane Inactivity Report Responses accepted transmitted.";
                            }

                            leaf user-plane-inactivity-report-response-fail {
                                type uint32;
                                description "The number of Session User Plane Inactivity Report Responses rejected transmitted.";
                            }

                        } // container session

                        container session-audit {
                            description "Enter the session-audit context";

                            leaf modification-request {
                                type uint32;
                                description "The number of Session Audit Modification Requests received.";
                            }

                            leaf modification-response {
                                type uint32;
                                description "The number of Session Audit Modification Responses accepted transmitted.";
                            }

                            leaf modification-response-fail {
                                type uint32;
                                description "The number of Session Audit Modification Responses rejected transmitted.";
                            }

                            leaf report-request {
                                type uint32;
                                description "The number of Session Audit Report Requests transmitted.";
                            }

                            leaf report-response {
                                type uint32;
                                description "The number of Session Audit Report Responses accepted received.";
                            }

                            leaf report-response-fail {
                                type uint32;
                                description "The number of Session Audit Report Responses rejected received.";
                            }

                        } // container session-audit

                        container node {
                            description "Enter the node context";

                            leaf report-request {
                                type uint32;
                                description "The number of Node Report Requests received.";
                            }

                            leaf report-response {
                                type uint32;
                                description "The number of Node Report Responses accepted transmitted.";
                            }

                            leaf report-response-fail {
                                type uint32;
                                description "The number of Node Report Responses rejected transmitted.";
                            }

                            leaf association-setup-request-rx {
                                type uint32;
                                description "The number of Association Setup Requests received.";
                            }

                            leaf association-setup-request-tx {
                                type uint32;
                                description "The number of Association Setup Requests transmitted.";
                            }

                            leaf association-setup-response-rx {
                                type uint32;
                                description "The number of Association Setup Responses accepted received.";
                            }

                            leaf association-setup-response-tx {
                                type uint32;
                                description "The number of Association Setup Responses accepted transmitted.";
                            }

                            leaf association-setup-response-fail-rx {
                                type uint32;
                                description "The number of Association Setup Responses rejected received.";
                            }

                            leaf association-setup-response-fail-tx {
                                type uint32;
                                description "The number of Association Setup Responses rejected transmitted.";
                            }

                            leaf association-update-request-rx {
                                type uint32;
                                description "The number of Association Update Requests received.";
                            }

                            leaf association-update-request-tx {
                                type uint32;
                                description "The number of Association Update Requests transmitted.";
                            }

                            leaf association-update-response-rx {
                                type uint32;
                                description "The number of Association Update Responses accepted received.";
                            }

                            leaf association-update-response-tx {
                                type uint32;
                                description "The number of Association Update Responses accepted transmitted.";
                            }

                            leaf association-update-response-fail-rx {
                                type uint32;
                                description "The number of Association Update Responses rejected received.";
                            }

                            leaf association-update-response-fail-tx {
                                type uint32;
                                description "The number of Association Update Responses rejected transmitted.";
                            }

                            leaf association-update-request-arr-tx {
                                type uint32;
                                description "The number of Association Update Requests with Association Release messages transmitted.";
                            }

                            leaf association-update-request-grp-tx {
                                type uint32;
                                description "The number of Association Update Requests with Graceful Release messages transmitted.";
                            }

                            leaf association-update-request-arr-grp-tx {
                                type uint32;
                                description "The number of Association Update Requests with Association Release and Graceful Release messages transmitted.";
                            }

                            leaf association-release-request-rx {
                                type uint32;
                                description "The number of Association Release Requests received.";
                            }

                            leaf association-release-response-tx {
                                type uint32;
                                description "The number of Association Release Responses accepted transmitted.";
                            }

                            leaf association-release-response-fail-tx {
                                type uint32;
                                description "The number of Association Release Responses rejected transmitted.";
                            }

                            leaf heartbeat-request-rx {
                                type uint32;
                                description "The number of Heartbeat Requests received.";
                            }

                            leaf heartbeat-request-tx {
                                type uint32;
                                description "The number of Heartbeat Requests transmitted.";
                            }

                            leaf heartbeat-response-rx {
                                type uint32;
                                description "The number of Heartbeat Responses received.";
                            }

                            leaf heartbeat-response-tx {
                                type uint32;
                                description "The number of Heartbeat Responses transmitted.";
                            }

                            leaf heartbeat-aud-start-request-rx {
                                type uint32;
                                description "The number of Heartbeat Audit Start Requests received.";
                            }

                            leaf heartbeat-aud-end-request-rx {
                                type uint32;
                                description "The number of Heartbeat Audit End Requests received.";
                            }

                            leaf heartbeat-aud-trig-request-tx {
                                type uint32;
                                description "The number of Heartbeat Audit Trigger Requests transmitted.";
                            }

                            leaf heartbeat-aud-start-response-tx {
                                type uint32;
                                description "The number of Heartbeat Audit Start Responses transmitted.";
                            }

                            leaf heartbeat-aud-end-response-tx {
                                type uint32;
                                description "The number of Heartbeat Audit End Responses transmitted.";
                            }

                            leaf heartbeat-aud-trig-response-rx {
                                type uint32;
                                description "The number of Heartbeat Audit Trigger Responses received.";
                            }

                        } // container node

                        container ibcp {
                            description "Enter the ibcp context";

                            leaf ipoe-rx {
                                type uint32;
                                description "The number of ipoe ibcp pkts successful received.";
                            }

                            leaf pppoe-ctrl-rx {
                                type uint32;
                                description "The number of pppoe ctrl ibcp pkts successful received.";
                            }

                            leaf pppoe-data-rx {
                                type uint32;
                                description "The number of pppoe data ibcp pkts successful received.";
                            }

                            leaf data-trigger-rx {
                                type uint32;
                                description "The number of data trigger pkts successful received.";
                            }

                            leaf to-smf-tx {
                                type uint32;
                                description "The number of ibcp pkts successful transmitted to smf.";
                            }

                            leaf missing-pkt-detection-rule-rx {
                                type uint32;
                                description "The number of ibcp rx pkts dropped because no matching rule session available.";
                            }

                            leaf default-tunnel-trigger-missing {
                                type uint32;
                                description "The number of ibcp pkts discarded because of a default tunnel trigger missing on smf.";
                            }

                            leaf default-tunnel-missing {
                                type uint32;
                                description "The number of ibcp pkts discarded because there is no default tunnel.";
                            }

                            leaf parsing-error-rx {
                                type uint32;
                                description "The number of ibcp rx pkts dropped because of a parsing error.";
                            }

                            leaf error-tx {
                                type uint32;
                                description "The number of ibcp tx pkts failed to sent to the smf.";
                            }

                            leaf def-tunnel-overwrite {
                                type uint32;
                                description "The number of times the default tunnel is overwritten with another id.";
                            }

                        } // container ibcp

                    } // container statistics

                } // list association

                container statistics {
                    description "Enter the statistics context";

                    container session {
                        description "Enter the session context";

                        leaf establishment-request {
                            type uint32;
                            description "The number of Session Establishment Requests received.";
                        }

                        leaf establishment-response {
                            type uint32;
                            description "The number of Session Establishment Responses accepted transmitted.";
                        }

                        leaf establishment-response-fail {
                            type uint32;
                            description "The number of Session Establishment Responses rejected transmitted.";
                        }

                        leaf modification-request {
                            type uint32;
                            description "The number of Session Modification Requests received.";
                        }

                        leaf modification-response {
                            type uint32;
                            description "The number of Session Modification Responses accepted transmitted.";
                        }

                        leaf modification-response-fail {
                            type uint32;
                            description "The number of Session Modification Responses rejected transmitted.";
                        }

                        leaf deletion-request {
                            type uint32;
                            description "The number of Session Deletion Requests received.";
                        }

                        leaf deletion-response {
                            type uint32;
                            description "The number of Session Deletion Responses accepted transmitted.";
                        }

                        leaf deletion-response-fail {
                            type uint32;
                            description "The number of Session Deletion Responses rejected transmitted.";
                        }

                        leaf report-request {
                            type uint32;
                            description "The number of Session Report Requests received.";
                        }

                        leaf report-response {
                            type uint32;
                            description "The number of Session Report Responses accepted transmitted.";
                        }

                        leaf report-response-fail {
                            type uint32;
                            description "The number of Session Report Responses rejected transmitted.";
                        }

                        leaf downlink-data-report-request {
                            type uint32;
                            description "The number of Session Downlink Data Report Requests received.";
                        }

                        leaf downlink-data-report-response {
                            type uint32;
                            description "The number of Session Downlink Data Report Responses accepted transmitted.";
                        }

                        leaf downlink-data-report-response-fail {
                            type uint32;
                            description "The number of Session Downlink Data Report Responses rejected transmitted.";
                        }

                        leaf usage-report-request {
                            type uint32;
                            description "The number of Session Usage Report Requests received.";
                        }

                        leaf usage-report-response {
                            type uint32;
                            description "The number of Session Usage Report Responses accepted transmitted.";
                        }

                        leaf usage-report-response-fail {
                            type uint32;
                            description "The number of Session Usage Report Responses rejected transmitted.";
                        }

                        leaf error-indication-report-request {
                            type uint32;
                            description "The number of Session Error Indication Report Requests received.";
                        }

                        leaf error-indication-report-response {
                            type uint32;
                            description "The number of Session Error Indication Report Responses accepted transmitted.";
                        }

                        leaf error-indication-report-response-fail {
                            type uint32;
                            description "The number of Session Error Indication Report Responses rejected transmitted.";
                        }

                        leaf user-plane-inactivity-report-request {
                            type uint32;
                            description "The number of Session User Plane Inactivity Report Requests received.";
                        }

                        leaf user-plane-inactivity-report-response {
                            type uint32;
                            description "The number of Session User Plane Inactivity Report Responses accepted transmitted.";
                        }

                        leaf user-plane-inactivity-report-response-fail {
                            type uint32;
                            description "The number of Session User Plane Inactivity Report Responses rejected transmitted.";
                        }

                    } // container session

                    container session-audit {
                        description "Enter the session-audit context";

                        leaf modification-request {
                            type uint32;
                            description "The number of Session Audit Modification Requests received.";
                        }

                        leaf modification-response {
                            type uint32;
                            description "The number of Session Audit Modification Responses accepted transmitted.";
                        }

                        leaf modification-response-fail {
                            type uint32;
                            description "The number of Session Audit Modification Responses rejected transmitted.";
                        }

                        leaf report-request {
                            type uint32;
                            description "The number of Session Audit Report Requests transmitted.";
                        }

                        leaf report-response {
                            type uint32;
                            description "The number of Session Audit Report Responses accepted received.";
                        }

                        leaf report-response-fail {
                            type uint32;
                            description "The number of Session Audit Report Responses rejected received.";
                        }

                    } // container session-audit

                    container node {
                        description "Enter the node context";

                        leaf report-request {
                            type uint32;
                            description "The number of Node Report Requests received.";
                        }

                        leaf report-response {
                            type uint32;
                            description "The number of Node Report Responses accepted transmitted.";
                        }

                        leaf report-response-fail {
                            type uint32;
                            description "The number of Node Report Responses rejected transmitted.";
                        }

                        leaf association-setup-request-rx {
                            type uint32;
                            description "The number of Association Setup Requests received.";
                        }

                        leaf association-setup-request-tx {
                            type uint32;
                            description "The number of Association Setup Requests transmitted.";
                        }

                        leaf association-setup-response-rx {
                            type uint32;
                            description "The number of Association Setup Responses accepted received.";
                        }

                        leaf association-setup-response-tx {
                            type uint32;
                            description "The number of Association Setup Responses accepted transmitted.";
                        }

                        leaf association-setup-response-fail-rx {
                            type uint32;
                            description "The number of Association Setup Responses rejected received.";
                        }

                        leaf association-setup-response-fail-tx {
                            type uint32;
                            description "The number of Association Setup Responses rejected transmitted.";
                        }

                        leaf association-update-request-rx {
                            type uint32;
                            description "The number of Association Update Requests received.";
                        }

                        leaf association-update-request-tx {
                            type uint32;
                            description "The number of Association Update Requests transmitted.";
                        }

                        leaf association-update-response-rx {
                            type uint32;
                            description "The number of Association Update Responses accepted received.";
                        }

                        leaf association-update-response-tx {
                            type uint32;
                            description "The number of Association Update Responses accepted transmitted.";
                        }

                        leaf association-update-response-fail-rx {
                            type uint32;
                            description "The number of Association Update Responses rejected received.";
                        }

                        leaf association-update-response-fail-tx {
                            type uint32;
                            description "The number of Association Update Responses rejected transmitted.";
                        }

                        leaf association-update-request-arr-tx {
                            type uint32;
                            description "The number of Association Update Requests with Association Release messages transmitted.";
                        }

                        leaf association-update-request-grp-tx {
                            type uint32;
                            description "The number of Association Update Requests with Graceful Release messages transmitted.";
                        }

                        leaf association-update-request-arr-grp-tx {
                            type uint32;
                            description "The number of Association Update Requests with Association Release and Graceful Release messages transmitted.";
                        }

                        leaf association-release-request-rx {
                            type uint32;
                            description "The number of Association Release Requests received.";
                        }

                        leaf association-release-response-tx {
                            type uint32;
                            description "The number of Association Release Responses accepted transmitted.";
                        }

                        leaf association-release-response-fail-tx {
                            type uint32;
                            description "The number of Association Release Responses rejected transmitted.";
                        }

                        leaf heartbeat-request-rx {
                            type uint32;
                            description "The number of Heartbeat Requests received.";
                        }

                        leaf heartbeat-request-tx {
                            type uint32;
                            description "The number of Heartbeat Requests transmitted.";
                        }

                        leaf heartbeat-response-rx {
                            type uint32;
                            description "The number of Heartbeat Responses received.";
                        }

                        leaf heartbeat-response-tx {
                            type uint32;
                            description "The number of Heartbeat Responses transmitted.";
                        }

                        leaf heartbeat-aud-start-request-rx {
                            type uint32;
                            description "The number of Heartbeat Audit Start Requests received.";
                        }

                        leaf heartbeat-aud-end-request-rx {
                            type uint32;
                            description "The number of Heartbeat Audit End Requests received.";
                        }

                        leaf heartbeat-aud-trig-request-tx {
                            type uint32;
                            description "The number of Heartbeat Audit Trigger Requests transmitted.";
                        }

                        leaf heartbeat-aud-start-response-tx {
                            type uint32;
                            description "The number of Heartbeat Audit Start Responses transmitted.";
                        }

                        leaf heartbeat-aud-end-response-tx {
                            type uint32;
                            description "The number of Heartbeat Audit End Responses transmitted.";
                        }

                        leaf heartbeat-aud-trig-response-rx {
                            type uint32;
                            description "The number of Heartbeat Audit Trigger Responses received.";
                        }

                    } // container node

                    container ibcp {
                        description "Enter the ibcp context";

                        leaf ipoe-rx {
                            type uint32;
                            description "The number of ipoe ibcp pkts successful received.";
                        }

                        leaf pppoe-ctrl-rx {
                            type uint32;
                            description "The number of pppoe ctrl ibcp pkts successful received.";
                        }

                        leaf pppoe-data-rx {
                            type uint32;
                            description "The number of pppoe data ibcp pkts successful received.";
                        }

                        leaf data-trigger-rx {
                            type uint32;
                            description "The number of data trigger pkts successful received.";
                        }

                        leaf to-smf-tx {
                            type uint32;
                            description "The number of ibcp pkts successful transmitted to smf.";
                        }

                        leaf missing-pkt-detection-rule-rx {
                            type uint32;
                            description "The number of ibcp rx pkts dropped because no matching rule session available.";
                        }

                        leaf default-tunnel-trigger-missing {
                            type uint32;
                            description "The number of ibcp pkts discarded because of a default tunnel trigger missing on smf.";
                        }

                        leaf default-tunnel-missing {
                            type uint32;
                            description "The number of ibcp pkts discarded because there is no default tunnel.";
                        }

                        leaf parsing-error-rx {
                            type uint32;
                            description "The number of ibcp rx pkts dropped because of a parsing error.";
                        }

                        leaf error-tx {
                            type uint32;
                            description "The number of ibcp tx pkts failed to sent to the smf.";
                        }

                        leaf def-tunnel-overwrite {
                            type uint32;
                            description "The number of times the default tunnel is overwritten with another id.";
                        }

                    } // container ibcp

                } // container statistics

                list peer {
                    key "router-instance ip-address local-ip-address";
                    description "Enter the peer list instance";

                    leaf router-instance {
                        type string;
                        description "The name of the router used for this PFCP peer";
                    }

                    leaf ip-address {
                        type types-sros:ip-address;
                        description "Identifies the peer ip-address of the mgmt path";
                    }

                    leaf local-ip-address {
                        type types-sros:ip-address;
                        description "Identifies the local ip-address of the mgmt path";
                    }

                    leaf path-mgmt-state {
                        type enumeration {
                            enum "idle"                         { value 0; }
                            enum "up"                           { value 1; }
                            enum "down"                         { value 2; }
                            enum "restart"                      { value 3; }
                            enum "restoration"                  { value 4; }
                            enum "heartbeattimeout"             { value 5; }
                        }
                        description "The path management state of the peer";
                    }

                    leaf restart-reason {
                        type enumeration {
                            enum "none"                         { value 1; }
                            enum "unknown"                      { value 2; }
                            enum "heartbeatmsgreq"              { value 3; }
                            enum "heartbeatmsgresp"             { value 4; }
                            enum "peeradded"                    { value 5; }
                        }
                        description "The reason why the path-mgmt-state is restarted";
                    }

                    leaf association {
                        type types-sros:named-item;
                        description "The pfcp association the peer is linked to";
                    }

                    leaf path-restoration-timer-expiry {
                        type yang:date-and-time;
                        description "Timestamp when the path-restoration-timer will expire";
                    }

                } // list peer

                container up-resiliency {
                    description "Enter the up-resiliency context";

                    container health {
                        description "Enter the health context";

                        list network-instance {
                            key "id";
                            description "Enter the network-instance list instance";

                            leaf id {
                                type types-services:service-name;
                                description "Network Instance";
                            }

                            leaf health {
                                type int32;
                                description "Health of the Network Instance";
                            }

                            leaf last-changed {
                                type yang:timestamp;
                                description "Timestanp when the Network Instance health was last changed";
                            }

                            leaf last-reported {
                                type yang:timestamp;
                                description "Timestanp when the Network Instance health was last reported";
                            }

                            leaf oper-flags {
                                type bits {
                                    bit monitor-conflict               { position 0; }
                                }
                                description "Operational state of the Network Instance";
                            }

                            leaf service-id {
                                type types-services:service-id;
                                description "Service Id of the Network Instance";
                            }

                        } // list network-instance

                        list l2-access-id {
                            key "id";
                            description "Enter the l2-access-id list instance";

                            leaf id {
                                type string {
                                    length "1..64";
                                }
                                description "L2-Access Id";
                            }

                            leaf health {
                                type int32;
                                description "Health of the L2-Access Id";
                            }

                            leaf last-changed {
                                type yang:timestamp;
                                description "Timestanp when the L2-Access Id health was last changed";
                            }

                            leaf last-reported {
                                type yang:timestamp;
                                description "Timestanp when the L2-Access Id health was last reported";
                            }

                            leaf oper-flags {
                                type bits {
                                    bit monitor-conflict               { position 0; }
                                }
                                description "Operational state of the L2-Access Id";
                            }

                            leaf service-id {
                                type types-services:service-id;
                                description "Service Id of the L2-Access Id";
                            }

                            leaf sap-id {
                                type types-sros:sap;
                                description "SAP Id of the L2-Access Id";
                            }

                        } // list l2-access-id

                        container statistics {
                            description "Enter the statistics context";

                            leaf network-instances-number {
                                type uint32;
                                description "Number of Network Instances";
                            }

                            leaf network-instances-number-updates {
                                type uint32;
                                description "Number of Network Instance Updates";
                            }

                            leaf network-instances-number-update-fails {
                                type uint32;
                                description "Number of Network Instance Update Fails";
                            }

                            leaf l2-access-ids-number {
                                type uint32;
                                description "Number of L2 Access Ids";
                            }

                            leaf l2-access-ids-number-updates {
                                type uint32;
                                description "Number of L2 Access Id Updates";
                            }

                            leaf l2-access-ids-number-update-fails {
                                type uint32;
                                description "Number of L2 Access Id Update Fails";
                            }

                        } // container statistics

                    } // container health

                    list fate-sharing-group {
                        key "fsg-id";
                        description "Enter the fate-sharing-group list instance";

                        leaf fsg-id {
                            type uint32;
                            description "Fate Sharing Group Id";
                        }

                        leaf last-changed {
                            type yang:timestamp;
                            description "Timestanp when the Fate Sharing Group was last changed";
                        }

                        leaf oper-state {
                            type enumeration {
                                enum "standby"                      { value 0; }
                                enum "active"                       { value 1; }
                            }
                            description "Operation State of the Fate Sharing Group";
                        }

                        leaf oper-flags {
                            type bits {
                                bit network-connectivity-down      { position 0; }
                            }
                            description "Operational state of the Fate Sahring Group";
                        }

                        leaf cp-oper-state {
                            type enumeration {
                                enum "standby"                      { value 0; }
                                enum "active"                       { value 1; }
                            }
                            description "Operation State of the Control Plane for this FSG";
                        }

                        leaf become-active {
                            type uint32;
                            description "Number of times that the Fate Sharing Group became active";
                        }

                        leaf become-standby {
                            type uint32;
                            description "Number of times that the Fate Sharing Group became standby";
                        }

                        leaf pfcp-sessions {
                            type uint32;
                            description "Number of PFCP sessions that exists in this Fate Sharing Group";
                        }

                        list interface {
                            key "service interface-name";
                            description "Enter the interface list instance";

                            leaf service {
                                type types-services:service-name;
                                description "The service to use for this interface";
                            }

                            leaf interface-name {
                                type types-sros:interface-name;
                                description "The interface to use for this interface";
                            }

                            leaf srrp {
                                type uint32;
                                description "The SRRP Instance used for this interface";
                            }

                        } // list interface

                    } // list fate-sharing-group

                } // container up-resiliency

            } // container pfcp

            list sub-profile {
                key "name";
                description "Enter the sub-profile list instance";

                leaf name {
                    type types-sros:external-named-item;
                    description "Subscriber profile name";
                }

                container associations {
                    description "Enter the associations context";

                    leaf current-value {
                        type uint32;
                        description "Current value of submgt counter";
                    }

                    leaf peak-value {
                        type uint32;
                        description "Peak value of submgt counter";
                    }

                    leaf peak-timestamp {
                        type yang:date-and-time;
                        description "Peak timestamp of submgt counter";
                    }

                } // container associations

            } // list sub-profile

            list sla-profile {
                key "name";
                description "Enter the sla-profile list instance";

                leaf name {
                    type types-sros:external-named-item;
                    description "SLA profile name";
                }

                container associations {
                    description "Enter the associations context";

                    leaf current-value {
                        type uint32;
                        description "Current value of submgt counter";
                    }

                    leaf peak-value {
                        type uint32;
                        description "Peak value of submgt counter";
                    }

                    leaf peak-timestamp {
                        type yang:date-and-time;
                        description "Peak timestamp of submgt counter";
                    }

                } // container associations

            } // list sla-profile

            list sub-ident-policy {
                key "name";
                description "Enter the sub-ident-policy list instance";

                leaf name {
                    type types-sros:external-named-item;
                    description "Subscriber identification policy name";
                }

                container primary {
                    description "Enter the primary context";

                    leaf oper-state {
                        type types-sros:oper-state;
                        description "Indicates the operational state of the script.";
                    }

                } // container primary

                container secondary {
                    description "Enter the secondary context";

                    leaf oper-state {
                        type types-sros:oper-state;
                        description "Indicates the operational state of the script.";
                    }

                } // container secondary

                container tertiary {
                    description "Enter the tertiary context";

                    leaf oper-state {
                        type types-sros:oper-state;
                        description "Indicates the operational state of the script.";
                    }

                } // container tertiary

            } // list sub-ident-policy

            container authentication-origin {
                description "Enter the authentication-origin context";

                list priority {
                    key "id";
                    description "Enter the priority list instance";

                    leaf id {
                        type uint32 {
                            range "1..4294967295";
                        }
                        description "Specifies the authentication origin priority.";
                    }

                    leaf source {
                        type types-submgt:authentication-origin;
                        description "The source of authentication having priority specified id.";
                    }

                } // list priority

            } // container authentication-origin

            list msap-policy {
                key "name";
                description "Enter the msap-policy list instance";

                leaf name {
                    type types-sros:named-item;
                    description "Managed SAP policy name";
                }

                leaf associated-msaps {
                    type yang:counter32;
                    description "Indicates the number of MSAPs associated with this MSAP policy.";
                }

            } // list msap-policy

            container statistics {
                description "Enter the statistics context";

                leaf last-reset-peak-values {
                    type yang:date-and-time;
                    description "Timestamp of the last reset of the peak values";
                }

                list ipv4-hosts {
                    key "counter";
                    description "Enter the ipv4-hosts list instance";

                    leaf counter {
                        type types-submgt:submgt-statistics-ipv4-type;
                        description "Type of submgt ipv4 hosts counter";
                    }

                    leaf current-value {
                        type uint32;
                        description "Current value of submgt counter";
                    }

                    leaf peak-value {
                        type uint32;
                        description "Peak value of submgt counter";
                    }

                    leaf peak-timestamp {
                        type yang:date-and-time;
                        description "Peak timestamp of submgt counter";
                    }

                } // list ipv4-hosts

                list ipv6-hosts {
                    key "counter";
                    description "Enter the ipv6-hosts list instance";

                    leaf counter {
                        type types-submgt:submgt-statistics-ipv6-type;
                        description "Type of submgt ipv6 hosts counter";
                    }

                    leaf current-value {
                        type uint32;
                        description "Current value of submgt counter";
                    }

                    leaf peak-value {
                        type uint32;
                        description "Peak value of submgt counter";
                    }

                    leaf peak-timestamp {
                        type yang:date-and-time;
                        description "Peak timestamp of submgt counter";
                    }

                } // list ipv6-hosts

                list total-hosts {
                    key "counter";
                    description "Enter the total-hosts list instance";

                    leaf counter {
                        type types-submgt:submgt-statistics-total-type;
                        description "Type of submgt total hosts counter";
                    }

                    leaf current-value {
                        type uint32;
                        description "Current value of submgt counter";
                    }

                    leaf peak-value {
                        type uint32;
                        description "Peak value of submgt counter";
                    }

                    leaf peak-timestamp {
                        type yang:date-and-time;
                        description "Peak timestamp of submgt counter";
                    }

                } // list total-hosts

                list l2tp {
                    key "counter";
                    description "Enter the l2tp list instance";

                    leaf counter {
                        type types-submgt:submgt-statistics-l2tp-type;
                        description "Type of submgt l2tp counter";
                    }

                    leaf current-value {
                        type uint32;
                        description "Current value of submgt counter";
                    }

                    leaf peak-value {
                        type uint32;
                        description "Peak value of submgt counter";
                    }

                    leaf peak-timestamp {
                        type yang:date-and-time;
                        description "Peak timestamp of submgt counter";
                    }

                } // list l2tp

                list sessions {
                    key "counter";
                    description "Enter the sessions list instance";

                    leaf counter {
                        type types-submgt:submgt-statistics-session-type;
                        description "Type of submgt sessions counter";
                    }

                    leaf current-value {
                        type uint32;
                        description "Current value of submgt counter";
                    }

                    leaf peak-value {
                        type uint32;
                        description "Peak value of submgt counter";
                    }

                    leaf peak-timestamp {
                        type yang:date-and-time;
                        description "Peak timestamp of submgt counter";
                    }

                } // list sessions

            } // container statistics

            container svlan-statistics {
                description "Enter the svlan-statistics context";

                leaf number-of-entries {
                    type uint32;
                    description "The number of entries in the list of Subscriber VLAN statistics";
                }

            } // container svlan-statistics

            container data-trigger {
                description "Enter the data-trigger context";

                leaf packets-received {
                    type yang:counter64;
                    description "The number of data packets received that may trigger creation of data-triggered subscriber hosts on this system.";
                }

                leaf packets-dropped {
                    type yang:counter64;
                    description "The number of data packets dropped that could have triggered creation of data-triggered subscriber hosts on this system.";
                }

                leaf packets-in-queue {
                    type yang:gauge32;
                    description "The number of data packets currently in the waiting queue that may trigger creation of data-triggered subscriber hosts on this system.";
                }

                leaf packets-in-queue-peak {
                    type yang:counter32;
                    description "The maximum value of packets-in-queue since the start-up of this system or the last time that the value of packets-in-queue was reset.";
                }

            } // container data-trigger

            list host-errors {
                key "mac-address timestamp index";
                description "Enter the host-errors list instance";

                leaf mac-address {
                    type yang:mac-address;
                    description "The MAC-address where the error occurred";
                }

                leaf timestamp {
                    type yang:date-and-time;
                    description "The timestamp when the error occurred";
                }

                leaf index {
                    type uint32;
                    description "The chronological order within the timestamp on which the error occurred";
                }

                leaf message {
                    type string {
                        length "1..128";
                    }
                    description "The message associated with the error";
                }

                leaf message-additional-details {
                    type string {
                        length "1..128";
                    }
                    description "Extra text associated with the error";
                }

                leaf service {
                    type types-services:service-name;
                    description "The service where the error occurred";
                }

                leaf sap {
                    type string {
                        length "1..45";
                    }
                    description "The SAP where the error occurred";
                }

                leaf sdp-bind {
                    type types-services:sdp-bind-id;
                    description "The SDP where the error occurred";
                }

            } // list host-errors

            container chassis-information {
                description "Enter the chassis-information context";

                leaf memory-usage-high {
                    type boolean;
                    description "Memory usage of the subscriber management function on this chassis is near the system memory limit.";
                }

                leaf dhcp-overload {
                    type boolean;
                    description "Subscriber management DHCP message processing function is in overload.";
                }

                container accumulated-statistics {
                    description "Enter the accumulated-statistics context";

                    leaf usage-high {
                        type boolean;
                        description "Memory used for subscriber statistics on this chassis is near the system memory limit.";
                    }

                    leaf subscribers {
                        type yang:gauge32;
                        description "The number of subscribers using memory to store accumulated statistics.";
                    }

                } // container accumulated-statistics

            } // container chassis-information

            uses state-submgt-gtp;
            uses state-submgt-isa-filter;
            uses state-submgt-service-chaining-isa-service-chaining;
            uses state-submgt-local-user-db;
            uses state-submgt-subscriber;
            uses state-submgt-vrgw;
            uses state-submgt-wlangw-wlan-gw;
        } // container subscriber-mgmt

    } // grouping state-subscriber-mgmt

}
