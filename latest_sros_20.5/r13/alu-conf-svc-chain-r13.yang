module alu-conf-svc-chain-r13 {
  yang-version "1";

  namespace "urn:alcatel-lucent.com:sros:ns:yang:conf-svc-chain-r13";

  prefix "conf-svc-chain-r13";

  import alu-types {
    prefix "alu";
  }
  import ietf-inet-types {
    prefix "inet";
  }

  alu:alu-major-release "rel20";

  organization "Alcatel-Lucent";

  contact
      "Alcatel-Lucent SR OS Support 
       Web: <http://www.alcatel-lucent.com>";

  description
      "Alcatel-Lucent YANG Data model to configure ISA Service Chaining functions on 
       SR OS based routers. 
       
       Copyright 2014-2015 Alcatel-Lucent, 2016 Nokia. All rights reserved. 
       Reproduction of this document is authorized on the condition that the 
       foregoing copyright notice is included. 
       
       This alu-conf-svc-chain-r13 YANG module embodies Alcatel-Lucent's proprietary 
       intellectual property. Alcatel-Lucent retains all title and ownership in the 
       Specification, including any revisions. 
       
       Alcatel-Lucent grants all interested parties a non-exclusive license to use 
       and distribute an unmodified copy of this Specification in connection with 
       management of Alcatel-Lucent products, and without fee, provided this 
       copyright notice and license appear on all copies. 
       
       This Specification is supplied `as is', and Alcatel-Lucent makes no warranty, 
       either express or implied, as to the use, operation, condition, or performance 
       of the Specification.";

  revision  "2019-08-08";

  grouping alu-conf-svc-chain-r13 {
    container isa-service-chaining {
      description
          "Configure ISA Service Chaining functions";
      container mac-prefix {
        description
            "Configure a unique MAC prefix";
        leaf mac-prefix {
          type string {
            length "1..8";
          }
          description
              "[8 chars] format AA:BB:CC";
        } //mac-prefix

      } //container mac-prefix

      list evpn {
        key "service-id";
        description
            "Configure an Ethernet VPN";
        leaf service-id {
          type uint32 {
            range "1..2147483647";
          }
        } //service-id

        leaf import-mode {
          type enumeration {
            enum none;
            enum bridged;
            enum routed;
          }
        } //import-mode

        leaf prefix-route-resolution {
          type enumeration {
            enum recursive;
            enum non-recursive;
          }
        } //prefix-route-resolution

        container description {
          description
              "Description for the EVPN";
          leaf description-string {
            type string {
              length "1..80";
            }
          } //description-string

        } //container description

        leaf shutdown {
          type boolean;
          description
              "Enable/disable the EVPN.";
        }

        container bgp {
          presence
              "Configure EVPN BGP specific information.";
          container route-distinguisher {
            description
                "Configure route distinguisher information.";
            leaf auto-rd {
              type boolean;
            } //auto-rd

            leaf rd {
              type string {
                length "1..21";
              }
              description
                  "<ip-addr:comm-val>|<2byte-asnumber:ext-comm-val>|<4byte-asnumber:comm-val> 
                   ip-addr - a.b.c.d 
                   comm-val - [0..65535] 
                   2byte-asnumber - [1..65535] 
                   ext-comm-val - [0..4294967295] 
                   4byte-asnumber - [1..4294967295]";
            } //rd

          } //container route-distinguisher

          container route-target {
            description
                "Configure route target information.";
            leaf export {
              type string;
              description
                  "Attribute ext-community for route-target";
            } //export

            leaf import {
              type string;
              description
                  "Attribute ext-community for route-target";
            } //import

          } //container route-target

        } //container bgp

        container export {
          presence
              "Configure EVPN export specific information.";
          container gw-address-range {
            description
                "Configure the gateway address range (V4) for this EVPN service.";
            leaf start {
              type inet:ip-address;
              description
                  "Attribute start for gw-address-range";
            } //start

            leaf end {
              type inet:ip-address;
              description
                  "Attribute end for gw-address-range";
            } //end

          } //container gw-address-range

          container vxlan {
            description
                "Configure the VXLAN created by the EVPN service.";
            leaf vni {
              type uint32 {
                range "1..16777215";
              }
            } //vni

          } //container vxlan

          container ip-advertise-routes {
            description
                "Configure the NAT pools to be used for this EVPN service.";
            list pool {
              key "pool-name";
              description
                  "Configure a list of NAT pools used in EVPN services.";
              leaf pool-name {
                type string;
              } //pool-name

              leaf router {
                type string {
                  length "1..32";
                }
                description
                    "Attribute router-instance for pool";
              } //router

              leaf service-name {
                type string;
              } //service-name

            } //list pool

            leaf shutdown {
              type boolean;
              description
                  "Configure if the system will advertise IP routes from NAT pools.";
            }

          } //container ip-advertise-routes

        } //container export

      } //list evpn

      list vas-filter {
        key "name";
        description
            "Configure a Value Added Service filter.";
        leaf name {
          type string;
        } //name

        container description {
          description
              "Description for the VAS filter.";
          leaf description-string {
            type string {
              length "1..80";
            }
          } //description-string

        } //container description

        list entry {
          key "id";
          description
              "Configure an entry in the VAS filter.";
          leaf id {
            type uint32;
          } //id

          container description {
            description
                "Description for the entry in a VAS filter.";
            leaf description-string {
              type string {
                length "1..80";
              }
            } //description-string

          } //container description

          leaf shutdown {
            type boolean;
            description
                "Enable/disable the entry.";
          }

          list action {
            key "direction";
            description
                "Configure the action that will happen for a match.";
            leaf direction {
              type enumeration {
                enum upstream;
                enum downstream;
              }
            } //direction

            container fail-action {
              description
                  "Configure the fail action.";
              leaf fail-action {
                type enumeration {
                  enum drop;
                  enum forward;
                }
              } //fail-action

            } //container fail-action

            container forward {
              description
                  "Configure the forward action.";
              leaf sf-ip {
                type string;
              } //sf-ip

              leaf svc {
                type uint32 {
                  range "1..2147483647";
                }
              } //svc

              leaf esi {
                type string;
                description
                    "Attribute esi for forward";
              } //esi

            } //container forward

            container insert-nsh {
              presence
                  "Configure the insert-nsh action.";
              container svc-path {
                description
                    "Configure the service path and index for the NSH.";
                leaf path-id {
                  type uint32 {
                    range "0..16777215";
                  }
                } //path-id

                leaf svc-index {
                  type uint32 {
                    range "0..255";
                  }
                } //svc-index

              } //container svc-path

              container meta-data {
                description
                    "Configure the meta-data for the NSH.";
                leaf insert-subscriber-id {
                  type boolean;
                  description
                      "Configure the subscriber-id to insert for the NSH.";
                }

                container opaque-data {
                  description
                      "Configure the opaque meta-data for the NSH.";
                  leaf hex-string {
                    type string;
                  } //hex-string

                } //container opaque-data

              } //container meta-data

            } //container insert-nsh

          } //list action

          container match {
            description
                "Configure the IP protocol values to match.";
            container dscp {
              status "obsolete";
              description
                  "Configure the DSCP value to match.";
              leaf dscp-name {
                type string {
                  length "1..32";
                }
                description
                    "Attribute dscp-name for dscp";
              } //dscp-name

            } //container dscp

            container foreign-ip {
              description
                  "Configure the foreign IP address or prefix to match.";
              leaf ip-address-mask {
                type string;
              } //ip-address-mask

            } //container foreign-ip

            container foreign-port {
              description
                  "Configure the foreign IP port to match.";
              leaf port {
                type int32 {
                  range "1..65535";
                }
              } //port

            } //container foreign-port

            container protocol {
              description
                  "Configure the protocol to match.";
              leaf protocol-id {
                type string;
                description
                    "Attribute protocol-id for protocol";
              } //protocol-id

            } //container protocol

          } //container match

        } //list entry

      } //list vas-filter

    } //container isa-service-chaining

  } //grouping alu-conf-svc-chain-r13

} //module  alu-conf-svc-chain-r13
