module alu-conf-conn-prof-r13 {
  yang-version "1";

  namespace "urn:alcatel-lucent.com:sros:ns:yang:conf-conn-prof-r13";

  prefix "conf-conn-prof-r13";

  import alu-types {
    prefix "alu";
  }

  alu:alu-major-release "rel20";

  organization "Alcatel-Lucent";

  contact
      "Alcatel-Lucent SR OS Support 
       Web: <http://www.alcatel-lucent.com>";

  description
      "Alcatel-Lucent YANG Data model to configure ATM Connection Profiles on SR OS 
       based routers. 
       
       Copyright 2014-2015 Alcatel-Lucent, 2016 Nokia. All rights reserved. 
       Reproduction of this document is authorized on the condition that the 
       foregoing copyright notice is included. 
       
       This alu-conf-conn-prof-r13 YANG module embodies Alcatel-Lucent's proprietary 
       intellectual property. Alcatel-Lucent retains all title and ownership in the 
       Specification, including any revisions. 
       
       Alcatel-Lucent grants all interested parties a non-exclusive license to use 
       and distribute an unmodified copy of this Specification in connection with 
       management of Alcatel-Lucent products, and without fee, provided this 
       copyright notice and license appear on all copies. 
       
       This Specification is supplied `as is', and Alcatel-Lucent makes no warranty, 
       either express or implied, as to the use, operation, condition, or performance 
       of the Specification.";

  revision  "2019-08-08";

  grouping alu-conf-conn-prof-r13 {
    list connection-profile {
      key "conn-prof-id";
      description
          "Configure ATM Connection Profiles";
      leaf conn-prof-id {
        type uint32 {
          range "1..8000";
        }
      } //conn-prof-id

      container description {
        description
            "Configure a connection profile description";
        leaf description-string {
          type string {
            length "1..80";
          }
        } //description-string

      } //container description

      list member {
        key "encap-value";
        description
            "Configure a connection profile member";
        leaf encap-value {
          type string;
          description
              "Attribute encap-value for member";
        } //encap-value

      } //list member

    } //list connection-profile

  } //grouping alu-conf-conn-prof-r13

} //module  alu-conf-conn-prof-r13
