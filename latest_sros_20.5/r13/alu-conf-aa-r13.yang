module alu-conf-aa-r13 {
  yang-version "1";

  namespace "urn:alcatel-lucent.com:sros:ns:yang:conf-aa-r13";

  prefix "conf-aa-r13";

  import alu-types {
    prefix "alu";
  }
  import ietf-inet-types {
    prefix "inet";
  }

  alu:alu-major-release "rel20";

  organization "Alcatel-Lucent";

  contact
      "Alcatel-Lucent SR OS Support 
       Web: <http://www.alcatel-lucent.com>";

  description
      "Alcatel-Lucent YANG Data model to configure Application Assurance (AA) on SR 
       OS based routers. 
       
       Copyright 2014-2015 Alcatel-Lucent, 2016 Nokia. All rights reserved. 
       Reproduction of this document is authorized on the condition that the 
       foregoing copyright notice is included. 
       
       This alu-conf-aa-r13 YANG module embodies Alcatel-Lucent's proprietary 
       intellectual property. Alcatel-Lucent retains all title and ownership in the 
       Specification, including any revisions. 
       
       Alcatel-Lucent grants all interested parties a non-exclusive license to use 
       and distribute an unmodified copy of this Specification in connection with 
       management of Alcatel-Lucent products, and without fee, provided this 
       copyright notice and license appear on all copies. 
       
       This Specification is supplied `as is', and Alcatel-Lucent makes no warranty, 
       either express or implied, as to the use, operation, condition, or performance 
       of the Specification.";

  revision  "2020-03-27";

  grouping alu-conf-aa-r13 {
    container application-assurance {
      description
          "Configure Application Assurance (AA)";
      container bit-rate-high-wmark {
        description
            "Configure high watermark for bit rate traps";
        leaf high-watermark {
          type string;
          description
              "[1..40000 | max] megabits/sec - default max = disabled";
        } //high-watermark

        leaf max {
          type boolean;
        } //max

      } //container bit-rate-high-wmark

      container bit-rate-low-wmark {
        description
            "Configure low watermark for bit rate traps";
        leaf low-watermark {
          type uint32 {
            range "0..39999";
          }
          description
              "[0..39999] megabits/sec - default 0";
        } //low-watermark

      } //container bit-rate-low-wmark

      container datapath-cpu-high-wmark {
        description
            "Configure high watermark for datapth CPU full traps";
        leaf high-watermark {
          type string;
          default 95;
          description
              "[0..100 | max] percent - Default: 95 
               max = disabled";
        } //high-watermark

        leaf max {
          type boolean;
        } //max

      } //container datapath-cpu-high-wmark

      container datapath-cpu-low-wmark {
        description
            "Configure low watermark for datapth CPU full traps";
        leaf low-watermark {
          type uint32 {
            range "0..100";
          }
          default 90;
          description
              "[0..100] percent - Default: 90";
        } //low-watermark

      } //container datapath-cpu-low-wmark

      container flow-setup-high-wmark {
        description
            "Configure high watermark for flow setup rate traps";
        leaf high-watermark {
          type string;
          description
              "[1..800000 | max] flows/sec - default max = disabled";
        } //high-watermark

        leaf max {
          type boolean;
        } //max

      } //container flow-setup-high-wmark

      container flow-setup-low-wmark {
        description
            "Configure low watermark for flow setup rate traps";
        leaf low-watermark {
          type uint32 {
            range "0..799999";
          }
          description
              "[0..799999] flows/sec - default 0";
        } //low-watermark

      } //container flow-setup-low-wmark

      container flow-table-high-wmark {
        description
            "Configure high watermark for flow table full traps";
        leaf high-watermark {
          type uint32 {
            range "0..100";
          }
          default 95;
          description
              "[0..100] percent - default: 95";
        } //high-watermark

      } //container flow-table-high-wmark

      container flow-table-low-wmark {
        description
            "Configure low watermark for flow table full traps";
        leaf low-watermark {
          type uint32 {
            range "0..100";
          }
          default 90;
          description
              "[0..100] percent - default: 90";
        } //low-watermark

      } //container flow-table-low-wmark

      container packet-rate-high-wmark {
        description
            "Configure high watermark for packet rate traps";
        leaf high-watermark {
          type string;
          description
              "[1..59523808 | max] packets/sec - default max = disabled";
        } //high-watermark

        leaf max {
          type boolean;
        } //max

      } //container packet-rate-high-wmark

      container packet-rate-low-wmark {
        description
            "Configure low watermark for packet rate traps";
        leaf low-watermark {
          type uint32 {
            range "0..59523807";
          }
          description
              "[0..59523807] packets/sec - default 0";
        } //low-watermark

      } //container packet-rate-low-wmark

      list aarp {
        key "aarpId";
        description
            "Configure Application Assurance Redundancy Protocol instance";
        leaf aarpId {
          type uint32 {
            range "1..65535";
          }
        } //aarpId

        container description {
          description
              "Configure the AARP instance description";
          leaf description-string {
            type string {
              length "1..80";
            }
          } //description-string

        } //container description

        container master-selection-mode {
          description
              "Configure the AARP master selection mode";
          leaf mode {
            type enumeration {
              enum minimize-switchovers;
              enum inter-chassis-efficiency;
              enum priority-based-balance;
            }
            default "minimize-switchovers";
            description
                "[minimize-switchovers|inter-chassis-efficiency|priority-based-balance] - 
                 Default: minimize-switchovers";
          } //mode

        } //container master-selection-mode

        container peer {
          description
              "Configure the AARP instance peer";
          leaf ip-address {
            type string;
            description
                "ipv4-address - a.b.c.d";
          } //ip-address

        } //container peer

        container peer-endpoint {
          description
              "Configure the AARP instance peer endpoint";
          leaf sap {
            type string;
            description
                "Attribute sap-id for peer-endpoint";
          } //sap

          leaf spoke-sdp {
            type string;
            description
                "sdp-id - [1..32767] 
                 vc-id - [1..4294967295]";
          } //spoke-sdp

          leaf encap-type {
            type enumeration {
              enum dot1q;
              enum null;
              enum qinq;
            }
          } //encap-type

        } //container peer-endpoint

        container priority {
          description
              "Configure the AARP instance priority";
          leaf priority-id {
            type uint32 {
              range "0..255";
            }
          } //priority-id

        } //container priority

        leaf shutdown {
          type boolean;
          description
              "Administratively enable/disable the AARP instance";
        }

      } //list aarp

      list group {
        key "aa-group-id-partition-id";
        description
            "Configure application assurance group/partition";
        leaf aa-group-id-partition-id {
          type string;
          description
              "Attribute aa-group-id:partition-id for group";
        } //aa-group-id-partition-id

        leaf aa-sub-remote {
          type boolean;
          description
              "Enable/disable AA subscriber remote";
        }

        container alternate-cdn-host-matching {
          description
              "Configure the alternate CDN host matching IP prefix list value";
          leaf ip-prefix-list-name {
            type string {
              length "1..32";
            }
          } //ip-prefix-list-name

        } //container alternate-cdn-host-matching

        leaf aqp-initial-lookup {
          type boolean;
          description
              "Enable/disable AQP (Application QoS Policy) initial lookup";
        }

        container description {
          description
              "Configure a partition description";
          leaf description-string {
            type string {
              length "1..80";
            }
          } //description-string

        } //container description

        leaf disable-deferred-billing {
          type boolean;
          description
              "Disable deferred billing";
        }

        leaf http-anti-fraud-cr-eol {
          type boolean;
          description
              "Enable/disable accepting carriage return as end-of-line in HTTP request 
               headers for anti-fraud policy for the group-partition";
        }

        leaf http-anti-fraud-policy {
          type boolean;
          description
              "Enable/disable HTTP anti-fraud policy for the group-partition";
        }

        leaf http-match-all-requests {
          type boolean;
          description
              "Enable/disable constant monitoring of HTTP request strings";
        }

        leaf http-x-online-host {
          type boolean;
          description
              "Enable/disable use of HTTP X-Online-Host header field";
        }

        leaf shallow-inspection {
          type boolean;
          description
              "Enable or disable shallow inspection";
        }

        container aa-sub-congestion-detection {
          description
              "Configure the congestion detection parameters";
          container rtt-threshold {
            description
                "Configure the round trip time threshold";
            leaf threshold {
              type uint32 {
                range "0..500";
              }
              default 173;
              description
                  "[0..500] default - 173 milliseconds";
            } //threshold

          } //container rtt-threshold

          container rtt-threshold-tolerance {
            description
                "Configure round trip time threshold tolerance";
            leaf tolerance {
              type uint32 {
                range "0..100";
              }
              default 50;
              description
                  "[0..100] default - 50 %";
            } //tolerance

          } //container rtt-threshold-tolerance

          leaf shutdown {
            type boolean;
            description
                "administratively enable/disable congestion detection";
          }

        } //container aa-sub-congestion-detection

        container access-network-location {
          description
              "Configure access network location";
          list source {
            key "source-type";
            description
                "Configure the access network location source";
            leaf source-type {
              type enumeration {
                enum mobile-3g;
                enum access-point;
                enum uli-3gpp;
              }
            } //source-type

            leaf level {
              type enumeration {
                enum cell;
                enum transport-network-link;
                enum mac-vlan;
              }
            } //level

            container rtt-threshold {
              description
                  "Configure the ANL source level RTT threshold";
              leaf threshold {
                type uint32 {
                  range "0..500";
                }
                default 173;
                description
                    "[0..500] default - 173 milliseconds";
              } //threshold

            } //container rtt-threshold

            container rtt-threshold-tolerance {
              description
                  "Configure the ANL source level RTT threshold tolerance";
              leaf tolerance {
                type uint32 {
                  range "0..100";
                }
                default 50;
                description
                    "[0..100] default - 50 %";
              } //tolerance

            } //container rtt-threshold-tolerance

          } //list source

        } //container access-network-location

        list certificate-profile {
          key "cert-prof-name";
          description
              "Configure a certificate-profile in the group";
          leaf cert-prof-name {
            type string {
              length "1..32";
            }
          } //cert-prof-name

          container certificate {
            description
                "Configure the certificate file";
            leaf certificate-file {
              type string {
                length "1..95";
              }
            } //certificate-file

          } //container certificate

          container description {
            description
                "Configure the certificate-profile description";
            leaf description-string {
              type string {
                length "1..80";
              }
            } //description-string

          } //container description

          leaf shutdown {
            type boolean;
            description
                "Administratively enable/disable the certificate-profile";
          }

        } //list certificate-profile

        container cflowd {
          description
              "Configure cflowd";
          leaf shutdown {
            type boolean;
            description
                "Administratively enable/disable cflowd";
          }

          container template-retransmit {
            description
                "Configure the time interval to resend template information";
            leaf seconds {
              type uint32 {
                range "10..600";
              }
            } //seconds

          } //container template-retransmit

          list collector {
            key "ip-address-port";
            description
                "Configure cflowd collector";
            leaf ip-address-port {
              type string;
              description
                  "ip-address - a.b.c.d 
                   port - [1..65535]";
            } //ip-address-port

            container description {
              description
                  "Configure description for this cflowd collector";
              leaf description-string {
                type string {
                  length "1..80";
                }
              } //description-string

            } //container description

            leaf shutdown {
              type boolean;
              description
                  "Administratively enable/disable this cflowd collector";
            }

          } //list collector

          container comprehensive {
            description
                "Configure cflowd comprehensive export";
            list app-group {
              key "app-group-name";
              description
                  "Configure application groups to export comprehensive records with cflowd";
              leaf app-group-name {
                type string {
                  length "1..32";
                }
              } //app-group-name

              leaf rate {
                type enumeration {
                  enum flow-rate;
                  enum flow-rate2;
                }
              } //rate

            } //list app-group

            list application {
              key "application-name";
              description
                  "Configure applications to export comprehensive records with cflowd";
              leaf application-name {
                type string {
                  length "1..32";
                }
              } //application-name

              leaf rate {
                type enumeration {
                  enum flow-rate;
                  enum flow-rate2;
                }
              } //rate

            } //list application

            container flow-rate {
              description
                  "Configure cflowd comprehensive flow sample rate";
              leaf sample-rate {
                type uint32 {
                  range "1..1000";
                }
              } //sample-rate

            } //container flow-rate

            container flow-rate2 {
              description
                  "Configure secondary cflowd comprehensive flow sample rate";
              leaf sample-rate {
                type uint32 {
                  range "1..1000";
                }
              } //sample-rate

            } //container flow-rate2

            leaf shutdown {
              type boolean;
              description
                  "Administratively enable/disable comprehensive sampling";
            }

            container template {
              description
                  "Configure comprehensive template";
              container field-selection {
                description
                    "Configure the field selection";
                leaf field-selection {
                  type enumeration {
                    enum legacy;
                    enum dynamic;
                  }
                } //field-selection

              } //container field-selection

              container dynamic-fields {
                presence
                    "Configure the list of dynamic fields";
                container field {
                  description
                      "Configure a dynamic field";
                  leaf field-name {
                    type string {
                    }
                  } //field-name

                  leaf field-name-1 {
                    type string {
                    }
                  } //field-name-1

                } //container field

                leaf shutdown {
                  type boolean;
                  description
                      "Administratively enable/disable comprehensive dynamic templates";
                }

              } //container dynamic-fields

            } //container template

          } //container comprehensive

          container direct-export {
            description
                "Configure cflowd direct export";
            container vlan-id {
              description
                  "Configure cflowd direct export VLAN ID";
              leaf service-port-vlan-id {
                type uint32 {
                  range "1..4094";
                }
              } //service-port-vlan-id

            } //container vlan-id

            list collector {
              key "collector-id";
              description
                  "Configure cflowd direct export collector";
              leaf collector-id {
                type uint32 {
                  range "1..65535";
                }
              } //collector-id

              container description {
                description
                    "Configure description for this cflowd direct export collector";
                leaf description-string {
                  type string {
                    length "1..80";
                  }
                } //description-string

              } //container description

              list address {
                key "ip-address-port";
                description
                    "Configure cflowd direct export collector remote address";
                leaf ip-address-port {
                  type string;
                  description
                      "ip-address - a.b.c.d 
                       port - [1..65535]";
                } //ip-address-port

                leaf shutdown {
                  type boolean;
                  description
                      "Administratively enable/disable this cflowd direct export collector remote 
                       address";
                }

              } //list address

            } //list collector

          } //container direct-export

          container export-override {
            description
                "Configure the cflowd export override";
            leaf mode {
              type enumeration {
                enum mobile;
              }
            } //mode

            container prefix {
              description
                  "Configure cflowd export override prefix";
              leaf prefix-string {
                type string {
                  length "1..8";
                }
              } //prefix-string

            } //container prefix

          } //container export-override

          container obfuscation {
            description
                "Configure cflowd obfuscation values";
            container aes-128-encryption {
              description
                  "Configure cflowd AES-128 encryption for obfuscation";
              leaf plaintext-key-type {
                type enumeration {
                  enum hex;
                  enum ascii;
                }
              } //plaintext-key-type

              leaf key-value {
                type string {
                  length "1..500";
                }
                description
                    "16 ASCII characters 
                     32 hex characters";
              } //key-value

              leaf hash-hash2-custom {
                type enumeration {
                  enum hash;
                  enum hash2;
                  enum custom;
                }
              } //hash-hash2-custom

            } //container aes-128-encryption

            container aes-256-encryption {
              description
                  "Configure cflowd AES-256 encryption for obfuscation";
              leaf plaintext-key-type {
                type enumeration {
                  enum hex;
                  enum ascii;
                }
              } //plaintext-key-type

              leaf key-value {
                type string {
                  length "1..500";
                }
                description
                    "16 ASCII characters 
                     32 hex characters";
              } //key-value

              leaf hash-hash2-custom {
                type enumeration {
                  enum hash;
                  enum hash2;
                  enum custom;
                }
              } //hash-hash2-custom

            } //container aes-256-encryption

          } //container obfuscation

          container pgw-edr {
            description
                "Configure cflowd pgw-edr export";
            container flow-rate {
              description
                  "Configure cflowd pgw-edr flow sampling rate";
              leaf sample-rate {
                type uint32 {
                  range "1..1000";
                }
              } //sample-rate

            } //container flow-rate

            leaf shutdown {
              type boolean;
              description
                  "Administratively enable/disable pgw-edr sampling";
            }

            container template {
              description
                  "Configure pgw-edr performance fields template";
              container field-selection {
                description
                    "Configure the field selection";
                leaf field-selection {
                  type enumeration {
                    enum legacy;
                    enum dynamic;
                  }
                } //field-selection

              } //container field-selection

              container dynamic-fields {
                presence
                    "Configure the list of dynamic fields";
                container field {
                  description
                      "Configure a dynamic field";
                  leaf field-name {
                    type string {
                    }
                  } //field-name

                  leaf field-name-1 {
                    type string {
                    }
                  } //field-name-1

                } //container field

                leaf shutdown {
                  type boolean;
                  description
                      "Administratively enable/disable pgw-edr template";
                }

              } //container dynamic-fields

            } //container template

          } //container pgw-edr

          container rtp-performance {
            description
                "Configure cflowd RTP performance export";
            list app-group {
              key "app-group-name";
              description
                  "Configure application groups to export RTP performance records with cflowd";
              leaf app-group-name {
                type string {
                  length "1..32";
                }
              } //app-group-name

              leaf rate {
                type enumeration {
                  enum flow-rate;
                  enum flow-rate2;
                }
              } //rate

            } //list app-group

            list application {
              key "application-name";
              description
                  "Configure applications to export RTP performance records with cflowd";
              leaf application-name {
                type string {
                  length "1..32";
                }
              } //application-name

              leaf rate {
                type enumeration {
                  enum flow-rate;
                  enum flow-rate2;
                }
              } //rate

            } //list application

            container flow-rate {
              description
                  "Configure cflowd RTP performance flow sample rate";
              leaf sample-rate {
                type uint32 {
                  range "1..1000";
                }
              } //sample-rate

            } //container flow-rate

            container flow-rate2 {
              description
                  "Configure secondary cflowd RTP performance flow sample rate";
              leaf sample-rate {
                type uint32 {
                  range "1..1000";
                }
              } //sample-rate

            } //container flow-rate2

            leaf shutdown {
              type boolean;
              description
                  "Administratively enable/disable RTP performance sampling";
            }

            container audio-template {
              description
                  "Configure rtp performance audio fields template";
              container field-selection {
                description
                    "Configure the field selection";
                leaf field-selection {
                  type enumeration {
                    enum legacy;
                    enum dynamic;
                  }
                } //field-selection

              } //container field-selection

              container dynamic-fields {
                presence
                    "Configure the list of dynamic fields";
                container field {
                  description
                      "Configure a dynamic field";
                  leaf field-name {
                    type string {
                    }
                  } //field-name

                  leaf field-name-1 {
                    type string {
                    }
                  } //field-name-1

                } //container field

                leaf shutdown {
                  type boolean;
                  description
                      "Administratively enable/disable rtp performance audio template";
                }

              } //container dynamic-fields

            } //container audio-template

            container video-template {
              description
                  "Configure rtp performance video fields template";
              container field-selection {
                description
                    "Configure the field selection";
                leaf field-selection {
                  type enumeration {
                    enum legacy;
                    enum dynamic;
                  }
                } //field-selection

              } //container field-selection

              container dynamic-fields {
                presence
                    "Configure the list of dynamic fields";
                container field {
                  description
                      "Configure a dynamic field";
                  leaf field-name {
                    type string {
                    }
                  } //field-name

                  leaf field-name-1 {
                    type string {
                    }
                  } //field-name-1

                } //container field

                leaf shutdown {
                  type boolean;
                  description
                      "Administratively enable/disable rtp performance video dynamic templates";
                }

              } //container dynamic-fields

            } //container video-template

            container voice-template {
              description
                  "Configure rtp performance voice template";
              container field-selection {
                description
                    "Configure the field selection";
                leaf field-selection {
                  type enumeration {
                    enum legacy;
                    enum dynamic;
                  }
                } //field-selection

              } //container field-selection

              container dynamic-fields {
                presence
                    "Configure the list of dynamic fields";
                container field {
                  description
                      "Configure a dynamic field";
                  leaf field-name {
                    type string {
                    }
                  } //field-name

                  leaf field-name-1 {
                    type string {
                    }
                  } //field-name-1

                } //container field

                leaf shutdown {
                  type boolean;
                  description
                      "Administratively enable/disable rtp performance Voice dynamic templates";
                }

              } //container dynamic-fields

            } //container voice-template

          } //container rtp-performance

          container tcp-performance {
            description
                "Configure cflowd TCP performance export";
            list app-group {
              key "app-group-name";
              description
                  "Configure application groups to export TCP performance records with cflowd";
              leaf app-group-name {
                type string {
                  length "1..32";
                }
              } //app-group-name

              leaf rate {
                type enumeration {
                  enum flow-rate;
                  enum flow-rate2;
                }
              } //rate

            } //list app-group

            list application {
              key "application-name";
              description
                  "Configure applications to export TCP performance records with cflowd";
              leaf application-name {
                type string {
                  length "1..32";
                }
              } //application-name

              leaf rate {
                type enumeration {
                  enum flow-rate;
                  enum flow-rate2;
                }
              } //rate

            } //list application

            container flow-rate {
              description
                  "Configure cflowd TCP performance flow sample rate";
              leaf sample-rate {
                type uint32 {
                  range "1..1000";
                }
              } //sample-rate

            } //container flow-rate

            container flow-rate2 {
              description
                  "Configure secondary cflowd TCP performance flow sample rate";
              leaf sample-rate {
                type uint32 {
                  range "1..1000";
                }
              } //sample-rate

            } //container flow-rate2

            leaf shutdown {
              type boolean;
              description
                  "Administratively enable/disable TCP performance sampling";
            }

            container template {
              description
                  "Configure tcp performance fields template";
              container field-selection {
                description
                    "Configure the field selection";
                leaf field-selection {
                  type enumeration {
                    enum legacy;
                    enum dynamic;
                  }
                } //field-selection

              } //container field-selection

              container dynamic-fields {
                presence
                    "Configure the list of dynamic fields";
                container field {
                  description
                      "Configure a dynamic field";
                  leaf field-name {
                    type string {
                    }
                  } //field-name

                  leaf field-name-1 {
                    type string {
                    }
                  } //field-name-1

                } //container field

                leaf shutdown {
                  type boolean;
                  description
                      "Administratively enable/disable tcp template";
                }

              } //container dynamic-fields

            } //container template

          } //container tcp-performance

          container volume {
            description
                "Configure cflowd volume export";
            container rate {
              description
                  "Configure cflowd volume sampling rate";
              leaf sample-rate {
                type uint32 {
                  range "1..10000";
                }
              } //sample-rate

            } //container rate

            leaf shutdown {
              type boolean;
              description
                  "Administratively enable/disable volume sampling";
            }

            container template {
              description
                  "Configure volume template";
              container field-selection {
                description
                    "Configure the field selection";
                leaf field-selection {
                  type enumeration {
                    enum legacy;
                    enum dynamic;
                  }
                } //field-selection

              } //container field-selection

              container dynamic-fields {
                presence
                    "Configure the list of dynamic fields";
                container field {
                  description
                      "Configure a dynamic field";
                  leaf field-name {
                    type string {
                    }
                  } //field-name

                  leaf field-name-1 {
                    type string {
                    }
                  } //field-name-1

                } //container field

                leaf shutdown {
                  type boolean;
                  description
                      "Administratively enable/disable volume template";
                }

              } //container dynamic-fields

            } //container template

          } //container volume

        } //container cflowd

        list dns-ip-cache {
          key "dns-ip-cache-name";
          description
              "Configure a dns-ip-cache";
          leaf dns-ip-cache-name {
            type string {
              length "1..32";
            }
          } //dns-ip-cache-name

          container description {
            description
                "configure a description of the dns-ip-cache";
            leaf description-string {
              type string {
                length "1..80";
              }
            } //description-string

          } //container description

          leaf shutdown {
            type boolean;
            description
                "administratively enable/disable the dns-ip-cache";
          }

          container dns-match {
            description
                "configure a match in the dns-ip-cache";
            list domain {
              key "domain-name";
              description
                  "configure a domain for the dns-ip-cache";
              leaf domain-name {
                type string {
                  length "1..32";
                }
              } //domain-name

              leaf expression {
                type string {
                }
                description
                    "expression string used to define a pattern match";
              } //expression

            } //list domain

            list server-address {
              key "server-address";
              description
                  "configure a server-address for the dns-ip-cache";
              leaf server-address {
                type string;
                description
                    "ipv4-address - a.b.c.d 
                     ipv6-address - x:x:x:x:x:x:x:x 
                     x:x:x:x:x:x:d.d.d.d 
                     x - [0..ffff]H 
                     d - [0..255]D";
              } //server-address

              leaf name {
                type string {
                  length "1..32";
                }
              } //name

            } //list server-address

          } //container dns-match

          container ip-cache {
            description
                "configure a cache in the dns-ip-cache";
            container high-wmark {
              description
                  "configure the dns-ip-cache high-watermark";
              leaf percent {
                type uint32 {
                  range "0..100";
                }
                default 90;
                description
                    "[0..100] - Default: 90";
              } //percent

            } //container high-wmark

            container low-wmark {
              description
                  "configure the dns-ip-cache low-watermark";
              leaf percent {
                type uint32 {
                  range "0..100";
                }
                default 80;
                description
                    "[0..100] - Default: 80";
              } //percent

            } //container low-wmark

            container size {
              description
                  "configure the dns-ip-cache size";
              leaf cache-size {
                type uint32 {
                  range "10..64000";
                }
                default 10;
                description
                    "[10..64000] - Default: 10";
              } //cache-size

            } //container size

            list static-address {
              key "static-ip-address";
              description
                  "configure a static-address in the cache";
              leaf static-ip-address {
                type string;
                description
                    "ipv4-address - a.b.c.d 
                     ipv6-address - x:x:x:x:x:x:x:x 
                     x:x:x:x:x:x:d.d.d.d 
                     x - [0..ffff]H 
                     d - [0..255]D";
              } //static-ip-address

            } //list static-address

          } //container ip-cache

        } //list dns-ip-cache

        list event-log {
          key "event-log-name";
          description
              "Configure an event-log";
          leaf event-log-name {
            type string {
              length "1..32";
            }
          } //event-log-name

          container buffer-type {
            description
                "Configure the type of buffer to be used in the event log";
            leaf buffer-type {
              type enumeration {
                enum linear;
                enum circular;
                enum syslog;
              }
            } //buffer-type

          } //container buffer-type

          container max-entries {
            description
                "Configure the maximum number of entries for the event log";
            leaf max-entries {
              type uint32 {
                range "1..100000";
              }
              default 500;
              description
                  "[1..100000] - Default: 500";
            } //max-entries

          } //container max-entries

          leaf shutdown {
            type boolean;
            description
                "Administratively enable/disable the event log";
          }

          container syslog {
            description
                "Configure a target syslog";
            container address {
              description
                  "Configure a syslog host address";
              leaf ip-address {
                type string;
                description
                    "ipv4-address - a.b.c.d 
                     ipv6-address - x:x:x:x:x:x:x:x 
                     x:x:x:x:x:x:d.d.d.d 
                     x - [0..ffff]H 
                     d - [0..255]D";
              } //ip-address

            } //container address

            container description {
              description
                  "Configure a syslog description";
              leaf description-string {
                type string {
                  length "1..80";
                }
              } //description-string

            } //container description

            container facility {
              description
                  "Configure the syslog facility";
              leaf syslog-facility {
                type enumeration {
                  enum kernel;
                  enum user;
                  enum mail;
                  enum systemd;
                  enum auth;
                  enum syslogd;
                  enum printer;
                  enum netnews;
                  enum uucp;
                  enum cron;
                  enum authpriv;
                  enum ftp;
                  enum ntp;
                  enum logaudit;
                  enum logalert;
                  enum cron2;
                  enum local0;
                  enum local1;
                  enum local2;
                  enum local3;
                  enum local4;
                  enum local5;
                  enum local6;
                  enum local7;
                }
                default "local7";
                description
                    "[kernel|user|mail|systemd|auth|syslogd|printer|netnews| 
                     uucp|cron|authpriv|ftp|ntp|logaudit|logalert|cron2| 
                     local0|local1|local2|local3|local4|local5|local6|local7] 
                     - Default : local7";
              } //syslog-facility

            } //container facility

            container port {
              description
                  "Configure the syslog host UDP port";
              leaf port {
                type uint16;
                default 514;
                description
                    "[0..65535] - Default : 514";
              } //port

            } //container port

            container severity {
              description
                  "Configure the syslog message severity level threshold";
              leaf syslog-severity {
                type enumeration {
                  enum emergency;
                  enum alert;
                  enum critical;
                  enum error;
                  enum warning;
                  enum notice;
                  enum info;
                  enum debug;
                }
                default "info";
                description
                    "[emergency|alert|critical|error|warning|notice|info| 
                     debug] 
                     - Default : info";
              } //syslog-severity

            } //container severity

            container vlan-id {
              description
                  "Configure a service port vlan-id";
              leaf service-port-vlan-id {
                type uint32 {
                  range "1..4094";
                }
              } //service-port-vlan-id

            } //container vlan-id

          } //container syslog

        } //list event-log

        container gtp {
          description
              "Configure the GTP (General packet radio service Tunneling Protocol) options";
          container event-log {
            description
                "Configure an event log for non-conforming GTP packets";
            leaf event-log-name {
              type string {
                length "1..32";
              }
            } //event-log-name

            leaf action {
              type enumeration {
                enum permit;
                enum deny;
                enum all;
              }
            } //action

          } //container event-log

          leaf gtpc-inspection {
            type boolean;
            description
                "Enable/disable GTP-c inspection";
          }

          container mode {
            description
                "Configure the GTP mode";
            leaf mode {
              type enumeration {
                enum filtering;
                enum untunneling;
              }
              default "filtering";
              description
                  "filtering|untunneling - Default: filtering";
            } //mode

          } //container mode

          leaf shutdown {
            type boolean;
            description
                "Administratively enable/disable GTP";
          }

          list gtp-filter {
            key "gtp-filter-name";
            description
                "Configure a GTP filter";
            leaf gtp-filter-name {
              type string {
                length "1..32";
              }
            } //gtp-filter-name

            container description {
              description
                  "Configure a description of the GTP filter";
              leaf description-string {
                type string {
                  length "1..80";
                }
              } //description-string

            } //container description

            container event-log {
              description
                  "Configure an event log for packets dropped by the GTP filter";
              leaf event-log-name {
                type string {
                  length "1..32";
                }
              } //event-log-name

              leaf action {
                type enumeration {
                  enum permit;
                  enum deny;
                  enum all;
                }
              } //action

            } //container event-log

            container gtp-in-gtp {
              description
                  "Configure the default action for GTP in GTP packets";
              leaf permit-deny {
                type enumeration {
                  enum permit;
                  enum deny;
                }
              } //permit-deny

            } //container gtp-in-gtp

            container max-payload-length {
              description
                  "Configure the maximum payload length of the GTP filter";
              leaf bytes {
                type int32 {
                  range "0..65535";
                }
              } //bytes

            } //container max-payload-length

            container gtp-tunnel-database {
              description
                  "Configure gtp-tunnel database parameters";
              container default-tunnel-endpoint-limit {
                description
                    "Configure the default limit for gtp tunnel enpoint";
                leaf default-endpoint {
                  type uint32 {
                    range "1..4294967295";
                  }
                } //default-endpoint

              } //container default-tunnel-endpoint-limit

              leaf validate-gtp-tunnels {
                type boolean;
                description
                    "Enable/disable GTP tunnel validation";
              }

              leaf validate-sequence-number {
                type boolean;
                description
                    "Enable/disable sequence number validation";
              }

              leaf validate-source-ip-addr {
                type boolean;
                description
                    "Enable/disable source IP address validation";
              }

            } //container gtp-tunnel-database

            container imsi-apn-filter {
              description
                  "Configure IMSI apn filter";
              container default-action {
                description
                    "Configure the default action for all imsi apn filters";
                leaf permit-deny {
                  type enumeration {
                    enum permit;
                    enum deny;
                  }
                } //permit-deny

              } //container default-action

              list entry {
                key "entry-id";
                description
                    "Configure an entry for a specific IMSI APN filter";
                leaf entry-id {
                  type uint32 {
                    range "1031..2030";
                  }
                } //entry-id

                container action {
                  description
                      "Configure the action for this entry";
                  leaf permit-deny {
                    type enumeration {
                      enum permit;
                      enum deny;
                    }
                  } //permit-deny

                } //container action

                container apn {
                  description
                      "Configure an APN as a GTP filter";
                  leaf apn {
                    type string {
                      length "1..100";
                    }
                    description
                        "Attribute apn for apn";
                  } //apn

                } //container apn

                container mcc-mnc-prefix {
                  description
                      "Configure the MCC and MNC prefix";
                  leaf mcc-mnc-prefix {
                    type string {
                      length "1..10";
                    }
                    description
                        "Attribute mcc-mnc-prefix for mcc-mnc-prefix";
                  } //mcc-mnc-prefix

                } //container mcc-mnc-prefix

                container src-gsn {
                  description
                      "Configure the source GSN address";
                  leaf ip-address {
                    type string;
                    description
                        "Attribute ip-address for src-gsn";
                  } //ip-address

                  leaf ip-prefix-list {
                    type string {
                      length "1..32";
                    }
                  } //ip-prefix-list

                } //container src-gsn

              } //list entry

            } //container imsi-apn-filter

            container message-type {
              description
                  "Configure actions for specific or default messages";
              container default-action {
                description
                    "Configure the default action for all GTP message types";
                leaf permit-deny {
                  type enumeration {
                    enum permit;
                    enum deny;
                  }
                  default "permit";
                  description
                      "permit|deny - Default: permit";
                } //permit-deny

              } //container default-action

              list entry {
                key "entry-id";
                description
                    "Configure an entry for a specific GTP message type value";
                leaf entry-id {
                  type uint32 {
                    range "1..255";
                  }
                } //entry-id

                leaf value {
                  type string {
                  }
                  description
                      "[1..255]D | [256 chars max]";
                } //value

                leaf action {
                  type enumeration {
                    enum permit;
                    enum deny;
                  }
                } //action

              } //list entry

            } //container message-type

            container message-type-gtpv2 {
              description
                  "Configure actions for specific or default messages for GTP V2";
              container default-action {
                description
                    "Configure the default action for all GTP V2 message types";
                leaf permit-deny {
                  type enumeration {
                    enum permit;
                    enum deny;
                  }
                } //permit-deny

              } //container default-action

              list entry {
                key "entry-id";
                description
                    "Configure an entry for a specific GTP V2 message type value";
                leaf entry-id {
                  type uint32 {
                    range "516..770";
                  }
                } //entry-id

                leaf value {
                  type string {
                  }
                  description
                      "[1..255]D | [256 chars max]";
                } //value

                leaf action {
                  type enumeration {
                    enum permit;
                    enum deny;
                  }
                } //action

              } //list entry

            } //container message-type-gtpv2

          } //list gtp-filter

        } //container gtp

        list http-enrich {
          key "http-enrich-name";
          description
              "Configure a HTTP header enrichment template";
          leaf http-enrich-name {
            type string {
              length "1..32";
            }
          } //http-enrich-name

          container description {
            description
                "Configure a http header enrichment template description";
            leaf description-string {
              type string {
                length "1..80";
              }
            } //description-string

          } //container description

          leaf shutdown {
            type boolean;
            description
                "Administratively enable/disable the http header enrichment template";
          }

          list field {
            key "field-name";
            description
                "Configure a http header enrichment template field";
            leaf field-name {
              type string {
                length "1..32";
              }
            } //field-name

            leaf anti-spoof {
              type boolean;
              description
                  "Configure HTTP header enrichment anti-spoofing";
            }

            leaf calling-line-id {
              type boolean;
              description
                  "Configure HTTP header for 'x-up-calling-line-id' anti-spoofing";
            }

            container encode {
              description
                  "Configure how the HTTP header enrichment field will be encoded";
              leaf type {
                type enumeration {
                  enum md5;
                  enum rc4;
                  enum certificate;
                  enum rc4md5-base64;
                }
              } //type

              leaf key {
                type string {
                  length "1..500";
                }
                description
                    "key - [64 chars max] 
                     hash-key - hashed key 
                     hash2-key - hashed key 
                     custom-key - hashed key";
              } //key

              leaf hash-hash2-custom {
                type enumeration {
                  enum hash;
                  enum hash2;
                  enum custom;
                }
                description
                    "keywords - hashing scheme used in the hashed key";
              } //hash-hash2-custom

              leaf cert-profile {
                type string {
                  length "1..32";
                }
              } //cert-profile

            } //container encode

            container name {
              description
                  "Configure a http header enrichment template field header name";
              leaf header-name {
                type string {
                  length "1..32";
                }
              } //header-name

            } //container name

            container static-string {
              description
                  "Configure an HTTP header enrichment template field static string";
              leaf string {
                type string {
                  length "1..16";
                }
              } //string

            } //container static-string

          } //list field

          container rat-enrichment {
            description
                "Configure RAT enrichment values";
            list rat-type {
              key "rat-type";
              description
                  "Configure mapping of RAT type value";
              leaf rat-type {
                type enumeration {
                  enum utran;
                  enum geran;
                  enum wlan;
                  enum gan;
                  enum hspa-evol;
                  enum eutran;
                  enum virtual;
                  enum eutran-nb;
                  enum ehrpd;
                  enum hrpd;
                  enum cdma-1x;
                  enum umb;
                  enum wifi;
                  enum nr;
                }
              } //rat-type

              leaf rat-value {
                type string {
                  length "1..31";
                }
              } //rat-value

            } //list rat-type

          } //container rat-enrichment

          container tls-extension {
            description
                "Configure the tls-extension field name";
            container extension-id {
              description
                  "Configure an extension ID to be used for the customized extension";
              leaf extension-id {
                type uint32 {
                  range "1..65535";
                }
                default 17516;
                description
                    "[1..65535] - Default: 17516";
              } //extension-id

            } //container extension-id

            list subtype {
              key "tls-extension-subtype";
              description
                  "Configure a tls extension subtype";
              leaf tls-extension-subtype {
                type string {
                  length "1..32";
                }
              } //tls-extension-subtype

              container encode {
                description
                    "Configure how the HTTP header enrichment TLS extension subtype will be encoded";
                leaf type {
                  type enumeration {
                    enum md5;
                    enum rc4;
                  }
                } //type

                leaf key {
                  type string {
                    length "1..500";
                  }
                  description
                      "key - [64 chars max] 
                       hash-key - hashed key 
                       hash2-key - hashed key 
                       custom-key - hashed key";
                } //key

                leaf hash-hash2-custom {
                  type enumeration {
                    enum hash;
                    enum hash2;
                    enum custom;
                  }
                  description
                      "keywords - hashing scheme used in the hashed key";
                } //hash-hash2-custom

              } //container encode

            } //list subtype

          } //container tls-extension

        } //list http-enrich

        list http-error-redirect {
          key "redirect-name";
          description
              "Configure a HTTP error redirect";
          leaf redirect-name {
            type string {
              length "1..32";
            }
          } //redirect-name

          container description {
            description
                "Configure a http error redirect description";
            leaf description-string {
              type string {
                length "1..80";
              }
            } //description-string

          } //container description

          list error-code {
            key "error-code";
            description
                "Configure a http error redirect error code";
            leaf error-code {
              type uint32;
            } //error-code

            leaf custom-msg-size {
              type uint32;
            } //custom-msg-size

          } //list error-code

          container http-host {
            description
                "Configure a http error redirect host";
            leaf http-host {
              type string {
                length "1..255";
              }
            } //http-host

          } //container http-host

          container participant-id {
            description
                "Configure a http error redirect participant id";
            leaf participant-id {
              type string {
                length "1..32";
              }
            } //participant-id

          } //container participant-id

          leaf shutdown {
            type boolean;
            description
                "Administratively enable/disable the http error redirect";
          }

          container template {
            description
                "Configure a http error redirect template";
            leaf template-id {
              type string;
              description
                  "Attribute template-id for template";
            } //template-id

          } //container template

        } //list http-error-redirect

        list http-notification {
          key "http-notification";
          description
              "Configure the HTTP notification template";
          leaf http-notification {
            type string {
              length "1..32";
            }
          } //http-notification

          container description {
            description
                "Configure the description";
            leaf description-string {
              type string {
                length "1..80";
              }
            } //description-string

          } //container description

          container interval {
            description
                "Configure the interval";
            leaf one-time {
              type boolean;
            } //one-time

            leaf minimum-interval {
              type uint32 {
                range "1..1440";
              }
              description
                  "[1..1440] - minutes";
            } //minimum-interval

          } //container interval

          container script-url {
            description
                "Configure the script URL";
            leaf script-url-name {
              type string {
                length "1..255";
              }
            } //script-url-name

          } //container script-url

          leaf shutdown {
            type boolean;
            description
                "Administratively enable/disable";
          }

          container template {
            description
                "Configure the HTTP notification template";
            leaf template-id {
              type string;
              description
                  "Attribute template-id for template";
            } //template-id

          } //container template

        } //list http-notification

        list http-redirect {
          key "redirect-name";
          description
              "Configure a HTTP redirect";
          leaf redirect-name {
            type string {
              length "1..32";
            }
          } //redirect-name

          container description {
            description
                "Configure a HTTP redirect description";
            leaf description-string {
              type string {
                length "1..80";
              }
            } //description-string

          } //container description

          leaf redirect-https {
            type boolean;
            description
                "Configure HTTPS redirect";
          }

          container redirect-url {
            description
                "Configure a HTTP redirect url";
            leaf redirect-url {
              type string {
                length "1..255";
              }
              description
                  "Attribute redirect-url for redirect-url";
            } //redirect-url

          } //container redirect-url

          leaf shutdown {
            type boolean;
            description
                "Administratively enable/disable the HTTP redirect";
          }

          leaf tcp-client-reset {
            type boolean;
            description
                "Configure TCP client reset";
          }

          container template {
            description
                "Configure a HTTP redirect template";
            leaf template-id {
              type string;
              description
                  "Attribute template-id for template";
            } //template-id

          } //container template

          container captive-redirect {
            description
                "Configure a captive HTTP redirect";
            leaf redirect-https {
              type boolean;
              status "obsolete";
              description
                  "Configure captive HTTPS redirect";
            }

            container vlan-id {
              description
                  "Configure the service port vlan-id";
              leaf service-port-vlan-id {
                type uint32 {
                  range "1..4094";
                }
              } //service-port-vlan-id

            } //container vlan-id

          } //container captive-redirect

        } //list http-redirect

        list ip-prefix-list {
          key "ip-prefix-list-name";
          description
              "Configure an IP prefix list";
          leaf ip-prefix-list-name {
            type string {
              length "1..32";
            }
          } //ip-prefix-list-name

          container description {
            description
                "Configure a description for the list";
            leaf description-string {
              type string {
                length "1..80";
              }
            } //description-string

          } //container description

          list prefix {
            key "ip-prefix-ip-prefix-length";
            description
                "Configure an IP Prefix within the list";
            leaf ip-prefix-ip-prefix-length {
              type string;
              description
                  "Attribute ip-prefix/ip-prefix-length for prefix";
            } //ip-prefix-ip-prefix-length

            leaf name {
              type string {
                length "1..32";
              }
            } //name

          } //list prefix

        } //list ip-prefix-list

        list mp-tcp-proxy {
          key "mp-tcp-proxy-name";
          description
              "Configure a Multi-Path TCP Proxy";
          leaf mp-tcp-proxy-name {
            type string {
              length "1..32";
            }
          } //mp-tcp-proxy-name

          leaf bonding-assist {
            type boolean;
            description
                "Enable or disable bonding assist";
          }

          container congestion-control {
            description
                "Configure the congestion control algorithm for MP TCP";
            leaf congestion-algorithm {
              type enumeration {
                enum olia;
                enum olia-plus;
                enum bbr;
              }
            } //congestion-algorithm

          } //container congestion-control

          container default-scheduler-policy {
            description
                "Configure the default scheduler policy";
            leaf scheduler-policy {
              type enumeration {
                enum min-rtt-prefer;
                enum min-cost-handover;
                enum max-cost-forbid;
                enum min-cost-prefer;
              }
            } //scheduler-policy

          } //container default-scheduler-policy

          container description {
            description
                "Configure the description of the proxy";
            leaf description-string {
              type string {
                length "1..80";
              }
            } //description-string

          } //container description

          leaf force-dss-checksums {
            type boolean;
            description
                "Enable or disable forcing DSS checksums";
          }

          container ip-address-profile {
            description
                "Configure the IP address profile";
            leaf profile-name {
              type string {
                length "1..32";
              }
            } //profile-name

          } //container ip-address-profile

          leaf subflow-failure-indication {
            type boolean;
            description
                "Enable or disable subflow failure indication";
          }

          container path {
            description
                "Configure a multipath TCP proxy path";
            container fixed {
              description
                  "Configure fixed path attributes";
              leaf admin-cost {
                type uint32 {
                  range "1..10";
                }
                description
                    "[1..10] - default 5";
              } //admin-cost

            } //container fixed

            container mobile {
              description
                  "Configure mobile path attributes";
              leaf admin-cost {
                type uint32 {
                  range "1..10";
                }
                description
                    "[1..10] - default 5";
              } //admin-cost

            } //container mobile

          } //container path

        } //list mp-tcp-proxy

        list policer {
          key "policer-name";
          description
              "Configure policer";
          leaf policer-name {
            type string {
              length "1..32";
            }
          } //policer-name

          leaf type {
            type enumeration {
              enum single-bucket-bandwidth;
              enum dual-bucket-bandwidth;
              enum flow-rate-limit;
              enum flow-count-limit;
            }
            description
                "single-bucket-bandwidth | dual-bucket-bandwidth | flow-rate-limit | 
                 flow-count-limit";
          } //type

          leaf granularity {
            type enumeration {
              enum system;
              enum subscriber;
              enum access-network-location;
            }
          } //granularity

          container action {
            description
                "Configure actions to be taken for conformant and non-conformant cases";
            leaf priority-mark-permit-deny {
              type enumeration {
                enum priority-mark;
                enum permit-deny;
              }
              description
                  "keyword - specifies action to be taken for conformant and non-conformant cases";
            } //priority-mark-permit-deny

          } //container action

          container adaptation-rule {
            description
                "Configure the PIR and CIR adaptation rules";
            leaf pir {
              type enumeration {
                enum max;
                enum min;
                enum closest;
              }
            } //pir

            leaf cir {
              type enumeration {
                enum max;
                enum min;
                enum closest;
              }
              description
                  "adaptation-rule";
            } //cir

          } //container adaptation-rule

          container cbs {
            description
                "Configure CBS for the policer";
            leaf committed-burst-size {
              type int32 {
                range "0..131071";
              }
              description
                  "[0..131071 KB]";
            } //committed-burst-size

          } //container cbs

          container description {
            description
                "Configure policer description";
            leaf description-string {
              type string {
                length "1..80";
              }
            } //description-string

          } //container description

          container flow-count {
            description
                "Configure the flow-count for flow-count-limit policer";
            leaf flow-count-string {
              type string;
              description
                  "[0..100000000|max flows]";
            } //flow-count-string

          } //container flow-count

          leaf gtp-traffic {
            type boolean;
            description
                "Enable/disable flow-count to only limit GTP flows";
          }

          container mbs {
            description
                "Configure MBS for the policer";
            leaf maximum-burst-size {
              type int32 {
                range "0..131071";
              }
              description
                  "[0..131071 KB or flows]";
            } //maximum-burst-size

          } //container mbs

          container rate {
            description
                "Configure the rates for the policer";
            leaf pir-rate {
              type string;
              description
                  "[1..100000000|max] Kbps or flows/sec";
            } //pir-rate

            leaf cir {
              type string;
              description
                  "[0..100000000|max] Kbps";
            } //cir

          } //container rate

          container rate-percentage {
            description
                "Configure the rate-percentage for the policer";
            leaf rate-percentage-id {
              type uint32 {
                range "0..200";
              }
            } //rate-percentage-id

          } //container rate-percentage

          container anl-congestion-override {
            status "obsolete";
            description
                "Configure ANL congestion override for the policer";
            container cbs {
              description
                  "Configure congested ANL CBS for the policer";
              leaf congested-anl-cbs {
                type int32 {
                  range "0..131071";
                }
              } //congested-anl-cbs

            } //container cbs

            container cir {
              description
                  "Configure congested ANL CIR for the policer";
              leaf congested-anl-cir {
                type int32 {
                  range "0..100000000";
                }
              } //congested-anl-cir

            } //container cir

            container mbs {
              description
                  "Configure congested ANL MBS for the policer";
              leaf congested-anl-mbs {
                type int32 {
                  range "0..131071";
                }
              } //congested-anl-mbs

            } //container mbs

            container pir {
              description
                  "Configure congested ANL PIR for the policer";
              leaf congested-anl-pir {
                type int32 {
                  range "0..100000000";
                }
              } //congested-anl-pir

            } //container pir

          } //container anl-congestion-override

          container congestion-override {
            description
                "Configure congestion override for the policer";
            container cbs {
              description
                  "Configure congested CBS for the policer";
              leaf congested-cbs {
                type int32 {
                  range "0..131071";
                }
                description
                    "[0..131071] KB";
              } //congested-cbs

            } //container cbs

            container cir {
              description
                  "Configure congested CIR for the policer";
              leaf congested-cir {
                type string;
                description
                    "[0..100000000|max] Kbps";
              } //congested-cir

            } //container cir

            container mbs {
              description
                  "Configure congested MBS for the policer";
              leaf congested-mbs {
                type int32 {
                  range "0..131071";
                }
                description
                    "[0..131071] KB";
              } //congested-mbs

            } //container mbs

            container pir {
              description
                  "Configure congested PIR for the policer";
              leaf congested-pir {
                type string;
                description
                    "[1..100000000|max] Kbps";
              } //congested-pir

            } //container pir

          } //container congestion-override

          list tod-override {
            key "tod-override-id";
            description
                "Configure policer time of day overrides";
            leaf tod-override-id {
              type uint16 {
                range "1..255";
              }
            } //tod-override-id

            container cbs {
              description
                  "Configure the Committed Burst Size";
              leaf committed-burst-size {
                type int32 {
                  range "0..131071";
                }
                description
                    "[0..131071] KB";
              } //committed-burst-size

            } //container cbs

            container description {
              description
                  "Configure the description";
              leaf description-string {
                type string {
                  length "1..80";
                }
              } //description-string

            } //container description

            container flow-count {
              description
                  "Configure the flow-count";
              leaf flow-count {
                type string;
                description
                    "[0..100000000|max] flows";
              } //flow-count

            } //container flow-count

            container mbs {
              description
                  "Configure the Maximum Burst Size";
              leaf maximum-burst-size {
                type int32 {
                  range "0..131071";
                }
                description
                    "[0..131071] KB or flows";
              } //maximum-burst-size

            } //container mbs

            container rate {
              description
                  "Configure the rates";
              leaf pir-rate {
                type string;
                description
                    "[1..100000000|max] kbps or flows/sec";
              } //pir-rate

              leaf cir {
                type string;
                description
                    "[0..100000000|max] kbps";
              } //cir

            } //container rate

            leaf shutdown {
              type boolean;
              description
                  "Administratively enable/disable a tod-override";
            }

            container time-range {
              description
                  "Configure the time-range to apply the override";
              leaf daily {
                type boolean;
                description
                    "keyword - Schedule the override as a daily occurrence";
              } //daily

              leaf weekly {
                type boolean;
                description
                    "keyword - Schedule the override as a weekly occurrence";
              } //weekly

              leaf start {
                type string {
                  length "1..32";
                }
                description
                    "daily : <hh>:<mm> 
                     weekly : <day>,<hh>:<mm> 
                         <hh> : 0..23 
                         <mm> : 0|15|30|45";
              } //start

              leaf end {
                type string {
                  length "1..32";
                }
                description
                    "daily : <hh>:<mm> 
                     weekly : <day>,<hh>:<mm> 
                         <hh> : 0..24 
                         <mm> : 0|15|30|45";
              } //end

              leaf-list on {
                type enumeration {
                  enum sunday;
                  enum monday;
                  enum tuesday;
                  enum wednesday;
                  enum thursday;
                  enum friday;
                  enum saturday;
                }
                max-elements 7;
              } //on

            } //container time-range

          } //list tod-override

        } //list policer

        container policy {
          description
              "Configure policy";
          leaf abort {
            type boolean;
            description
                "Discard the changes that have been made to application-assurance policies 
                 during a session";
          }

          leaf begin {
            type boolean;
            description
                "Switch to edit mode for application-assurance policies - use commit to save or 
                 abort to discard the changes made in a session";
          }

          leaf commit {
            type boolean;
            description
                "Save the changes made to application-assurance policies during a session";
          }

          container default-charging-group {
            description
                "Configure default charging-group";
            leaf charging-group-name {
              type string {
                length "1..32";
              }
            } //charging-group-name

          } //container default-charging-group

          container default-tethered-charging-group {
            description
                "Configure default thethered-charging-group";
            leaf charging-group-name {
              type string {
                length "1..32";
              }
            } //charging-group-name

          } //container default-tethered-charging-group

          container app-filter {
            description
                "Configure mapping of protocols on to applications";
            list entry {
              key "entry-id";
              description
                  "Configure an app-filter entry";
              leaf entry-id {
                type uint32 {
                  range "1..65535";
                }
              } //entry-id

              container application {
                description
                    "Configure the application that is determined as a result of matching all other 
                     entry parameters";
                leaf application-name {
                  type string {
                    length "1..32";
                  }
                } //application-name

              } //container application

              container description {
                description
                    "Configure an application filter entry description";
                leaf description-string {
                  type string {
                    length "1..80";
                  }
                } //description-string

              } //container description

              list expression {
                key "expr-index";
                description
                    "Configure expression strings to match against when determining an application";
                leaf expr-index {
                  type uint32 {
                    range "1..4";
                  }
                } //expr-index

                leaf expr-type {
                  type enumeration {
                    enum http-host;
                    enum http-uri;
                    enum http-referer;
                    enum http-user-agent;
                    enum sip-ua;
                    enum sip-uri;
                    enum sip-mt;
                    enum citrix-app;
                    enum h323-product-id;
                    enum tls-cert-subj-org-name;
                    enum tls-cert-subj-common-name;
                    enum rtsp-host;
                    enum rtsp-uri;
                    enum rtsp-ua;
                    enum rtmp-page-host;
                    enum rtmp-page-uri;
                    enum rtmp-swf-host;
                    enum rtmp-swf-uri;
                    enum rtmp-tc-host;
                    enum rtmp-tc-uri;
                  }
                } //expr-type

                leaf eq---neq {
                  type enumeration {
                    enum eq;
                    enum neq;
                  }
                  default "eq";
                  description
                      "keyword - specifies comparison operator";
                } //eq---neq

                leaf expr-string {
                  type string {
                  }
                  description
                      "expression string used to define a pattern match";
                } //expr-string

              } //list expression

              container flow-setup-direction {
                description
                    "Configure the flow setup direction(s) to match against when determining an 
                     application";
                leaf flow-setup-direction-id {
                  type enumeration {
                    enum subscriber-to-network;
                    enum network-to-subscriber;
                    enum both;
                  }
                } //flow-setup-direction-id

              } //container flow-setup-direction

              leaf http-match-all-requests {
                type boolean;
                description
                    "Enable/disable constant monitoring of HTTP request strings";
              }

              container http-port {
                description
                    "Configure the http-port to match against when determining an application";
                leaf eq---neq {
                  type enumeration {
                    enum eq;
                    enum neq;
                  }
                  default "eq";
                  description
                      "keyword - comparison operator";
                } //eq---neq

                leaf port-num {
                  type string;
                  description
                      "Attribute port-num for http-port";
                } //port-num

                leaf port-list {
                  type string {
                    length "1..32";
                  }
                } //port-list

              } //container http-port

              container ip-protocol-num {
                description
                    "Configure the ip protocol number to match against when determining an 
                     application";
                leaf eq-neq {
                  type enumeration {
                    enum eq;
                    enum neq;
                  }
                  default "eq";
                  description
                      "keyword - comparison operator";
                } //eq-neq

                leaf protocol-id {
                  type string;
                  description
                      "Attribute protocol-id for ip-protocol-num";
                } //protocol-id

              } //container ip-protocol-num

              container network-address {
                description
                    "Configure the network IP address or IP prefix list to match against when 
                     determining an application";
                leaf eq---neq {
                  type enumeration {
                    enum eq;
                    enum neq;
                  }
                  default "eq";
                  description
                      "keyword - comparison operator";
                } //eq---neq

                leaf ip-address {
                  type string;
                  description
                      "Attribute ip-address for network-address";
                } //ip-address

                leaf ip-prefix-list {
                  type string {
                    length "1..32";
                  }
                } //ip-prefix-list

              } //container network-address

              container protocol {
                description
                    "Configure the protocol signature to match against to determine the application";
                leaf eq-neq {
                  type enumeration {
                    enum eq;
                    enum neq;
                  }
                  default "eq";
                  description
                      "keyword - specifies comparison operator";
                } //eq-neq

                leaf protocol-name {
                  type string {
                    length "1..32";
                  }
                } //protocol-name

              } //container protocol

              container server-address {
                description
                    "Configure the server IP address or IP prefix list to match against when 
                     determining an application";
                leaf eq-neq {
                  type enumeration {
                    enum eq;
                    enum neq;
                  }
                  default "eq";
                  description
                      "keyword - comparison operator";
                } //eq-neq

                leaf ip-address {
                  type string;
                  description
                      "Attribute ip-address for server-address";
                } //ip-address

                leaf ip-prefix-list {
                  type string {
                    length "1..32";
                  }
                } //ip-prefix-list

                leaf dns-ip-cache {
                  type string {
                    length "1..32";
                  }
                } //dns-ip-cache

              } //container server-address

              container server-port {
                description
                    "Configure the server TCP or UDP port to match against when determining an 
                     application";
                leaf eq---neq---gt---lt {
                  type enumeration {
                    enum eq;
                    enum neq;
                    enum gt;
                    enum lt;
                  }
                  default "eq";
                  description
                      "keyword - comparison operator";
                } //eq---neq---gt---lt

                leaf range {
                  type boolean;
                } //range

                leaf port-num {
                  type string;
                  description
                      "Attribute port-num for server-port";
                } //port-num

                leaf start-port-num {
                  type string;
                  description
                      "Attribute start-port-num for server-port";
                } //start-port-num

                leaf end-port-num {
                  type string;
                  description
                      "Attribute end-port-num for server-port";
                } //end-port-num

                leaf first-packet-policy {
                  type enumeration {
                    enum first-packet-trusted;
                    enum first-packet-validate;
                  }
                  description
                      "keywords : 
                       first-packet-trusted - apply application on first packet 
                       first-packet-validate - apply application on first packet then verify";
                } //first-packet-policy

                leaf port-list {
                  type string {
                    length "1..32";
                  }
                } //port-list

                leaf first-packet-policy-1 {
                  type enumeration {
                    enum first-packet-trusted;
                    enum first-packet-validate;
                  }
                  description
                      "keywords : 
                       first-packet-trusted - apply application on first packet 
                       first-packet-validate - apply application on first packet then verify";
                } //first-packet-policy-1

              } //container server-port

              leaf shutdown {
                type boolean;
                description
                    "Administratively shut down an application filter entry";
              }

            } //list entry

          } //container app-filter

          list app-group {
            key "application-group-name";
            description
                "Configure application group";
            leaf application-group-name {
              type string {
                length "1..32";
              }
            } //application-group-name

            container charging-group {
              description
                  "Configure this app-group's charging-group";
              leaf charging-group-name {
                type string {
                  length "1..32";
                }
              } //charging-group-name

            } //container charging-group

            container description {
              description
                  "Configure application group description";
              leaf description {
                type string {
                  length "1..80";
                }
              } //description

            } //container description

            container export-id {
              description
                  "Identifier used to represent this app-group in the exported accounting records";
              leaf export-id {
                type uint32 {
                  range "1..255";
                }
              } //export-id

            } //container export-id

          } //list app-group

          list app-profile {
            key "app-profile-name";
            description
                "Configure application profile parameters";
            leaf app-profile-name {
              type string {
                length "1..32";
              }
            } //app-profile-name

            leaf aa-sub-suppressible {
              type boolean;
              description
                  "Configure application profile flag to allow suppressing Application-Assurance 
                   for ESM subscribers";
            }

            container capacity-cost {
              description
                  "Configure an application profile capacity cost";
              leaf cost {
                type uint32 {
                  range "1..65535";
                }
              } //cost

            } //container capacity-cost

            list characteristic {
              key "characteristic-name";
              description
                  "Configure an application profile characteristic and value";
              leaf characteristic-name {
                type string {
                  length "1..32";
                }
              } //characteristic-name

              leaf value {
                type string {
                  length "1..32";
                }
              } //value

            } //list characteristic

            container description {
              description
                  "Configure application profile description";
              leaf description-string {
                type string {
                  length "1..80";
                }
                description
                    "[80 chars max]";
              } //description-string

            } //container description

            leaf divert {
              type boolean;
              description
                  "Configure application profile flag to enable subscriber traffic to be sent to 
                   an ISA-AA";
            }

          } //list app-profile

          container app-qos-policy {
            description
                "Configure application QoS policy actions";
            list entry {
              key "entry-id";
              description
                  "Configure an application qos policy entry";
              leaf entry-id {
                type uint32 {
                  range "1..65535";
                }
              } //entry-id

              container description {
                description
                    "Configure an application qos policy entry description";
                leaf description-string {
                  type string {
                    length "1..80";
                  }
                } //description-string

              } //container description

              leaf shutdown {
                type boolean;
                description
                    "Administratively shut down an application qos filter entry";
              }

              container action {
                description
                    "Configure actions for application qos policies";
                leaf abandon-tcp-optimization {
                  type boolean;
                  description
                      "Enable/disable abandon TCP optimization";
                }

                container bandwidth-policer {
                  description
                      "Configure a bandwidth policer action for flows matching this entry";
                  leaf policer-name {
                    type string {
                      length "1..32";
                    }
                  } //policer-name

                } //container bandwidth-policer

                leaf checkpoint {
                  type boolean;
                  description
                      "Configure a checkpoint notification for flows matching this entry";
                }

                container dns-ip-cache {
                  description
                      "Configure a DNS IP Cache action for flows matching this entry";
                  leaf dns-ip-cache-name {
                    type string {
                      length "1..32";
                    }
                  } //dns-ip-cache-name

                } //container dns-ip-cache

                leaf drop {
                  type boolean;
                  description
                      "Configure a drop action for flows matching this entry";
                }

                container error-drop {
                  description
                      "Configure a drop action for error flows (bad IP checksums, tcp/udp port 0, 
                       etc.)";
                  leaf event-log {
                    type string {
                      length "1..32";
                    }
                  } //event-log

                } //container error-drop

                container flow-count-limit {
                  description
                      "Configure a flow count limiter action for flows matching this entry";
                  leaf policer-name {
                    type string {
                      length "1..32";
                    }
                  } //policer-name

                  leaf event-log {
                    type string {
                      length "1..32";
                    }
                  } //event-log

                } //container flow-count-limit

                container flow-rate-limit {
                  description
                      "Configure a flow rate policer action for flows matching this entry";
                  leaf policer-name {
                    type string {
                      length "1..32";
                    }
                  } //policer-name

                  leaf event-log {
                    type string {
                      length "1..32";
                    }
                  } //event-log

                } //container flow-rate-limit

                container fragment-drop {
                  description
                      "Configure a drop action for IP fragments (all or out-of-order on the first 
                       packet)";
                  leaf all---out-of-order {
                    type enumeration {
                      enum all;
                      enum out-of-order;
                    }
                  } //all---out-of-order

                  leaf event-log {
                    type string {
                      length "1..32";
                    }
                  } //event-log

                } //container fragment-drop

                container gtp-filter {
                  description
                      "Configure the GTP filter action for flows matching this entry";
                  leaf gtp-filter-name {
                    type string {
                      length "1..32";
                    }
                  } //gtp-filter-name

                } //container gtp-filter

                container http-enrich {
                  description
                      "Configure a http enrichment action for flows matching this entry";
                  leaf http-enrich-name {
                    type string {
                      length "1..32";
                    }
                  } //http-enrich-name

                } //container http-enrich

                container http-error-redirect {
                  description
                      "Configure a http-error redirect action for flows matching this entry";
                  leaf redirect-name {
                    type string {
                      length "1..32";
                    }
                  } //redirect-name

                } //container http-error-redirect

                container http-notification {
                  description
                      "Configure an http notification action for flows matching this entry";
                  leaf http-notification {
                    type string {
                      length "1..32";
                    }
                  } //http-notification

                } //container http-notification

                container http-redirect {
                  description
                      "Configure a http redirect action for flows of a specific type matching this 
                       entry";
                  leaf redirect-name {
                    type string {
                      length "1..32";
                    }
                  } //redirect-name

                  leaf flow-type {
                    type enumeration {
                      enum admitted-flows;
                      enum dropped-flows;
                    }
                  } //flow-type

                } //container http-redirect

                container mirror-source {
                  description
                      "Configure a mirror source action for flows matching this entry";
                  leaf mirror-source-id {
                    type enumeration {
                      enum all-inclusive;
                    }
                  } //mirror-source-id

                  leaf mirror-service-id {
                    type string;
                    description
                        "Attribute mirror-service-id for mirror-source";
                  } //mirror-service-id

                } //container mirror-source

                container mp-tcp-proxy {
                  description
                      "Configure the multi-path TCP proxy action";
                  leaf mp-tcp-proxy-name {
                    type string {
                      length "1..32";
                    }
                  } //mp-tcp-proxy-name

                } //container mp-tcp-proxy

                container mp-tcp-scheduler-policy-override {
                  description
                      "Configure the multi-path TCP scheduler policy override";
                  leaf scheduler-policy {
                    type enumeration {
                      enum min-rtt-prefer;
                      enum min-cost-handover;
                      enum max-cost-forbid;
                      enum min-cost-prefer;
                    }
                  } //scheduler-policy

                } //container mp-tcp-scheduler-policy-override

                leaf offload {
                  type boolean;
                  description
                      "Configure an offload notification for flows matching this entry";
                }

                container overload-drop {
                  description
                      "Configure a drop action for cases where flow records are not created 
                       (overload)";
                  leaf event-log {
                    type string {
                      length "1..32";
                    }
                  } //event-log

                } //container overload-drop

                container sctp-filter {
                  description
                      "Configure the SCTP filter action for flows matching this entry";
                  leaf sctp-filter-name {
                    type string {
                      length "1..32";
                    }
                  } //sctp-filter-name

                } //container sctp-filter

                container session-filter {
                  description
                      "Configure the session filter to be applied";
                  leaf session-filter-name {
                    type string {
                      length "1..32";
                    }
                  } //session-filter-name

                } //container session-filter

                container tcp-mss-adjust {
                  description
                      "Configure an intended Maximum Segment Size (MSS) for flows matching this entry";
                  leaf segment-size {
                    type uint32 {
                      range "160..10240";
                    }
                  } //segment-size

                } //container tcp-mss-adjust

                container tcp-validate {
                  description
                      "Configure a TCP validate action for flows of a specific type matching this 
                       entry";
                  leaf tcp-validate-name {
                    type string {
                      length "1..32";
                    }
                  } //tcp-validate-name

                } //container tcp-validate

                container tls-enrich {
                  description
                      "Configure a tls enrichment action for flows matching this entry";
                  leaf tls-enrich-name {
                    type string {
                      length "1..32";
                    }
                  } //tls-enrich-name

                } //container tls-enrich

                container url-filter {
                  description
                      "Configure a URL filter action for flows of a specific type matching this entry";
                  leaf url-filter-name {
                    type string {
                      length "1..32";
                    }
                  } //url-filter-name

                  leaf characteristic {
                    type string {
                      length "1..32";
                    }
                    description
                        "application service option characteristic name used to determine custom 
                         X-Header value";
                  } //characteristic

                } //container url-filter

                container remark {
                  description
                      "Configure remark actions for flows matching this entry";
                  container dscp {
                    description
                        "Configure dscp remark action for flows matching this entry";
                    leaf in-profile {
                      type string {
                        length "1..32";
                      }
                      description
                          "Attribute dscp-name for dscp";
                    } //in-profile

                    leaf out-profile {
                      type string {
                        length "1..32";
                      }
                    } //out-profile

                  } //container dscp

                  container fc {
                    description
                        "Configure fc remark action for flows matching this entry";
                    leaf fc-name {
                      type enumeration {
                        enum be;
                        enum l2;
                        enum af;
                        enum l1;
                        enum h2;
                        enum ef;
                        enum h1;
                        enum nc;
                      }
                      default "be";
                    } //fc-name

                  } //container fc

                  container priority {
                    description
                        "Configure priority remark action for flows matching this entry";
                    leaf priority {
                      type enumeration {
                        enum high;
                        enum low;
                      }
                      description
                          "[high|low]";
                    } //priority

                  } //container priority

                } //container remark

              } //container action

              container match {
                description
                    "Configure match conditions for application qos policies";
                container aa-sub {
                  description
                      "Configure an application assurance subscriber to match against to resolve to 
                       actions";
                  leaf esm {
                    type enumeration {
                      enum eq;
                      enum neq;
                    }
                  } //esm

                  leaf sap {
                    type enumeration {
                      enum eq;
                      enum neq;
                    }
                  } //sap

                  leaf sap-id {
                    type string;
                    description
                        "Attribute sap-id for aa-sub";
                  } //sap-id

                  leaf sub-ident-string {
                    type string {
                      length "1..32";
                    }
                  } //sub-ident-string

                  leaf spoke-sdp {
                    type enumeration {
                      enum eq;
                      enum neq;
                    }
                  } //spoke-sdp

                  leaf sdp-id-vc-id {
                    type string;
                    description
                        "sdp-id - [1..32767] 
                         vc-id - [1..4294967295]";
                  } //sdp-id-vc-id

                  leaf transit {
                    type enumeration {
                      enum eq;
                      enum neq;
                    }
                  } //transit

                  leaf transit-aasub-name {
                    type string {
                      length "1..32";
                    }
                  } //transit-aasub-name

                  leaf esm-mac {
                    type enumeration {
                      enum eq;
                      enum neq;
                    }
                  } //esm-mac

                  leaf esm-mac-name {
                    type string {
                      length "1..32";
                    }
                  } //esm-mac-name

                } //container aa-sub

                container aa-sub-tethering-state {
                  description
                      "Configure an application assurance subscriber tethering state to match against 
                       to resolve to actions";
                  leaf tethering-state {
                    type enumeration {
                      enum detected;
                      enum not-detected;
                    }
                  } //tethering-state

                } //container aa-sub-tethering-state

                container app-group {
                  description
                      "Configure an application group to match against to resolve to actions";
                  leaf eq-neq {
                    type enumeration {
                      enum eq;
                      enum neq;
                    }
                    default "eq";
                    description
                        "keywords - comparison operator to apply to parameter(s)";
                  } //eq-neq

                  leaf application-group-name {
                    type string {
                      length "1..32";
                    }
                  } //application-group-name

                } //container app-group

                container application {
                  description
                      "Configure an application to match against to resolve to actions";
                  leaf eq-neq {
                    type enumeration {
                      enum eq;
                      enum neq;
                    }
                    default "eq";
                    description
                        "keywords - comparison operator to apply to parameter(s)";
                  } //eq-neq

                  leaf application-name {
                    type string {
                      length "1..32";
                    }
                  } //application-name

                } //container application

                list characteristic {
                  key "characteristic-name";
                  description
                      "Configure characteristics from the app-service-options to match against to 
                       resolve to actions";
                  leaf characteristic-name {
                    type string {
                      length "1..32";
                    }
                  } //characteristic-name

                  leaf eq {
                    type enumeration {
                      enum eq;
                    }
                    default "eq";
                    description
                        "keyword - comparison operator";
                  } //eq

                  leaf value-name {
                    type string {
                      length "1..32";
                    }
                  } //value-name

                } //list characteristic

                container charging-group {
                  description
                      "Configure a charging group to match against to resolve to actions";
                  leaf eq---neq {
                    type enumeration {
                      enum eq;
                      enum neq;
                    }
                    default "eq";
                  } //eq---neq

                  leaf charging-group-name {
                    type string {
                      length "1..32";
                    }
                  } //charging-group-name

                } //container charging-group

                container dscp {
                  description
                      "Configure a DSCP name to match against to resolve to actions";
                  leaf eq---neq {
                    type enumeration {
                      enum eq;
                      enum neq;
                    }
                    default "eq";
                    description
                        "keyword - comparison operator";
                  } //eq---neq

                  leaf dscp-name {
                    type string {
                      length "1..32";
                    }
                    description
                        "Attribute dscp-name for dscp";
                  } //dscp-name

                } //container dscp

                container dst-ip {
                  description
                      "Configure a dst ip address to match against to resolve to actions";
                  leaf eq-neq {
                    type enumeration {
                      enum eq;
                      enum neq;
                    }
                    default "eq";
                    description
                        "keyword - comparison operator";
                  } //eq-neq

                  leaf ip-address {
                    type string;
                    description
                        "Attribute ip-address for dst-ip";
                  } //ip-address

                  leaf ip-prefix-list {
                    type string {
                      length "1..32";
                    }
                  } //ip-prefix-list

                } //container dst-ip

                container dst-port {
                  description
                      "Configure a dst port or port range to match against to resolve to actions";
                  leaf eq---neq {
                    type enumeration {
                      enum eq;
                      enum neq;
                    }
                    default "eq";
                    description
                        "keyword - comparison operator";
                  } //eq---neq

                  leaf range {
                    type boolean;
                  } //range

                  leaf port-num {
                    type string;
                    description
                        "Attribute port-num for dst-port";
                  } //port-num

                  leaf start-port-num {
                    type string;
                    description
                        "Attribute start-port-num for dst-port";
                  } //start-port-num

                  leaf end-port-num {
                    type string;
                    description
                        "Attribute end-port-num for dst-port";
                  } //end-port-num

                  leaf port-list {
                    type boolean;
                  } //port-list

                  leaf port-list-name {
                    type string {
                      length "1..32";
                    }
                  } //port-list-name

                } //container dst-port

                container ip-protocol-num {
                  description
                      "Configure the IP protocol number to match against to resolve to actions";
                  leaf eq---neq {
                    type enumeration {
                      enum eq;
                      enum neq;
                    }
                    default "eq";
                    description
                        "keyword - comparison operator";
                  } //eq---neq

                  leaf protocol-id {
                    type string;
                    description
                        "Attribute protocol-id for ip-protocol-num";
                  } //protocol-id

                } //container ip-protocol-num

                container src-ip {
                  description
                      "Configure a src ip address to match against to resolve to actions";
                  leaf eq-neq {
                    type enumeration {
                      enum eq;
                      enum neq;
                    }
                    default "eq";
                    description
                        "keyword - comparison operator";
                  } //eq-neq

                  leaf ip-address {
                    type string;
                    description
                        "Attribute ip-address for src-ip";
                  } //ip-address

                  leaf ip-prefix-list {
                    type string {
                      length "1..32";
                    }
                  } //ip-prefix-list

                } //container src-ip

                container src-port {
                  description
                      "Configure a src port or port range to match against to resolve to actions";
                  leaf eq---neq {
                    type enumeration {
                      enum eq;
                      enum neq;
                    }
                    default "eq";
                    description
                        "keyword - comparison operator";
                  } //eq---neq

                  leaf range {
                    type boolean;
                  } //range

                  leaf port-num {
                    type string;
                    description
                        "Attribute port-num for src-port";
                  } //port-num

                  leaf start-port-num {
                    type string;
                    description
                        "Attribute start-port-num for src-port";
                  } //start-port-num

                  leaf end-port-num {
                    type string;
                    description
                        "Attribute end-port-num for src-port";
                  } //end-port-num

                  leaf port-list {
                    type boolean;
                  } //port-list

                  leaf port-list-name {
                    type string {
                      length "1..32";
                    }
                  } //port-list-name

                } //container src-port

                container traffic-direction {
                  description
                      "Configure a traffic flow direction to match against to resolve to actions";
                  leaf traffic-direction-id {
                    type enumeration {
                      enum subscriber-to-network;
                      enum network-to-subscriber;
                      enum both;
                    }
                  } //traffic-direction-id

                } //container traffic-direction

                list flow-attribute {
                  key "flow-attribute-name";
                  description
                      "Configure a flow-attribtue to match against to resolve to actions";
                  leaf flow-attribute-name {
                    type string {
                    }
                  } //flow-attribute-name

                  container confidence {
                    description
                        "Set the confidence level of the flow-attribute";
                    leaf eq {
                      type uint32 {
                        range "0..100";
                      }
                    } //eq

                    leaf lt {
                      type uint32 {
                        range "1..100";
                      }
                    } //lt

                    leaf gte {
                      type uint32 {
                        range "0..100";
                      }
                    } //gte

                  } //container confidence

                } //list flow-attribute

              } //container match

            } //list entry

          } //container app-qos-policy

          container app-service-options {
            description
                "Configure application service option characteristics";
            list characteristic {
              key "characteristic-name";
              description
                  "Configure an application service option characteristic";
              leaf characteristic-name {
                type string {
                  length "1..32";
                }
              } //characteristic-name

              leaf persist-id {
                type uint32;
              } //persist-id

              container default-value {
                description
                    "Configure an application service option characteristic's default value";
                leaf value-name {
                  type string {
                    length "1..32";
                  }
                } //value-name

              } //container default-value

              list value {
                key "value-name";
                description
                    "Configure an application service option characteristic value";
                leaf value-name {
                  type string {
                    length "1..32";
                  }
                } //value-name

                leaf persist-id {
                  type uint32;
                } //persist-id

              } //list value

            } //list characteristic

          } //container app-service-options

          list application {
            key "application-name";
            description
                "Configure application";
            leaf application-name {
              type string {
                length "1..32";
              }
            } //application-name

            container app-group {
              description
                  "Configure application group that this application is a member of";
              leaf app-group-name {
                type string {
                  length "1..32";
                }
              } //app-group-name

            } //container app-group

            container charging-group {
              description
                  "Configure this application's charging group";
              leaf charging-group-name {
                type string {
                  length "1..32";
                }
              } //charging-group-name

            } //container charging-group

            container description {
              description
                  "Configure application description";
              leaf description-string {
                type string {
                  length "1..80";
                }
              } //description-string

            } //container description

            container export-id {
              description
                  "Identifier used to represent this application in the exported accounting 
                   records";
              leaf export-id {
                type uint32 {
                  range "1..255";
                }
              } //export-id

            } //container export-id

          } //list application

          list charging-group {
            key "charging-group-name";
            description
                "Configure charging group";
            leaf charging-group-name {
              type string {
                length "1..32";
              }
            } //charging-group-name

            container description {
              description
                  "Configure charging group description";
              leaf description-string {
                type string {
                  length "1..80";
                }
              } //description-string

            } //container description

            container export-id {
              description
                  "Identifier used to represent this charging-group in the exported accounting 
                   records";
              leaf export-id {
                type uint32 {
                  range "1..255";
                }
              } //export-id

            } //container export-id

            container notify-start-stop {
              description
                  "Enable/disable start and stop notifications";
              leaf notify-start-stop {
                type enumeration {
                  enum flow-based;
                }
              } //notify-start-stop

            } //container notify-start-stop

          } //list charging-group

          list custom-protocol {
            key "custom-protocol-id";
            description
                "Configure a custom-protocol";
            leaf custom-protocol-id {
              type uint32 {
                range "1..10";
              }
            } //custom-protocol-id

            leaf ip-protocol-num {
              type string;
              description
                  "[6,17] - protocol numbers 
                   keywords - tcp|udp";
            } //ip-protocol-num

            container description {
              description
                  "Configure a custom protocol description";
              leaf description-string {
                type string {
                  length "1..80";
                }
              } //description-string

            } //container description

            list expression {
              key "expr-index";
              description
                  "Configure expression strings to match against when determining a custom 
                   protocol";
              leaf expr-index {
                type uint32 {
                }
              } //expr-index

              leaf eq {
                type enumeration {
                  enum eq;
                }
                default "eq";
              } //eq

              leaf expr-string {
                type string {
                }
                description
                    "expression string used to define a custom protocol match";
              } //expr-string

              leaf offset {
                type uint32 {
                  range "0..127";
                }
              } //offset

              leaf direction {
                type enumeration {
                  enum client-to-server;
                  enum server-to-client;
                  enum any;
                }
              } //direction

            } //list expression

            leaf shutdown {
              type boolean;
              description
                  "Administratively enable/disable a custom protocol";
            }

          } //list custom-protocol

        } //container policy

        container policy-override {
          description
              "Configure policy override";
          list policy {
            key "aa-sub";
            description
                "Configure a policy-override";
            leaf aa-sub {
              type boolean;
            } //aa-sub

            leaf sap {
              type string;
              description
                  "Attribute sap-id for policy";
            } //sap

            leaf spoke-sdp {
              type string;
              description
                  "sdp-id - [1..32767] 
                   vc-id - [1..4294967295]";
            } //spoke-sdp

            leaf transit {
              type string {
                length "1..32";
              }
            } //transit

            list characteristic {
              key "characteristic-name";
              description
                  "Configure an override characteristic and value";
              leaf characteristic-name {
                type string {
                  length "1..32";
                }
              } //characteristic-name

              leaf value {
                type string {
                  length "1..32";
                }
              } //value

            } //list characteristic

          } //list policy

        } //container policy-override

        list port-list {
          key "port-list-name";
          description
              "Configure a port-list";
          leaf port-list-name {
            type string {
              length "1..32";
            }
          } //port-list-name

          container description {
            description
                "Configure the port-list description";
            leaf description-string {
              type string {
                length "1..80";
              }
            } //description-string

          } //container description

          container port {
            description
                "Configure a port or port-range in the port-list";
            leaf port-number {
              type string;
              description
                  "[0..65535]D 
                   [0x0..0xFFFF]H 
                   [0b0..0b1111111111111111]B";
            } //port-number

            leaf range {
              type boolean;
            } //range

            leaf start-port {
              type string;
              description
                  "[0..65535]D 
                   [0x0..0xFFFF]H 
                   [0b0..0b1111111111111111]B";
            } //start-port

            leaf end-port {
              type string;
              description
                  "[0..65535]D 
                   [0x0..0xFFFF]H 
                   [0b0..0b1111111111111111]B";
            } //end-port

          } //container port

        } //list port-list

        list sctp-filter {
          key "sctp-filter-name";
          description
              "Configure an SCTP (Stream Control Transmission Protocol) filter";
          leaf sctp-filter-name {
            type string {
              length "1..32";
            }
          } //sctp-filter-name

          container description {
            description
                "Configure a description of the SCTP filter";
            leaf description-string {
              type string {
                length "1..80";
              }
            } //description-string

          } //container description

          container event-log {
            description
                "Configure an event log for packets dropped by the SCTP filter";
            leaf event-log-name {
              type string {
                length "1..32";
              }
            } //event-log-name

          } //container event-log

          container ppid-range {
            description
                "Configure the range of allowable PPIDs for the SCTP filter";
            leaf min {
              type uint32;
            } //min

            leaf max {
              type uint32;
            } //max

          } //container ppid-range

          container ppid {
            description
                "Configure actions for specific or default PPIDs (Payload Protocol Identifiers)";
            container default-action {
              description
                  "Configure the default action for all SCTP PPIDs";
              leaf permit-deny {
                type enumeration {
                  enum permit;
                  enum deny;
                }
                default "permit";
                description
                    "permit|deny - Default: permit";
              } //permit-deny

            } //container default-action

            list entry {
              key "entry-id";
              description
                  "Configure an entry for a specific SCTP PPID value";
              leaf entry-id {
                type uint32 {
                  range "1..255";
                }
              } //entry-id

              leaf value {
                type string {
                }
                description
                    "[0..4294967295]D | [256 chars max]";
              } //value

              leaf action {
                type enumeration {
                  enum permit;
                  enum deny;
                }
              } //action

            } //list entry

          } //container ppid

        } //list sctp-filter

        list session-filter {
          key "session-filter-name";
          description
              "Configure a session-filter";
          leaf session-filter-name {
            type string {
              length "1..32";
            }
          } //session-filter-name

          container default-action {
            description
                "Configure the default action";
            leaf permit-deny {
              type enumeration {
                enum permit;
                enum deny;
              }
            } //permit-deny

            leaf event-log {
              type string {
                length "1..32";
              }
            } //event-log

          } //container default-action

          container description {
            description
                "Configure the description";
            leaf description-string {
              type string {
                length "1..80";
              }
            } //description-string

          } //container description

          list entry {
            key "entry-id";
            description
                "Configure an entry in the session filter";
            leaf entry-id {
              type uint32 {
                range "1..65535";
              }
            } //entry-id

            container action {
              description
                  "Configure the action for this entry";
              leaf permit-deny-tcp-strict-order-bypass-mptcp {
                type enumeration {
                  enum permit;
                  enum deny;
                  enum tcp-strict-order;
                  enum bypass-mptcp;
                }
              } //permit-deny-tcp-strict-order-bypass-mptcp

              leaf http-redirect {
                type string {
                  length "1..32";
                }
              } //http-redirect

              leaf redirect {
                type boolean;
              } //redirect

              leaf dst-ip {
                type string;
                description
                    "Attribute ip-address for action";
              } //dst-ip

              leaf dst-port {
                type string;
                description
                    "destination port";
              } //dst-port

              leaf event-log {
                type string {
                  length "1..32";
                }
              } //event-log

            } //container action

            container description {
              description
                  "Configure the description for this entry";
              leaf description-string {
                type string {
                  length "1..80";
                }
              } //description-string

            } //container description

            container match {
              description
                  "Configure match conditions for this entry";
              container dst-ip {
                description
                    "Configure the destination IP address to match against";
                leaf ip-address {
                  type string;
                  description
                      "Attribute ip-address for dst-ip";
                } //ip-address

                leaf ip-prefix-list {
                  type string {
                    length "1..32";
                  }
                } //ip-prefix-list

                leaf dns-ip-cache {
                  type string {
                    length "1..32";
                  }
                } //dns-ip-cache

              } //container dst-ip

              container dst-port {
                description
                    "Configure a destination port or port range to match against";
                leaf eq---gt---lt {
                  type enumeration {
                    enum eq;
                    enum gt;
                    enum lt;
                  }
                  default "eq";
                } //eq---gt---lt

                leaf port-num {
                  type string;
                  description
                      "Attribute port-num for dst-port";
                } //port-num

                leaf range {
                  type boolean;
                } //range

                leaf start-port-num {
                  type string;
                  description
                      "Attribute start-port-num for dst-port";
                } //start-port-num

                leaf end-port-num {
                  type string;
                  description
                      "Attribute end-port-num for dst-port";
                } //end-port-num

                leaf port-list {
                  type boolean;
                } //port-list

                leaf port-list-name {
                  type string {
                    length "1..32";
                  }
                } //port-list-name

              } //container dst-port

              container ip-protocol-num {
                description
                    "Configure the IP protocol number to match against";
                leaf ip-protocol-number {
                  type string;
                  description
                      "Attribute ip-protocol-number for ip-protocol-num";
                } //ip-protocol-number

              } //container ip-protocol-num

              container src-ip {
                description
                    "Configure the source IP address to match against";
                leaf ip-address {
                  type string;
                  description
                      "Attribute ip-address for src-ip";
                } //ip-address

                leaf ip-prefix-list {
                  type string {
                    length "1..32";
                  }
                } //ip-prefix-list

              } //container src-ip

              container src-port {
                description
                    "Configure a source port or port range to match against";
                leaf eq---gt---lt {
                  type enumeration {
                    enum eq;
                    enum gt;
                    enum lt;
                  }
                  default "eq";
                } //eq---gt---lt

                leaf port-num {
                  type string;
                  description
                      "Attribute port-num for src-port";
                } //port-num

                leaf range {
                  type boolean;
                } //range

                leaf start-port-num {
                  type string;
                  description
                      "Attribute start-port-num for src-port";
                } //start-port-num

                leaf end-port-num {
                  type string;
                  description
                      "Attribute end-port-num for src-port";
                } //end-port-num

                leaf port-list {
                  type boolean;
                } //port-list

                leaf port-list-name {
                  type string {
                    length "1..32";
                  }
                } //port-list-name

              } //container src-port

            } //container match

          } //list entry

        } //list session-filter

        container statistics {
          description
              "Configure statistics generation";
          container aa-admit-deny {
            description
                "Configure admit-deny statistics generation";
            container accounting-policy {
              description
                  "Configure accounting-policy to be used";
              leaf acct-policy-id {
                type uint64 {
                  range "1..99";
                }
              } //acct-policy-id

            } //container accounting-policy

            leaf collect-stats {
              type boolean;
              description
                  "Enable/Disable admit-deny statistics collection for accounting";
            }

            leaf gtp-filter-stats {
              type boolean;
              description
                  "Include/Exclude GTP filter admit-deny statistics in accounting";
            }

            leaf policer-stats {
              type boolean;
              description
                  "Include/Exclude policer admit-deny statistics in accounting";
            }

            leaf policer-stats-resources {
              type boolean;
              description
                  "Allocate/Deallocate ISA resources for policer admit-deny statistics";
            }

            leaf sctp-filter-stats {
              type boolean;
              description
                  "Include/Exclude SCTP filter admit-deny statistics in accounting";
            }

            leaf session-filter-stats {
              type boolean;
              description
                  "Include/Exclude session filter admit-deny statistics in accounting";
            }

            leaf tcp-validate-stats {
              type boolean;
              description
                  "Include/Exclude TCP validate admit-deny statistics in accounting";
            }

          } //container aa-admit-deny

          container aa-partition {
            description
                "Configure per-partition statistics generation";
            container accounting-policy {
              description
                  "Configure accounting-policy to be used";
              leaf acct-policy-id {
                type uint64 {
                  range "1..99";
                }
              } //acct-policy-id

            } //container accounting-policy

            leaf collect-stats {
              type boolean;
              description
                  "Enable/Disable statistics collection for aa-partition";
            }

            leaf tethering-summary {
              type boolean;
              description
                  "Enable/Disable tethering summary statistics collection within aa-partition";
            }

            leaf traffic-type {
              type boolean;
              description
                  "Enable/Disable traffic type statistics collection within aa-partition";
            }

          } //container aa-partition

          container aa-sub {
            description
                "Configure per-subscriber statistics generation";
            container accounting-policy {
              description
                  "Configure accounting-policy to be used";
              leaf acct-policy-id {
                type uint64 {
                  range "1..99";
                }
              } //acct-policy-id

            } //container accounting-policy

            container aggregate-stats {
              description
                  "Configure aggregate statistics collection";
              leaf no-export {
                type boolean;
              } //no-export

              leaf-list export-using {
                type enumeration {
                  enum accounting-policy;
                  enum radius-accounting-policy;
                }
                max-elements 2;
              } //export-using

            } //container aggregate-stats

            list app-group {
              key "app-group-name";
              description
                  "Configure application groups reported on a per-subscriber basis";
              leaf app-group-name {
                type string {
                  length "1..32";
                }
              } //app-group-name

              leaf-list export-using {
                type enumeration {
                  enum accounting-policy;
                  enum radius-accounting-policy;
                }
                max-elements 2;
              } //export-using

              leaf no-export {
                type boolean;
              } //no-export

            } //list app-group

            list application {
              key "application-name";
              description
                  "Configure applications reported on a per-subscriber basis";
              leaf application-name {
                type string {
                  length "1..32";
                }
              } //application-name

              leaf-list export-using {
                type enumeration {
                  enum accounting-policy;
                  enum radius-accounting-policy;
                }
                max-elements 2;
              } //export-using

              leaf no-export {
                type boolean;
              } //no-export

            } //list application

            list charging-group {
              key "charging-group-name";
              description
                  "Configure charging groups reported on a per-subscriber basis";
              leaf charging-group-name {
                type string {
                  length "1..32";
                }
              } //charging-group-name

              leaf-list export-using {
                type enumeration {
                  enum accounting-policy;
                  enum radius-accounting-policy;
                }
                max-elements 2;
              } //export-using

              leaf no-export {
                type boolean;
              } //no-export

            } //list charging-group

            leaf collect-stats {
              type boolean;
              description
                  "Enable/Disable statistics collection";
            }

            leaf exclude-tcp-retrans {
              type boolean;
              description
                  "Exclude billing of TCP retransmissions";
            }

            leaf max-throughput-stats {
              type boolean;
              description
                  "Enable/Disable max-throughput stats collection";
            }

            list protocol {
              key "protocol-name";
              description
                  "Configure protocols reported on a per-subscriber basis";
              leaf protocol-name {
                type string {
                  length "1..32";
                }
              } //protocol-name

              leaf-list export-using {
                type enumeration {
                  enum accounting-policy;
                }
                max-elements 1;
              } //export-using

            } //list protocol

            container radius-accounting-policy {
              description
                  "Configure radius-accounting-policy to be used";
              leaf rad-acct-plcy-name {
                type string {
                  length "1..32";
                }
              } //rad-acct-plcy-name

            } //container radius-accounting-policy

            leaf usage-monitoring {
              type boolean;
              description
                  "Enable/Disable usage-monitoring";
            }

          } //container aa-sub

          list aa-sub-study {
            key "study-type";
            description
                "Configure per-subscriber special study statistics generation";
            leaf study-type {
              type enumeration {
                enum application;
                enum protocol;
              }
            } //study-type

            container aa-sub {
              description
                  "Configure subscriber to be used";
              leaf esm {
                type string {
                  length "1..32";
                }
              } //esm

              leaf sap {
                type string;
                description
                    "Attribute sap-id for aa-sub";
              } //sap

              leaf spoke-sdp {
                type string;
                description
                    "sdp-id - [1..32767] 
                     vc-id - [1..4294967295]";
              } //spoke-sdp

              leaf transit {
                type string {
                  length "1..32";
                }
              } //transit

              leaf esm-mac {
                type string {
                  length "1..32";
                }
              } //esm-mac

            } //container aa-sub

            container accounting-policy {
              description
                  "Configure accounting-policy to be used";
              leaf acct-policy-id {
                type uint64 {
                  range "1..99";
                }
              } //acct-policy-id

            } //container accounting-policy

            leaf collect-stats {
              type boolean;
              description
                  "Enable/Disable statistics collection";
            }

          } //list aa-sub-study

          container app-group {
            description
                "Configure application-group statistics generation";
            container accounting-policy {
              description
                  "Configure accounting-policy to be used";
              leaf acct-policy-id {
                type uint64 {
                  range "1..99";
                }
              } //acct-policy-id

            } //container accounting-policy

            leaf collect-stats {
              type boolean;
              description
                  "Enable/Disable statistics collection";
            }

          } //container app-group

          container application {
            description
                "Configure application statistics generation";
            container accounting-policy {
              description
                  "Configure accounting-policy to be used";
              leaf acct-policy-id {
                type uint64 {
                  range "1..99";
                }
              } //acct-policy-id

            } //container accounting-policy

            leaf collect-stats {
              type boolean;
              description
                  "Enable/Disable statistics collection";
            }

          } //container application

          container protocol {
            description
                "Configure protocol statistics generation";
            container accounting-policy {
              description
                  "Configure accounting-policy to be used";
              leaf acct-policy-id {
                type uint64 {
                  range "1..99";
                }
              } //acct-policy-id

            } //container accounting-policy

            leaf collect-stats {
              type boolean;
              description
                  "Enable/Disable statistics collection";
            }

            leaf shutdown {
              type boolean;
              description
                  "Administratively shut down protocol statistics collection";
            }

          } //container protocol

          container threshold-crossing-alert {
            description
                "Configure threshold crossing alert (TCA) generation";
            list error-drop {
              key "direction";
              description
                  "Configure error-drop TCA generation";
              leaf direction {
                type enumeration {
                  enum from-sub;
                  enum to-sub;
                }
              } //direction

              container high-wmark {
                description
                    "Configure the high and low watermarks";
                leaf high-watermark {
                  type uint32 {
                    range "1..4294967295";
                  }
                  default 4294967295;
                  description
                      "[1..4294967295] - Default: 4294967295";
                } //high-watermark

                leaf low-wmark {
                  type uint32 {
                    range "0..4294967294";
                  }
                  default 0;
                  description
                      "[0..4294967294] - Default: 0";
                } //low-wmark

              } //container high-wmark

            } //list error-drop

            list fragment-drop-all {
              key "direction";
              description
                  "Configure fragment-drop-all TCA generation";
              leaf direction {
                type enumeration {
                  enum from-sub;
                  enum to-sub;
                }
              } //direction

              container high-wmark {
                description
                    "Configure the high and low watermarks";
                leaf high-watermark {
                  type uint32 {
                    range "1..4294967295";
                  }
                  default 4294967295;
                  description
                      "[1..4294967295] - Default: 4294967295";
                } //high-watermark

                leaf low-wmark {
                  type uint32 {
                    range "0..4294967294";
                  }
                  default 0;
                  description
                      "[0..4294967294] - Default: 0";
                } //low-wmark

              } //container high-wmark

            } //list fragment-drop-all

            list fragment-drop-out-of-order {
              key "direction";
              description
                  "Configure fragment-drop-out-of-order TCA generation";
              leaf direction {
                type enumeration {
                  enum from-sub;
                  enum to-sub;
                }
              } //direction

              container high-wmark {
                description
                    "Configure the high and low watermarks";
                leaf high-watermark {
                  type uint32 {
                    range "1..4294967295";
                  }
                  default 4294967295;
                  description
                      "[1..4294967295] - Default: 4294967295";
                } //high-watermark

                leaf low-wmark {
                  type uint32 {
                    range "0..4294967294";
                  }
                  default 0;
                  description
                      "[0..4294967294] - Default: 0";
                } //low-wmark

              } //container high-wmark

            } //list fragment-drop-out-of-order

            container gtp-filter {
              description
                  "Configure GTP filter TCA generation";
              leaf gtp-filter-name {
                type string {
                  length "1..32";
                }
              } //gtp-filter-name

              list gtp-in-gtp {
                key "direction";
                description
                    "Configure GTP filter gtp-in-gtp TCA generation";
                leaf direction {
                  type enumeration {
                    enum from-sub;
                    enum to-sub;
                  }
                } //direction

                container high-wmark {
                  description
                      "Configure the high and low watermarks";
                  leaf high-watermark {
                    type uint32 {
                      range "1..4294967295";
                    }
                    default 4294967295;
                    description
                        "[1..4294967295] - Default: 4294967295";
                  } //high-watermark

                  leaf low-wmark {
                    type uint32 {
                      range "0..4294967294";
                    }
                    default 0;
                    description
                        "[0..4294967294] - Default: 0";
                  } //low-wmark

                } //container high-wmark

              } //list gtp-in-gtp

              container imsi-apn-filter {
                description
                    "Configure IMSI APN filter TCA generation";
                list default-action {
                  key "direction";
                  description
                      "Configure GTP filter default-action TCA generation";
                  leaf direction {
                    type enumeration {
                      enum from-sub;
                      enum to-sub;
                    }
                  } //direction

                  container high-wmark {
                    description
                        "Configure the high and low watermarks";
                    leaf high-watermark {
                      type uint32 {
                        range "1..4294967295";
                      }
                      default 4294967295;
                      description
                          "[1..4294967295] - Default: 4294967295";
                    } //high-watermark

                    leaf low-wmark {
                      type uint32 {
                        range "0..4294967294";
                      }
                      default 0;
                      description
                          "[0..4294967294] - Default: 0";
                    } //low-wmark

                  } //container high-wmark

                } //list default-action

                list entry {
                  key "entry-id direction";
                  description
                      "Configure GTP filter entry TCA generation";
                  leaf entry-id {
                    type uint32 {
                      range "1031..2030";
                    }
                  } //entry-id

                  leaf direction {
                    type enumeration {
                      enum from-sub;
                      enum to-sub;
                    }
                  } //direction

                  container high-wmark {
                    description
                        "Configure the high and low watermarks";
                    leaf high-watermark {
                      type uint32 {
                        range "1..4294967295";
                      }
                      default 4294967295;
                      description
                          "[1..4294967295] - Default: 4294967295";
                    } //high-watermark

                    leaf low-wmark {
                      type uint32 {
                        range "0..4294967294";
                      }
                      default 0;
                      description
                          "[0..4294967294] - Default: 0";
                    } //low-wmark

                  } //container high-wmark

                } //list entry

              } //container imsi-apn-filter

              list max-payload-length {
                key "direction";
                description
                    "Configure GTP filter maximum-payload-length TCA generation";
                leaf direction {
                  type enumeration {
                    enum from-sub;
                    enum to-sub;
                  }
                } //direction

                container high-wmark {
                  description
                      "Configure the high and low watermarks";
                  leaf high-watermark {
                    type uint32 {
                      range "1..4294967295";
                    }
                    default 4294967295;
                    description
                        "[1..4294967295] - Default: 4294967295";
                  } //high-watermark

                  leaf low-wmark {
                    type uint32 {
                      range "0..4294967294";
                    }
                    default 0;
                    description
                        "[0..4294967294] - Default: 0";
                  } //low-wmark

                } //container high-wmark

              } //list max-payload-length

              container message-type {
                description
                    "Configure GTP filter message-type TCA generation";
                list default-action {
                  key "direction";
                  description
                      "Configure GTP filter default-action TCA generation";
                  leaf direction {
                    type enumeration {
                      enum from-sub;
                      enum to-sub;
                    }
                  } //direction

                  container high-wmark {
                    description
                        "Configure the high and low watermarks";
                    leaf high-watermark {
                      type uint32 {
                        range "1..4294967295";
                      }
                      default 4294967295;
                      description
                          "[1..4294967295] - Default: 4294967295";
                    } //high-watermark

                    leaf low-wmark {
                      type uint32 {
                        range "0..4294967294";
                      }
                      default 0;
                      description
                          "[0..4294967294] - Default: 0";
                    } //low-wmark

                  } //container high-wmark

                } //list default-action

                list entry {
                  key "entry-id direction";
                  description
                      "Configure GTP filter entry TCA generation";
                  leaf entry-id {
                    type uint32 {
                      range "1..255";
                    }
                  } //entry-id

                  leaf direction {
                    type enumeration {
                      enum from-sub;
                      enum to-sub;
                    }
                  } //direction

                  container high-wmark {
                    description
                        "Configure the high and low watermarks";
                    leaf high-watermark {
                      type uint32 {
                        range "1..4294967295";
                      }
                      default 4294967295;
                      description
                          "[1..4294967295] - Default: 4294967295";
                    } //high-watermark

                    leaf low-wmark {
                      type uint32 {
                        range "0..4294967294";
                      }
                      default 0;
                      description
                          "[0..4294967294] - Default: 0";
                    } //low-wmark

                  } //container high-wmark

                } //list entry

                list header-sanity {
                  key "direction";
                  description
                      "Configure GTP filter header-sanity TCA generation";
                  leaf direction {
                    type enumeration {
                      enum from-sub;
                      enum to-sub;
                    }
                  } //direction

                  container high-wmark {
                    description
                        "Configure the high and low watermarks";
                    leaf high-watermark {
                      type uint32 {
                        range "1..4294967295";
                      }
                      default 4294967295;
                      description
                          "[1..4294967295] - Default: 4294967295";
                    } //high-watermark

                    leaf low-wmark {
                      type uint32 {
                        range "0..4294967294";
                      }
                      default 0;
                      description
                          "[0..4294967294] - Default: 0";
                    } //low-wmark

                  } //container high-wmark

                } //list header-sanity

              } //container message-type

              container message-type-gtpv2 {
                description
                    "Configure GTP V2 filter message-type TCA generation";
                list default-action {
                  key "direction";
                  description
                      "Configure GTP filter default-action TCA generation";
                  leaf direction {
                    type enumeration {
                      enum from-sub;
                      enum to-sub;
                    }
                  } //direction

                  container high-wmark {
                    description
                        "Configure the high and low watermarks";
                    leaf high-watermark {
                      type uint32 {
                        range "1..4294967295";
                      }
                      default 4294967295;
                      description
                          "[1..4294967295] - Default: 4294967295";
                    } //high-watermark

                    leaf low-wmark {
                      type uint32 {
                        range "0..4294967294";
                      }
                      default 0;
                      description
                          "[0..4294967294] - Default: 0";
                    } //low-wmark

                  } //container high-wmark

                } //list default-action

                list entry {
                  key "entry-id direction";
                  description
                      "Configure GTP filter entry TCA generation";
                  leaf entry-id {
                    type uint32 {
                      range "516..770";
                    }
                  } //entry-id

                  leaf direction {
                    type enumeration {
                      enum from-sub;
                      enum to-sub;
                    }
                  } //direction

                  container high-wmark {
                    description
                        "Configure the high and low watermarks";
                    leaf high-watermark {
                      type uint32 {
                        range "1..4294967295";
                      }
                      default 4294967295;
                      description
                          "[1..4294967295] - Default: 4294967295";
                    } //high-watermark

                    leaf low-wmark {
                      type uint32 {
                        range "0..4294967294";
                      }
                      default 0;
                      description
                          "[0..4294967294] - Default: 0";
                    } //low-wmark

                  } //container high-wmark

                } //list entry

              } //container message-type-gtpv2

              list missing-mandatory-ie {
                key "direction";
                description
                    "Configure GTP filter missing-mandatory-ie TCA generation";
                leaf direction {
                  type enumeration {
                    enum from-sub;
                    enum to-sub;
                  }
                } //direction

                container high-wmark {
                  description
                      "Configure the high and low watermarks";
                  leaf high-watermark {
                    type uint32 {
                      range "1..4294967295";
                    }
                    default 4294967295;
                    description
                        "[1..4294967295] - Default: 4294967295";
                  } //high-watermark

                  leaf low-wmark {
                    type uint32 {
                      range "0..4294967294";
                    }
                    default 0;
                    description
                        "[0..4294967294] - Default: 0";
                  } //low-wmark

                } //container high-wmark

              } //list missing-mandatory-ie

              list tunnel-endpoint-limit {
                key "direction";
                description
                    "Configure tunnel endpoint limit TCA generation";
                leaf direction {
                  type enumeration {
                    enum from-sub;
                    enum to-sub;
                  }
                } //direction

                container high-wmark {
                  description
                      "Configure the high and low watermarks";
                  leaf high-watermark {
                    type uint32 {
                      range "1..4294967295";
                    }
                    default 4294967295;
                    description
                        "[1..4294967295] - Default: 4294967295";
                  } //high-watermark

                  leaf low-wmark {
                    type uint32 {
                      range "0..4294967294";
                    }
                    default 0;
                    description
                        "[0..4294967294] - Default: 0";
                  } //low-wmark

                } //container high-wmark

              } //list tunnel-endpoint-limit

              list tunnel-resource-limit {
                key "direction";
                description
                    "Configure tunnel resource limit TCA generation";
                leaf direction {
                  type enumeration {
                    enum from-sub;
                    enum to-sub;
                  }
                } //direction

                container high-wmark {
                  description
                      "Configure the high and low watermarks";
                  leaf high-watermark {
                    type uint32 {
                      range "1..4294967295";
                    }
                    default 4294967295;
                    description
                        "[1..4294967295] - Default: 4294967295";
                  } //high-watermark

                  leaf low-wmark {
                    type uint32 {
                      range "0..4294967294";
                    }
                    default 0;
                    description
                        "[0..4294967294] - Default: 0";
                  } //low-wmark

                } //container high-wmark

              } //list tunnel-resource-limit

              list validate-gtp-tunnels {
                key "direction";
                description
                    "Configure GTP filter validate-gtp-tunnels TCA generation";
                leaf direction {
                  type enumeration {
                    enum from-sub;
                    enum to-sub;
                  }
                } //direction

                container high-wmark {
                  description
                      "Configure the high and low watermarks";
                  leaf high-watermark {
                    type uint32 {
                      range "1..4294967295";
                    }
                    default 4294967295;
                    description
                        "[1..4294967295] - Default: 4294967295";
                  } //high-watermark

                  leaf low-wmark {
                    type uint32 {
                      range "0..4294967294";
                    }
                    default 0;
                    description
                        "[0..4294967294] - Default: 0";
                  } //low-wmark

                } //container high-wmark

              } //list validate-gtp-tunnels

              list validate-sequence-number {
                key "direction";
                description
                    "Configure GTP filter validate-sequence-number TCA generation";
                leaf direction {
                  type enumeration {
                    enum from-sub;
                    enum to-sub;
                  }
                } //direction

                container high-wmark {
                  description
                      "Configure the high and low watermarks";
                  leaf high-watermark {
                    type uint32 {
                      range "1..4294967295";
                    }
                    default 4294967295;
                    description
                        "[1..4294967295] - Default: 4294967295";
                  } //high-watermark

                  leaf low-wmark {
                    type uint32 {
                      range "0..4294967294";
                    }
                    default 0;
                    description
                        "[0..4294967294] - Default: 0";
                  } //low-wmark

                } //container high-wmark

              } //list validate-sequence-number

              list validate-src-ip-addr {
                key "direction";
                description
                    "Configure GTP filter validate source IP address TCA generation";
                leaf direction {
                  type enumeration {
                    enum from-sub;
                    enum to-sub;
                  }
                } //direction

                container high-wmark {
                  description
                      "Configure the high and low watermarks";
                  leaf high-watermark {
                    type uint32 {
                      range "1..4294967295";
                    }
                    default 4294967295;
                    description
                        "[1..4294967295] - Default: 4294967295";
                  } //high-watermark

                  leaf low-wmark {
                    type uint32 {
                      range "0..4294967294";
                    }
                    default 0;
                    description
                        "[0..4294967294] - Default: 0";
                  } //low-wmark

                } //container high-wmark

              } //list validate-src-ip-addr

            } //container gtp-filter

            list gtp-sanity-drop {
              key "direction";
              description
                  "Configure gtp-sanity-drop TCA generation";
              leaf direction {
                type enumeration {
                  enum from-sub;
                  enum to-sub;
                }
              } //direction

              container high-wmark {
                description
                    "Configure the high and low watermarks";
                leaf high-watermark {
                  type uint32 {
                    range "1..4294967295";
                  }
                  default 4294967295;
                  description
                      "[1..4294967295] - Default: 4294967295";
                } //high-watermark

                leaf low-wmark {
                  type uint32 {
                    range "0..4294967294";
                  }
                  default 0;
                  description
                      "[0..4294967294] - Default: 0";
                } //low-wmark

              } //container high-wmark

            } //list gtp-sanity-drop

            list overload-drop {
              key "direction";
              description
                  "Configure overload-drop TCA generation";
              leaf direction {
                type enumeration {
                  enum from-sub;
                  enum to-sub;
                }
              } //direction

              container high-wmark {
                description
                    "Configure the high and low watermarks";
                leaf high-watermark {
                  type uint32 {
                    range "1..4294967295";
                  }
                  default 4294967295;
                  description
                      "[1..4294967295] - Default: 4294967295";
                } //high-watermark

                leaf low-wmark {
                  type uint32 {
                    range "0..4294967294";
                  }
                  default 0;
                  description
                      "[0..4294967294] - Default: 0";
                } //low-wmark

              } //container high-wmark

            } //list overload-drop

            list policer {
              key "policer-name direction";
              description
                  "Configure policer TCA generation";
              leaf policer-name {
                type string {
                  length "1..32";
                }
              } //policer-name

              leaf direction {
                type enumeration {
                  enum from-sub;
                  enum to-sub;
                }
              } //direction

              container high-wmark {
                description
                    "Configure the high and low watermarks";
                leaf high-watermark {
                  type uint32 {
                    range "1..4294967295";
                  }
                  default 4294967295;
                  description
                      "[1..4294967295] - Default: 4294967295";
                } //high-watermark

                leaf low-wmark {
                  type uint32 {
                    range "0..4294967294";
                  }
                  default 0;
                  description
                      "[0..4294967294] - Default: 0";
                } //low-wmark

              } //container high-wmark

            } //list policer

            container sctp-filter {
              description
                  "Configure SCTP filter TCA generation";
              leaf sctp-filter-name {
                type string {
                  length "1..32";
                }
              } //sctp-filter-name

              list packet-sanity {
                key "direction";
                description
                    "Configure SCTP filter packet-sanity TCA generation";
                leaf direction {
                  type enumeration {
                    enum from-sub;
                    enum to-sub;
                  }
                } //direction

                container high-wmark {
                  description
                      "Configure the high and low watermarks";
                  leaf high-watermark {
                    type uint32 {
                      range "1..4294967295";
                    }
                    default 4294967295;
                    description
                        "[1..4294967295] - Default: 4294967295";
                  } //high-watermark

                  leaf low-wmark {
                    type uint32 {
                      range "0..4294967294";
                    }
                    default 0;
                    description
                        "[0..4294967294] - Default: 0";
                  } //low-wmark

                } //container high-wmark

              } //list packet-sanity

              container ppid {
                description
                    "Configure SCTP filter PPID TCA generation";
                list default-action {
                  key "direction";
                  description
                      "Configure SCTP filter default-action TCA generation";
                  leaf direction {
                    type enumeration {
                      enum from-sub;
                      enum to-sub;
                    }
                  } //direction

                  container high-wmark {
                    description
                        "Configure the high and low watermarks";
                    leaf high-watermark {
                      type uint32 {
                        range "1..4294967295";
                      }
                      default 4294967295;
                      description
                          "[1..4294967295] - Default: 4294967295";
                    } //high-watermark

                    leaf low-wmark {
                      type uint32 {
                        range "0..4294967294";
                      }
                      default 0;
                      description
                          "[0..4294967294] - Default: 0";
                    } //low-wmark

                  } //container high-wmark

                } //list default-action

                list entry {
                  key "entry-id direction";
                  description
                      "Configure SCTP filter entry TCA generation";
                  leaf entry-id {
                    type uint32 {
                      range "1..255";
                    }
                  } //entry-id

                  leaf direction {
                    type enumeration {
                      enum from-sub;
                      enum to-sub;
                    }
                  } //direction

                  container high-wmark {
                    description
                        "Configure the high and low watermarks";
                    leaf high-watermark {
                      type uint32 {
                        range "1..4294967295";
                      }
                      default 4294967295;
                      description
                          "[1..4294967295] - Default: 4294967295";
                    } //high-watermark

                    leaf low-wmark {
                      type uint32 {
                        range "0..4294967294";
                      }
                      default 0;
                      description
                          "[0..4294967294] - Default: 0";
                    } //low-wmark

                  } //container high-wmark

                } //list entry

              } //container ppid

              list ppid-range {
                key "direction";
                description
                    "Configure SCTP filter PPID range TCA generation";
                leaf direction {
                  type enumeration {
                    enum from-sub;
                    enum to-sub;
                  }
                } //direction

                container high-wmark {
                  description
                      "Configure the high and low watermarks";
                  leaf high-watermark {
                    type uint32 {
                      range "1..4294967295";
                    }
                    default 4294967295;
                    description
                        "[1..4294967295] - Default: 4294967295";
                  } //high-watermark

                  leaf low-wmark {
                    type uint32 {
                      range "0..4294967294";
                    }
                    default 0;
                    description
                        "[0..4294967294] - Default: 0";
                  } //low-wmark

                } //container high-wmark

              } //list ppid-range

            } //container sctp-filter

            container session-filter {
              description
                  "Configure session filter TCA generation";
              leaf session-filter-name {
                type string {
                  length "1..32";
                }
              } //session-filter-name

              list default-action {
                key "direction";
                description
                    "Configure session filter default-action TCA generation";
                leaf direction {
                  type enumeration {
                    enum from-sub;
                    enum to-sub;
                  }
                } //direction

                container high-wmark {
                  description
                      "Configure the high and low watermarks";
                  leaf high-watermark {
                    type uint32 {
                      range "1..4294967295";
                    }
                    default 4294967295;
                    description
                        "[1..4294967295] - Default: 4294967295";
                  } //high-watermark

                  leaf low-wmark {
                    type uint32 {
                      range "0..4294967294";
                    }
                    default 0;
                    description
                        "[0..4294967294] - Default: 0";
                  } //low-wmark

                } //container high-wmark

              } //list default-action

              list entry {
                key "entry-id direction";
                description
                    "Configure session filter entry TCA generation";
                leaf entry-id {
                  type uint32 {
                    range "1..65535";
                  }
                } //entry-id

                leaf direction {
                  type enumeration {
                    enum from-sub;
                    enum to-sub;
                  }
                } //direction

                container high-wmark {
                  description
                      "Configure the high and low watermarks";
                  leaf high-watermark {
                    type uint32 {
                      range "1..4294967295";
                    }
                    default 4294967295;
                    description
                        "[1..4294967295] - Default: 4294967295";
                  } //high-watermark

                  leaf low-wmark {
                    type uint32 {
                      range "0..4294967294";
                    }
                    default 0;
                    description
                        "[0..4294967294] - Default: 0";
                  } //low-wmark

                } //container high-wmark

              } //list entry

            } //container session-filter

            list tcp-validate {
              key "tcp-validate-name direction";
              description
                  "Configure TCP validate TCA generation";
              leaf tcp-validate-name {
                type string {
                  length "1..32";
                }
              } //tcp-validate-name

              leaf direction {
                type enumeration {
                  enum from-sub;
                  enum to-sub;
                }
              } //direction

              container high-wmark {
                description
                    "Configure the high and low watermarks";
                leaf high-watermark {
                  type uint32 {
                    range "1..4294967295";
                  }
                  default 4294967295;
                  description
                      "[1..4294967295] - Default: 4294967295";
                } //high-watermark

                leaf low-wmark {
                  type uint32 {
                    range "0..4294967294";
                  }
                  default 0;
                  description
                      "[0..4294967294] - Default: 0";
                } //low-wmark

              } //container high-wmark

            } //list tcp-validate

          } //container threshold-crossing-alert

        } //container statistics

        list tcp-optimizer {
          key "tcp-optimizer-name";
          description
              "Configure a TCP optimizer";
          leaf tcp-optimizer-name {
            type string {
              length "1..32";
            }
          } //tcp-optimizer-name

          container dack-timeout {
            description
                "Configure a delayed acknowledgment timeout for the TCP optimizer";
            leaf dack-timeout {
              type uint32 {
              }
              description
                  "[200..200] ms";
            } //dack-timeout

          } //container dack-timeout

          container description {
            description
                "Configure a description of the TCP optimizer";
            leaf description-string {
              type string {
                length "1..80";
              }
            } //description-string

          } //container description

          container init-cwnd-size {
            description
                "Configure the initial congestion window of the TCP optimizer";
            leaf init-cwnd-size {
              type uint32 {
                range "1..256";
              }
              default 8;
              description
                  "[1..256] MSS - Default: 8";
            } //init-cwnd-size

          } //container init-cwnd-size

          container init-ss-threshold {
            description
                "Configure the initial slow-start threshold of the TCP optimizer";
            leaf init-ss-threshold {
              type string;
              description
                  "Attribute init-ss-threshold for init-ss-threshold";
            } //init-ss-threshold

          } //container init-ss-threshold

          container network-rtt-threshold {
            description
                "Configure the network round trip time threshold of the TCP optimizer";
            leaf network-rtt-threshold {
              type uint32 {
                range "1..100";
              }
              description
                  "[1..100] ms";
            } //network-rtt-threshold

          } //container network-rtt-threshold

          container tcp-stack {
            description
                "Configure the TCP stack type of the TCP optimizer";
            leaf tcp-stack-type {
              type enumeration {
                enum tcp-westwood;
                enum tcp-illinois;
                enum tcp-new-reno;
                enum tcp-bbr;
              }
              default "tcp-westwood";
              description
                  "tcp-westwood|tcp-illinois|tcp-new-reno|tcp-bbr - Default: tcp-westwood";
            } //tcp-stack-type

          } //container tcp-stack

        } //list tcp-optimizer

        list tcp-validate {
          key "tcp-validate-name";
          description
              "Configure a TCP validation template";
          leaf tcp-validate-name {
            type string {
              length "1..32";
            }
          } //tcp-validate-name

          container description {
            description
                "Configure a description of the TCP validate";
            leaf description-string {
              type string {
                length "1..80";
              }
            } //description-string

          } //container description

          container event-log {
            description
                "Configure an event log for traffic dropped by the TCP validate";
            leaf event-log-name {
              type string {
                length "1..32";
              }
            } //event-log-name

            leaf all {
              type boolean;
              description
                  "keyword - log all dropped traffic";
            } //all

          } //container event-log

          leaf strict {
            type boolean;
            description
                "Enable/disable strict checking of TCP traffic";
          }

        } //list tcp-validate

        container tethering-detection {
          description
              "Configure tethering detection";
          leaf shutdown {
            type boolean;
            description
                "Administratively enable/disable AA support for tethering detection";
          }

          container single-device {
            list expected-ttl {
              key "ttl-value";
              description
                  "Configure a expected TTL";
              leaf ttl-value {
                type uint32 {
                  range "1..255";
                }
              } //ttl-value

            } //list expected-ttl

          } //container single-device

        } //container tethering-detection

        list transit-ip-policy {
          key "ip-policy-id";
          description
              "Configure IP transit policy";
          leaf ip-policy-id {
            type uint32 {
              range "1..65535";
            }
          } //ip-policy-id

          container def-app-profile {
            description
                "Configure a default application profile";
            leaf app-profile-name {
              type string {
                length "1..32";
              }
            } //app-profile-name

          } //container def-app-profile

          container description {
            description
                "Configure a transit IP policy description";
            leaf description-string {
              type string {
                length "1..80";
              }
            } //description-string

          } //container description

          leaf detect-seen-ip {
            type boolean;
            description
                "Enable detection of transit subscribers based on IP address";
          }

          container ipv6-address-prefix-length {
            description
                "Configure a transit IP policy IPv6 address prefix length";
            leaf IPv6-prefix-length {
              type uint32 {
                range "32..64";
              }
            } //IPv6-prefix-length

          } //container ipv6-address-prefix-length

          container sub-ident-policy {
            description
                "Configure subscriber identification policy for the IP transit policy";
            leaf sub-ident-policy-name {
              type string {
                length "1..32";
              }
            } //sub-ident-policy-name

          } //container sub-ident-policy

          container dhcp {
            description
                "Configure DHCP parameters for the IP transit policy";
            leaf shutdown {
              type boolean;
              description
                  "Administratively enable/disable learning dynamic transits via DHCP";
            }

          } //container dhcp

          container diameter {
            description
                "Configure Diameter parameters for the IP transit policy";
            container application-policy {
              description
                  "Configure Diameter application-policy for the IP transit policy";
              leaf application-policy-name {
                type string {
                  length "1..32";
                }
              } //application-policy-name

            } //container application-policy

            leaf shutdown {
              type boolean;
              description
                  "Administratively enable/disable learning dynamic transits via Diameter";
            }

          } //container diameter

          container radius {
            description
                "Configure RADIUS parameters for the IP transit policy";
            container authentication-policy {
              description
                  "Configure RADIUS authentication-policy for the IP transit policy";
              leaf name {
                type string {
                  length "1..32";
                }
              } //name

            } //container authentication-policy

            container seen-ip-radius-acct-policy {
              description
                  "Configure the RADIUS accounting policy to be used by Seen IP";
              leaf rad-acct-plcy-name {
                type string {
                  length "1..32";
                }
              } //rad-acct-plcy-name

            } //container seen-ip-radius-acct-policy

            leaf shutdown {
              type boolean;
              description
                  "Administratively enable/disable learning dynamic transits via RADIUS";
            }

          } //container radius

          list static-aa-sub {
            key "transit-aasub-name";
            description
                "Configure static transit subscriber information";
            leaf transit-aasub-name {
              type string {
                length "1..32";
              }
            } //transit-aasub-name

            leaf app-profile {
              type string {
                length "1..32";
              }
            } //app-profile

            list ip {
              key "ip-address-mask";
              description
                  "Configure static transit subscriber ip-address";
              leaf ip-address-mask {
                type string;
                description
                    "ipv4-address - a.b.c.d 
                     ipv6-address - x:x:x:x:x:x:x:x/prefix-length 
                     x:x:x:x:x:x:d.d.d.d 
                     x - [0..FFFF]H 
                     d - [0..255]D 
                     prefix-length [1..128]";
              } //ip-address-mask

            } //list ip

          } //list static-aa-sub

          container transit-auto-create {
            description
                "Configure auto creation of transit subscriber parameters for the IP transit 
                 policy";
            leaf shutdown {
              type boolean;
              description
                  "Administratively enable/disable creation of dynamic transits automatically";
            }

          } //container transit-auto-create

        } //list transit-ip-policy

        list transit-prefix-policy {
          key "prefix-policy-id";
          description
              "Configure prefix transit policy";
          leaf prefix-policy-id {
            type uint32 {
              range "1..65535";
            }
          } //prefix-policy-id

          container description {
            description
                "Configure a transit prefix policy description";
            leaf description-string {
              type string {
                length "1..80";
              }
            } //description-string

          } //container description

          list static-aa-sub {
            key "transit-aasub-name";
            description
                "Configure a static transit prefix subscriber";
            leaf transit-aasub-name {
              type string {
                length "1..32";
              }
            } //transit-aasub-name

            leaf app-profile {
              type string {
                length "1..32";
              }
            } //app-profile

          } //list static-aa-sub

          list static-remote-aa-sub {
            key "transit-aasub-name";
            description
                "Configure a static remote transit prefix subscriber";
            leaf transit-aasub-name {
              type string {
                length "1..32";
              }
            } //transit-aasub-name

            leaf app-profile {
              type string {
                length "1..32";
              }
            } //app-profile

          } //list static-remote-aa-sub

          list entry {
            key "entry-id";
            description
                "Configure a transit prefix policy entry";
            leaf entry-id {
              type uint32 {
                range "1..4294967295";
              }
            } //entry-id

            container aa-sub {
              description
                  "Configure a transit prefix policy entry subscriber";
              leaf transit-aasub-name {
                type string {
                  length "1..32";
                }
              } //transit-aasub-name

            } //container aa-sub

            container match {
              description
                  "Configure transit prefix policy entry match criteria";
              container aa-sub-ip {
                description
                    "Configure a transit prefix subscriber ip address prefix";
                leaf ip-address-mask {
                  type string;
                  description
                      "Attribute ip-address[/mask] for aa-sub-ip";
                } //ip-address-mask

              } //container aa-sub-ip

              container network-ip {
                description
                    "Configure a transit prefix network ip address prefix";
                leaf ip-address-mask {
                  type string;
                  description
                      "Attribute ip-address[/mask] for network-ip";
                } //ip-address-mask

              } //container network-ip

            } //container match

          } //list entry

        } //list transit-prefix-policy

        list url-filter {
          key "url-filter-name";
          description
              "Configure the URL filter";
          leaf url-filter-name {
            type string {
            }
          } //url-filter-name

          container default-action {
            description
                "Configure the default action to take when the ICAP server and local-filtering 
                 are out of service";
            leaf allow {
              type boolean;
              description
                  "allow";
            } //allow

            leaf block-all {
              type boolean;
              description
                  "block-all";
            } //block-all

            leaf block-http-redirect {
              type string {
                length "1..32";
              }
              description
                  "http-redirect-name";
            } //block-http-redirect

          } //container default-action

          container description {
            description
                "Configure the URL filter's description";
            leaf description-string {
              type string {
                length "1..80";
              }
            } //description-string

          } //container description

          container http-redirect {
            description
                "Configure the HTTP Redirect";
            leaf http-redirect-name {
              type string {
                length "1..32";
              }
            } //http-redirect-name

          } //container http-redirect

          container http-request-filtering {
            description
                "Configure the level of URL filtering for HTTP requests in a TCP session";
            leaf all---first {
              type enumeration {
                enum all;
                enum first;
              }
              default "all";
              description
                  "all | first - Default: all";
            } //all---first

          } //container http-request-filtering

          leaf shutdown {
            type boolean;
            description
                "Administratively enable/disable a URL filter";
          }

          container icap {
            description
                "Configure url-filter ICAP";
            container custom-x-header {
              description
                  "Configure the ICAP custom X-Header";
              leaf custom-x-header-name {
                type string {
                  length "1..32";
                }
              } //custom-x-header-name

            } //container custom-x-header

            container vlan-id {
              description
                  "Configure the service port vlan-id";
              leaf service-port-vlan-id {
                type uint32 {
                  range "1..4094";
                }
              } //service-port-vlan-id

            } //container vlan-id

            list server {
              key "ip-address-port";
              description
                  "Configure the ICAP Server";
              leaf ip-address-port {
                type string;
                description
                    "ip-address - a.b.c.d 
                     port - [1..65535]";
              } //ip-address-port

              container description {
                description
                    "Configure the description for this ICAP server";
                leaf description-string {
                  type string {
                    length "1..80";
                  }
                } //description-string

              } //container description

              leaf shutdown {
                type boolean;
                description
                    "Administratively enable/disable an ICAP server";
              }

            } //list server

          } //container icap

          container local-filtering {
            description
                "Configure url-filter local-filtering";
            list url-list {
              key "url-list-name";
              description
                  "Configure a url-filter url-list";
              leaf url-list-name {
                type string {
                  length "1..32";
                }
              } //url-list-name

            } //list url-list

          } //container local-filtering

          container web-service {
            description
                "Configure url-filter web-service";
            container classifier {
              description
                  "Configure the web-service classifier";
              leaf classifier {
                type enumeration {
                  enum web-service-1;
                  enum web-service-2;
                }
              } //classifier

              leaf category-set-id {
                type uint32 {
                  range "0..65535";
                }
                description
                    "Attribute category-set for classifier";
              } //category-set-id

            } //container classifier

            container default-profile {
              description
                  "Configure the default profile for web-service";
              leaf profile-name {
                type string {
                }
              } //profile-name

            } //container default-profile

            container dns-server {
              description
                  "Configure the dns-server for web-service";
              leaf ip-address {
                type string;
                description
                    "Attribute ip-address for dns-server";
              } //ip-address

            } //container dns-server

            container fqdn {
              description
                  "Configure the fully qualified domain name for the web-service";
              leaf fully-qualified-domain-name {
                type string {
                  length "1..255";
                }
              } //fully-qualified-domain-name

            } //container fqdn

            container vlan-id {
              description
                  "Configure vlan-id for web-service";
              leaf vlan-id {
                type uint32 {
                  range "1..4094";
                }
              } //vlan-id

            } //container vlan-id

            list profile {
              key "profile-name";
              description
                  "Configure web-service profiles";
              leaf profile-name {
                type string {
                }
              } //profile-name

              list category {
                key "category";
                description
                    "Configure a profile category";
                leaf category {
                  type string {
                  }
                } //category

                leaf block {
                  type boolean;
                } //block

              } //list category

              container description {
                description
                    "Configure the description for this profile";
                leaf description {
                  type string {
                  }
                } //description

              } //container description

            } //list profile

          } //container web-service

        } //list url-filter

        list url-list {
          key "url-list-name";
          description
              "Configure the URL list";
          leaf url-list-name {
            type string {
              length "1..32";
            }
          } //url-list-name

          container decrypt-key {
            description
                "Configure the URL list decrypt-key";
            leaf key-hash-key-hash2-key-custom-key {
              type string {
                length "1..500";
              }
              description
                  "key - [64 chars max] 
                   hash-key - hashed key 
                   hash2-key - hashed key 
                   custom-key - hashed key";
            } //key-hash-key-hash2-key-custom-key

            leaf hash-hash2-custom {
              type enumeration {
                enum hash;
                enum hash2;
                enum custom;
              }
              description
                  "keywords - hashing scheme used in the hashed key";
            } //hash-hash2-custom

          } //container decrypt-key

          container description {
            description
                "Configure a description of the URL list";
            leaf description-string {
              type string {
                length "1..80";
              }
            } //description-string

          } //container description

          container file {
            description
                "Configure the URL list file";
            leaf file-url {
              type string {
              }
              description
                  "Attribute file-url for file";
            } //file-url

          } //container file

          leaf shutdown {
            type boolean;
            description
                "Administratively enable/disable a URL list";
          }

          container size {
            description
                "Configure the URL list size limit";
            leaf url-list-size {
              type enumeration {
                enum standard;
                enum extended;
              }
              default "standard";
              description
                  "[standard|extended] - Default : standard";
            } //url-list-size

          } //container size

        } //list url-list

        container wap1x {
          description
              "Configure Wireless Application Protocol (WAP) 1.X parameters";
          leaf shutdown {
            type boolean;
            description
                "Administratively enable/disable AA support for Wireless Application Protocol 
                 (WAP) 1.X";
          }

        } //container wap1x

      } //list group

      container protocol {
        description
            "Configure shutdown of protocols system-wide";
        leaf protocol-name {
          type string {
            length "1..32";
          }
          description
              "shutable protocol name";
        } //protocol-name

        leaf shutdown {
          type boolean;
          description
              "Administratively enable/disable a protocol";
        }

      } //container protocol

      list radius-accounting-policy {
        key "rad-acct-plcy-name";
        description
            "Configure a RADIUS accounting policy";
        leaf rad-acct-plcy-name {
          type string {
            length "1..32";
          }
        } //rad-acct-plcy-name

        container description {
          description
              "Configure a RADIUS accounting policy description";
          leaf description-string {
            type string {
              length "1..80";
            }
          } //description-string

        } //container description

        container interim-update-interval {
          description
              "Configure the interim update interval";
          leaf minutes {
            type uint32 {
              range "5..1080";
            }
          } //minutes

        } //container interim-update-interval

        container significant-change {
          description
              "Configure the significant change required to generate a RADIUS accounting 
               request";
          leaf delta {
            type uint32 {
            }
          } //delta

        } //container significant-change

        container radius-accounting-server {
          description
              "Configure RADIUS accounting servers";
          container access-algorithm {
            description
                "Configure the algorithm used to access the set of RADIUS servers";
            leaf direct-round-robin {
              type enumeration {
                enum direct;
                enum round-robin;
              }
              default "direct";
              description
                  "[direct|round-robin] - Default: direct";
            } //direct-round-robin

          } //container access-algorithm

          container retry {
            description
                "Number of retries for contacting the RADIUS server";
            leaf count {
              type uint32 {
                range "1..10";
              }
              default 3;
              description
                  "[1..10] - Default: 3";
            } //count

          } //container retry

          container router {
            description
                "Configure the routing instance";
            leaf router-instance {
              type string {
                length "1..32";
              }
              default "Base";
              description
                  "Attribute router-instance for router";
            } //router-instance

            leaf service-name {
              type string;
            } //service-name

          } //container router

          list server {
            key "server-index";
            description
                "Add/remove a RADIUS server";
            leaf server-index {
              type uint32 {
                range "1..5";
              }
            } //server-index

            leaf address {
              type inet:ip-address;
            } //address

            leaf secret {
              type string {
                length "1..500";
              }
              description
                  "secret-key - [20 chars max] 
                   hash-key 
                   hash2-key 
                   custom-key";
            } //secret

            leaf hash-hash2-custom {
              type enumeration {
                enum hash;
                enum hash2;
                enum custom;
              }
              description
                  "keywords - specify hashing scheme";
            } //hash-hash2-custom

            leaf port {
              type uint16 {
                range "1..65535";
              }
            } //port

          } //list server

          container source-address {
            description
                "Source address of the RADIUS message";
            leaf ip-address {
              type inet:ip-address;
            } //ip-address

          } //container source-address

          container timeout {
            description
                "Timeout for a response from the RADIUS server";
            leaf seconds {
              type uint32 {
                range "1..90";
              }
              default 5;
              description
                  "[1..90] - Default: 5";
            } //seconds

          } //container timeout

        } //container radius-accounting-server

      } //list radius-accounting-policy

    } //container application-assurance

  } //grouping alu-conf-aa-r13

} //module  alu-conf-aa-r13
