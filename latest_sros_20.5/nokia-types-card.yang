module nokia-types-card {

    yang-version "1.1";

    namespace "urn:nokia.com:sros:ns:yang:sr:types-card";

    prefix "types-card";

    import nokia-sros-yang-extensions     { prefix "sros-ext"; }


    sros-ext:sros-major-release "rel20";

    organization "Nokia";

    contact
        "Nokia SR OS Support
         Web: <http://www.nokia.com>";

    description
        "Common card types data types used in the SR OS management system.

         Copyright 2016 Nokia. All rights reserved. Reproduction of this document
         is authorized on the condition that the foregoing copyright notice is included.

         This nokia-types-card YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";

    revision "2020-03-30";

    typedef iom-card-slot {
        type uint32 {
            range "1..20";
        }
        description "An I/O Module (IOM) card slot.";
    }

    typedef cpm-card-slot {
        type string {
            length "1";
            pattern "[A-D]" {
                error-message "only values A to D are allowed";
            }
        }
        description "A Control Plane Module (CPM) card slot.";
    }

    typedef slot-mda {
        type string;
        description
            "A Nokia SROS series manufactured hardware component, such as
             an IOM, CPM, Fabric or MDA card";
    }

    typedef sros-cpm-type {
        type enumeration {
            enum "cpm-x20"                      { value 36; }
            enum "cpm-v"                        { value 44; }
            enum "cpm-x16"                      { value 48; }
            enum "cpm5"                         { value 54; }
            enum "cpm-a"                        { value 55; }
            enum "cpm-e"                        { value 64; }
            enum "cpm-sar-hm"                   { value 71; }
            enum "cpm-sar-hmc"                  { value 74; }
            enum "cpm-ixr-e-gnss"               { value 75; }
            enum "cpm-s"                        { value 76; }
            enum "cpiom-ixr-r6"                 { value 82; }
            enum "cpm-ixr"                      { value 83; }
            enum "cpm-1"                        { value 87; }
            enum "cpm-ixr-s"                    { value 90; }
            enum "cpm-1s"                       { value 93; }
            enum "cpm-2s"                       { value 96; }
            enum "cpm-ixr-e"                    { value 98; }
            enum "cpm-ixr-r4"                   { value 104; }
        }
        description "Specifies an SR OS series Control Plane Module type.";
    }

    typedef sros-cpm-type-state {
        type enumeration {
            enum "unknown"                      { value 0; }
            enum "unassigned"                   { value 1; }
            enum "cpm-x20"                      { value 36; }
            enum "cpm-v"                        { value 44; }
            enum "cpm-x16"                      { value 48; }
            enum "cpm5"                         { value 54; }
            enum "cpm-a"                        { value 55; }
            enum "cpm-e"                        { value 64; }
            enum "cpm-sar-hm"                   { value 71; }
            enum "cpm-sar-hmc"                  { value 74; }
            enum "cpm-ixr-e-gnss"               { value 75; }
            enum "cpm-s"                        { value 76; }
            enum "cpiom-ixr-r6"                 { value 82; }
            enum "cpm-ixr"                      { value 83; }
            enum "cpm-1"                        { value 87; }
            enum "cpm-ixr-s"                    { value 90; }
            enum "cpm-1s"                       { value 93; }
            enum "cpm-2s"                       { value 96; }
            enum "cpm-ixr-e"                    { value 98; }
            enum "cpm-ixr-r4"                   { value 104; }
        }
        description "Specifies an SR OS series Control Plane Module type.";
    }

    typedef sros-iom-type {
        type enumeration {
            enum "iom3-xp"                      { value 14; }
            enum "imm48-1gb-sfp"                { value 16; }
            enum "imm48-1gb-tx"                 { value 17; }
            enum "imm8-10gb-xfp"                { value 18; }
            enum "imm4-10gb-xfp"                { value 19; }
            enum "imm5-10gb-xfp"                { value 25; }
            enum "imm1-100gb-cfp"               { value 32; }
            enum "imm12-10gb-sf+"               { value 33; }
            enum "iom3-xp-b"                    { value 35; }
            enum "xcm-x20"                      { value 37; }
            enum "imm48-1gb-sfp-b"              { value 38; }
            enum "imm3-40gb-qsfp"               { value 43; }
            enum "imm40-10gb-sfp"               { value 46; }
            enum "xcm-x16"                      { value 49; }
            enum "imm4-100gb-cxp"               { value 50; }
            enum "iom3-xp-c"                    { value 51; }
            enum "iom4-e"                       { value 56; }
            enum "iom-a"                        { value 57; }
            enum "xcm-x16w"                     { value 58; }
            enum "imm-1pac-fp3"                 { value 59; }
            enum "imm-2pac-fp3"                 { value 60; }
            enum "iom4-e-hs"                    { value 62; }
            enum "imm48-1gb-sfp-c"              { value 63; }
            enum "imm4-100gb-cfp4"              { value 65; }
            enum "iom-e"                        { value 66; }
            enum "iom-v"                        { value 67; }
            enum "iom4-e-b"                     { value 68; }
            enum "iom-sar-hm"                   { value 72; }
            enum "xcm2-x20"                     { value 77; }
            enum "iom-1"                        { value 78; }
            enum "xcm-14s"                      { value 79; }
            enum "imm40-10gb-sfp-ptp"           { value 80; }
            enum "iom-ixr-r6"                   { value 81; }
            enum "imm36-100g-qsfp28"            { value 85; }
            enum "imm48-sfp+2-qsfp28"           { value 86; }
            enum "iom5-e"                       { value 88; }
            enum "xcm-7s"                       { value 89; }
            enum "imm48-sfp++6-qsfp28"          { value 92; }
            enum "xcm-1s"                       { value 94; }
            enum "xcm-2s"                       { value 97; }
            enum "imm24-sfp++8-sfp28+2-qsfp28"  { value 99; }
            enum "iom-sar-hmc"                  { value 100; }
            enum "imm14-10g-sfp++4-1g-tx"       { value 101; }
            enum "iom-ixr-r4"                   { value 105; }
        }
        description "Specifies an SR OS series I/O Module type.";
    }

    typedef sros-iom-type-state {
        type enumeration {
            enum "unknown"                      { value 0; }
            enum "unassigned"                   { value 1; }
            enum "iom3-xp"                      { value 14; }
            enum "imm48-1gb-sfp"                { value 16; }
            enum "imm48-1gb-tx"                 { value 17; }
            enum "imm8-10gb-xfp"                { value 18; }
            enum "imm4-10gb-xfp"                { value 19; }
            enum "imm5-10gb-xfp"                { value 25; }
            enum "imm1-100gb-cfp"               { value 32; }
            enum "imm12-10gb-sf+"               { value 33; }
            enum "iom3-xp-b"                    { value 35; }
            enum "xcm-x20"                      { value 37; }
            enum "imm48-1gb-sfp-b"              { value 38; }
            enum "imm3-40gb-qsfp"               { value 43; }
            enum "imm40-10gb-sfp"               { value 46; }
            enum "xcm-x16"                      { value 49; }
            enum "imm4-100gb-cxp"               { value 50; }
            enum "iom3-xp-c"                    { value 51; }
            enum "iom4-e"                       { value 56; }
            enum "iom-a"                        { value 57; }
            enum "xcm-x16w"                     { value 58; }
            enum "imm-1pac-fp3"                 { value 59; }
            enum "imm-2pac-fp3"                 { value 60; }
            enum "iom4-e-hs"                    { value 62; }
            enum "imm48-1gb-sfp-c"              { value 63; }
            enum "imm4-100gb-cfp4"              { value 65; }
            enum "iom-e"                        { value 66; }
            enum "iom-v"                        { value 67; }
            enum "iom4-e-b"                     { value 68; }
            enum "iom-sar-hm"                   { value 72; }
            enum "xcm2-x20"                     { value 77; }
            enum "iom-1"                        { value 78; }
            enum "xcm-14s"                      { value 79; }
            enum "imm40-10gb-sfp-ptp"           { value 80; }
            enum "iom-ixr-r6"                   { value 81; }
            enum "imm36-100g-qsfp28"            { value 85; }
            enum "imm48-sfp+2-qsfp28"           { value 86; }
            enum "iom5-e"                       { value 88; }
            enum "xcm-7s"                       { value 89; }
            enum "imm48-sfp++6-qsfp28"          { value 92; }
            enum "xcm-1s"                       { value 94; }
            enum "xcm-2s"                       { value 97; }
            enum "imm24-sfp++8-sfp28+2-qsfp28"  { value 99; }
            enum "iom-sar-hmc"                  { value 100; }
            enum "imm14-10g-sfp++4-1g-tx"       { value 101; }
            enum "iom-ixr-r4"                   { value 105; }
        }
        description "Specifies an SR OS series I/O Module type.";
    }

    typedef sros-iom-level {
        type enumeration {
            enum "unrestricted"                 { value 1; }
            enum "he"                           { value 2; }
            enum "er"                           { value 3; }
            enum "cr"                           { value 4; }
            enum "he1200g+"                     { value 5; }
            enum "er1200g+"                     { value 6; }
            enum "cr1200g+"                     { value 7; }
            enum "he400g"                       { value 8; }
            enum "er400g"                       { value 9; }
            enum "cr400g"                       { value 10; }
            enum "he400g+"                      { value 11; }
            enum "er400g+"                      { value 12; }
            enum "cr400g+"                      { value 13; }
            enum "he800g+"                      { value 14; }
            enum "er800g+"                      { value 15; }
            enum "cr800g+"                      { value 16; }
        }
        description "Specifies an SR OS series I/O Module level.";
    }

    typedef sros-iom-level-state {
        type enumeration {
            enum "unknown"                      { value 0; }
            enum "unrestricted"                 { value 1; }
            enum "he"                           { value 2; }
            enum "er"                           { value 3; }
            enum "cr"                           { value 4; }
            enum "he1200g+"                     { value 5; }
            enum "er1200g+"                     { value 6; }
            enum "cr1200g+"                     { value 7; }
            enum "he400g"                       { value 8; }
            enum "er400g"                       { value 9; }
            enum "cr400g"                       { value 10; }
            enum "he400g+"                      { value 11; }
            enum "er400g+"                      { value 12; }
            enum "cr400g+"                      { value 13; }
            enum "he800g+"                      { value 14; }
            enum "er800g+"                      { value 15; }
            enum "cr800g+"                      { value 16; }
        }
        description "Indicates an SR OS series I/O Module level.";
    }

    typedef sros-iom-level-upgrade-path {
        type enumeration {
            enum "cr-er"                        { value 1; }
            enum "er-he"                        { value 2; }
            enum "cr400g-cr1200g+"              { value 3; }
            enum "er400g-er1200g+"              { value 4; }
            enum "he400g-he1200g+"              { value 5; }
            enum "cr-er1200g+"                  { value 6; }
            enum "er-he1200g+"                  { value 7; }
            enum "cr-er400g+"                   { value 8; }
            enum "er-he400g+"                   { value 9; }
            enum "cr-er800g+"                   { value 10; }
            enum "er-he800g+"                   { value 11; }
            enum "cr400g-cr800g+"               { value 12; }
            enum "er400g-er800g+"               { value 13; }
            enum "he400g-he800g+"               { value 14; }
            enum "cr800g-cr1200g+"              { value 15; }
            enum "er800g-er1200g+"              { value 16; }
            enum "he800g-he1200g+"              { value 17; }
        }
        description "Specifies an SR OS series I/O Module level upgrade path.";
    }

    typedef card-slot-bitmap {
        type bits {
            bit slot1                          { position 0; }
            bit slot2                          { position 1; }
            bit slot3                          { position 2; }
            bit slot4                          { position 3; }
            bit slot5                          { position 4; }
            bit slot6                          { position 5; }
            bit slot7                          { position 6; }
            bit slot8                          { position 7; }
            bit slot9                          { position 8; }
            bit slot10                         { position 9; }
            bit slot11                         { position 10; }
            bit slot12                         { position 11; }
            bit slot13                         { position 12; }
            bit slot14                         { position 13; }
            bit slot15                         { position 14; }
            bit slot16                         { position 15; }
            bit slot17                         { position 16; }
            bit slot18                         { position 17; }
            bit slot19                         { position 18; }
            bit slot20                         { position 19; }
            bit slot21                         { position 20; }
            bit slot22                         { position 21; }
            bit slot23                         { position 22; }
            bit slot24                         { position 23; }
        }
        description "Specifies a bitmap of card slots. A set bit indicates the slot is in use.";
    }

    typedef sros-mda-type {
        type enumeration {
            enum "m4-choc3-as-sfp"              { value 28; }
            enum "m10-1gb+1-10gb"               { value 33; }
            enum "isa-tunnel"                   { value 34; }
            enum "m1-choc12-as-sfp"             { value 39; }
            enum "m12-chds3-as"                 { value 40; }
            enum "m4-chds3-as"                  { value 41; }
            enum "isa-aa"                       { value 42; }
            enum "m4-choc3-ces-sfp"             { value 45; }
            enum "m1-choc3-ces-sfp"             { value 46; }
            enum "x12-400g-qsfpdd"              { value 47; }
            enum "x6-200g-cfp2-dco"             { value 48; }
            enum "m4-10gb-xp-xfp"               { value 49; }
            enum "m2-10gb-xp-xfp"               { value 50; }
            enum "m1-10gb-xp-xfp"               { value 54; }
            enum "m10-1gb-xp-sfp"               { value 55; }
            enum "m20-1gb-xp-sfp"               { value 56; }
            enum "m20-1gb-xp-tx"                { value 57; }
            enum "m1-choc12-ces-sfp"            { value 58; }
            enum "imm24-1gb-xp-sfp"             { value 59; }
            enum "imm24-1gb-xp-tx"              { value 60; }
            enum "imm4-10gb-xp-xfp"             { value 61; }
            enum "imm2-10gb-xp-xfp"             { value 62; }
            enum "isa-video"                    { value 63; }
            enum "imm5-10gb-xp-xfp"             { value 68; }
            enum "m48-1gb-xp-tx"                { value 69; }
            enum "isa-bb"                       { value 70; }
            enum "isa-ms"                       { value 76; }
            enum "isa-ms-e"                     { value 77; }
            enum "imm1-100gb-xp-cfp"            { value 78; }
            enum "imm12-10gb-xp-sf+"            { value 79; }
            enum "vsm-cca-xp"                   { value 81; }
            enum "imm3-40gb-xp-qsfp"            { value 85; }
            enum "m10-1gb-hs-sfp-b"             { value 88; }
            enum "m16-oc12/3-sfp-b"             { value 89; }
            enum "m4-oc48-sfp-b"                { value 94; }
            enum "m1-10gb-hs-xfp-b"             { value 95; }
            enum "cx20-10g-sfp"                 { value 96; }
            enum "cx2-100g-cfp"                 { value 97; }
            enum "p10-10g-sfp"                  { value 98; }
            enum "p1-100g-cfp"                  { value 99; }
            enum "m2-oc192-xp-xfp"              { value 102; }
            enum "m12-1gb-xp-sfp"               { value 103; }
            enum "m12-1gb+2-10gb-xp"            { value 105; }
            enum "p3-40g-qsfp"                  { value 106; }
            enum "p6-10g-sfp"                   { value 108; }
            enum "x40-10g-sfp"                  { value 111; }
            enum "m40-10g-sfp"                  { value 112; }
            enum "x4-100g-cxp"                  { value 113; }
            enum "cx6-40g-qsfp"                 { value 114; }
            enum "m4-100g-cxp"                  { value 115; }
            enum "p20-1gb-sfp"                  { value 116; }
            enum "s36-100gb-qsfp28-3.6t"        { value 117; }
            enum "p-isa2-ms"                    { value 118; }
            enum "p-isa2-ms-e"                  { value 119; }
            enum "isa2-aa"                      { value 120; }
            enum "isa2-tunnel"                  { value 121; }
            enum "isa2-bb"                      { value 122; }
            enum "x4-100g-cfp2"                 { value 123; }
            enum "cx72-1g-csfp"                 { value 124; }
            enum "p160-1gb-csfp"                { value 125; }
            enum "maxp1-100gb-cfp"              { value 126; }
            enum "ma4-10gb-sfp+"                { value 127; }
            enum "maxp10-10gb-sfp+"             { value 129; }
            enum "me10-10gb-sfp+"               { value 130; }
            enum "ma2-10gb-sfp+12-1gb-sfp"      { value 132; }
            enum "maxp6-10gb-sfp+1-40gb-qsfp+"  { value 133; }
            enum "ma44-1gb-csfp"                { value 134; }
            enum "ma20-1gb-tx"                  { value 135; }
            enum "me1-100gb-cfp2"               { value 137; }
            enum "m4-100g-cfp4"                 { value 139; }
            enum "p1-100g-tun-b"                { value 140; }
            enum "maxp1-100gb-cfp2"             { value 141; }
            enum "maxp1-100gb-cfp4"             { value 142; }
            enum "isa-ms-v"                     { value 148; }
            enum "isa-aa-v"                     { value 149; }
            enum "isa-tunnel-v"                 { value 150; }
            enum "isa-bb-v"                     { value 151; }
            enum "m20-v"                        { value 152; }
            enum "me-isa2-ms"                   { value 153; }
            enum "me-isa2-ms-e"                 { value 154; }
            enum "me40-1gb-csfp"                { value 158; }
            enum "me2-100gb-cfp4"               { value 160; }
            enum "me6-10gb-sfp+"                { value 161; }
            enum "isa2-video"                   { value 162; }
            enum "me2-100gb-qsfp28"             { value 163; }
            enum "i6-10/100eth-tx"              { value 164; }
            enum "x2-100g-tun"                  { value 165; }
            enum "i2-sdi"                       { value 166; }
            enum "i2-cellular"                  { value 167; }
            enum "me12-10/1gb-sfp+"             { value 168; }
            enum "me16-25gb-sfp28+2-100gb-qsfp28" { value 169; }
            enum "me6-100gb-qsfp28"             { value 170; }
            enum "x6-400g-cfp8"                 { value 172; }
            enum "me2-100gb-ms-qsfp28"          { value 173; }
            enum "s18-100gb-qsfp28"             { value 174; }
            enum "x40-10g-sfp-ptp"              { value 175; }
            enum "m40-10g-sfp-ptp"              { value 176; }
            enum "m36-100g-qsfp28"              { value 177; }
            enum "m48-sfp+2-qsfp28"             { value 178; }
            enum "m10-10g-sfp+"                 { value 180; }
            enum "m20-1g-csfp"                  { value 181; }
            enum "m6-10g-sfp++1-100g-qsfp28"    { value 183; }
            enum "me3-200gb-cfp2-dco"           { value 184; }
            enum "x24-100g-qsfp28"              { value 185; }
            enum "me12-100gb-qsfp28"            { value 186; }
            enum "i1-wlan"                      { value 187; }
            enum "s36-400gb-qsfpdd"             { value 188; }
            enum "m24-sfp++8-sfp28+2-qsfp28"    { value 189; }
            enum "s36-100gb-qsfp28"             { value 190; }
            enum "a32-chds1v2"                  { value 191; }
            enum "m48-sfp++6-qsfp28"            { value 196; }
            enum "maxp10-10/1gb-msec-sfp+"      { value 197; }
            enum "m4-10g-sfp++1-100g-cfp2"      { value 200; }
            enum "i3-10/100eth-tx"              { value 202; }
            enum "me3-400gb-qsfpdd"             { value 203; }
            enum "m14-10g-sfp++4-1g-tx"         { value 205; }
            enum "m6-10g-sfp++4-25g-sfp28"      { value 206; }
            enum "me6-400gb-qsfpdd"             { value 207; }
            enum "me8-10/25gb-sfp28"            { value 208; }
            enum "m10-1g-sfp+2-10g-sfp+"        { value 210; }
        }
        description "Specifies an SROS Media Dependent Adapter (MDA) type";
    }

    typedef sros-mda-type-state {
        type enumeration {
            enum "unknown"                      { value 0; }
            enum "unassigned"                   { value 1; }
            enum "m4-choc3-as-sfp"              { value 28; }
            enum "m10-1gb+1-10gb"               { value 33; }
            enum "isa-tunnel"                   { value 34; }
            enum "m1-choc12-as-sfp"             { value 39; }
            enum "m12-chds3-as"                 { value 40; }
            enum "m4-chds3-as"                  { value 41; }
            enum "isa-aa"                       { value 42; }
            enum "m4-choc3-ces-sfp"             { value 45; }
            enum "m1-choc3-ces-sfp"             { value 46; }
            enum "x12-400g-qsfpdd"              { value 47; }
            enum "x6-200g-cfp2-dco"             { value 48; }
            enum "m4-10gb-xp-xfp"               { value 49; }
            enum "m2-10gb-xp-xfp"               { value 50; }
            enum "m1-10gb-xp-xfp"               { value 54; }
            enum "m10-1gb-xp-sfp"               { value 55; }
            enum "m20-1gb-xp-sfp"               { value 56; }
            enum "m20-1gb-xp-tx"                { value 57; }
            enum "m1-choc12-ces-sfp"            { value 58; }
            enum "imm24-1gb-xp-sfp"             { value 59; }
            enum "imm24-1gb-xp-tx"              { value 60; }
            enum "imm4-10gb-xp-xfp"             { value 61; }
            enum "imm2-10gb-xp-xfp"             { value 62; }
            enum "isa-video"                    { value 63; }
            enum "imm5-10gb-xp-xfp"             { value 68; }
            enum "m48-1gb-xp-tx"                { value 69; }
            enum "isa-bb"                       { value 70; }
            enum "isa-ms"                       { value 76; }
            enum "isa-ms-e"                     { value 77; }
            enum "imm1-100gb-xp-cfp"            { value 78; }
            enum "imm12-10gb-xp-sf+"            { value 79; }
            enum "vsm-cca-xp"                   { value 81; }
            enum "imm3-40gb-xp-qsfp"            { value 85; }
            enum "m10-1gb-hs-sfp-b"             { value 88; }
            enum "m16-oc12/3-sfp-b"             { value 89; }
            enum "m4-oc48-sfp-b"                { value 94; }
            enum "m1-10gb-hs-xfp-b"             { value 95; }
            enum "cx20-10g-sfp"                 { value 96; }
            enum "cx2-100g-cfp"                 { value 97; }
            enum "p10-10g-sfp"                  { value 98; }
            enum "p1-100g-cfp"                  { value 99; }
            enum "m2-oc192-xp-xfp"              { value 102; }
            enum "m12-1gb-xp-sfp"               { value 103; }
            enum "m12-1gb+2-10gb-xp"            { value 105; }
            enum "p3-40g-qsfp"                  { value 106; }
            enum "p6-10g-sfp"                   { value 108; }
            enum "x40-10g-sfp"                  { value 111; }
            enum "m40-10g-sfp"                  { value 112; }
            enum "x4-100g-cxp"                  { value 113; }
            enum "cx6-40g-qsfp"                 { value 114; }
            enum "m4-100g-cxp"                  { value 115; }
            enum "p20-1gb-sfp"                  { value 116; }
            enum "s36-100gb-qsfp28-3.6t"        { value 117; }
            enum "p-isa2-ms"                    { value 118; }
            enum "p-isa2-ms-e"                  { value 119; }
            enum "isa2-aa"                      { value 120; }
            enum "isa2-tunnel"                  { value 121; }
            enum "isa2-bb"                      { value 122; }
            enum "x4-100g-cfp2"                 { value 123; }
            enum "cx72-1g-csfp"                 { value 124; }
            enum "p160-1gb-csfp"                { value 125; }
            enum "maxp1-100gb-cfp"              { value 126; }
            enum "ma4-10gb-sfp+"                { value 127; }
            enum "maxp10-10gb-sfp+"             { value 129; }
            enum "me10-10gb-sfp+"               { value 130; }
            enum "ma2-10gb-sfp+12-1gb-sfp"      { value 132; }
            enum "maxp6-10gb-sfp+1-40gb-qsfp+"  { value 133; }
            enum "ma44-1gb-csfp"                { value 134; }
            enum "ma20-1gb-tx"                  { value 135; }
            enum "me1-100gb-cfp2"               { value 137; }
            enum "m4-100g-cfp4"                 { value 139; }
            enum "p1-100g-tun-b"                { value 140; }
            enum "maxp1-100gb-cfp2"             { value 141; }
            enum "maxp1-100gb-cfp4"             { value 142; }
            enum "isa-ms-v"                     { value 148; }
            enum "isa-aa-v"                     { value 149; }
            enum "isa-tunnel-v"                 { value 150; }
            enum "isa-bb-v"                     { value 151; }
            enum "m20-v"                        { value 152; }
            enum "me-isa2-ms"                   { value 153; }
            enum "me-isa2-ms-e"                 { value 154; }
            enum "me40-1gb-csfp"                { value 158; }
            enum "me2-100gb-cfp4"               { value 160; }
            enum "me6-10gb-sfp+"                { value 161; }
            enum "isa2-video"                   { value 162; }
            enum "me2-100gb-qsfp28"             { value 163; }
            enum "i6-10/100eth-tx"              { value 164; }
            enum "x2-100g-tun"                  { value 165; }
            enum "i2-sdi"                       { value 166; }
            enum "i2-cellular"                  { value 167; }
            enum "me12-10/1gb-sfp+"             { value 168; }
            enum "me16-25gb-sfp28+2-100gb-qsfp28" { value 169; }
            enum "me6-100gb-qsfp28"             { value 170; }
            enum "x6-400g-cfp8"                 { value 172; }
            enum "me2-100gb-ms-qsfp28"          { value 173; }
            enum "s18-100gb-qsfp28"             { value 174; }
            enum "x40-10g-sfp-ptp"              { value 175; }
            enum "m40-10g-sfp-ptp"              { value 176; }
            enum "m36-100g-qsfp28"              { value 177; }
            enum "m48-sfp+2-qsfp28"             { value 178; }
            enum "m10-10g-sfp+"                 { value 180; }
            enum "m20-1g-csfp"                  { value 181; }
            enum "m6-10g-sfp++1-100g-qsfp28"    { value 183; }
            enum "me3-200gb-cfp2-dco"           { value 184; }
            enum "x24-100g-qsfp28"              { value 185; }
            enum "me12-100gb-qsfp28"            { value 186; }
            enum "i1-wlan"                      { value 187; }
            enum "s36-400gb-qsfpdd"             { value 188; }
            enum "m24-sfp++8-sfp28+2-qsfp28"    { value 189; }
            enum "s36-100gb-qsfp28"             { value 190; }
            enum "a32-chds1v2"                  { value 191; }
            enum "m48-sfp++6-qsfp28"            { value 196; }
            enum "maxp10-10/1gb-msec-sfp+"      { value 197; }
            enum "m4-10g-sfp++1-100g-cfp2"      { value 200; }
            enum "i3-10/100eth-tx"              { value 202; }
            enum "me3-400gb-qsfpdd"             { value 203; }
            enum "m14-10g-sfp++4-1g-tx"         { value 205; }
            enum "m6-10g-sfp++4-25g-sfp28"      { value 206; }
            enum "me6-400gb-qsfpdd"             { value 207; }
            enum "me8-10/25gb-sfp28"            { value 208; }
            enum "m10-1g-sfp+2-10g-sfp+"        { value 210; }
        }
        description "Specifies an SROS Media Dependent Adapter (MDA) type";
    }

    typedef sros-mda-level {
        type enumeration {
            enum "unrestricted"                 { value 1; }
            enum "he2400g"                      { value 2; }
            enum "he1600g"                      { value 3; }
            enum "he1200g"                      { value 4; }
            enum "er2400g"                      { value 5; }
            enum "er1600g"                      { value 6; }
            enum "er1200g"                      { value 7; }
            enum "cr2400g"                      { value 8; }
            enum "cr1600g"                      { value 9; }
            enum "cr1200g"                      { value 10; }
            enum "he2400g+"                     { value 11; }
            enum "er2400g+"                     { value 12; }
            enum "cr2400g+"                     { value 13; }
            enum "he3600g"                      { value 14; }
            enum "er3600g"                      { value 15; }
            enum "cr3600g"                      { value 16; }
            enum "he3600gdd"                    { value 17; }
            enum "er3600gdd"                    { value 18; }
            enum "cr3600gdd"                    { value 19; }
            enum "he4800g"                      { value 20; }
            enum "er4800g"                      { value 21; }
            enum "cr4800g"                      { value 22; }
            enum "he4800g+"                     { value 23; }
            enum "er4800g+"                     { value 24; }
            enum "cr4800g+"                     { value 25; }
            enum "he600g"                       { value 26; }
            enum "er600g"                       { value 27; }
            enum "cr600g"                       { value 28; }
            enum "he1200g+"                     { value 29; }
            enum "er1200g+"                     { value 30; }
            enum "cr1200g+"                     { value 31; }
            enum "he2400g+4t"                   { value 32; }
            enum "er2400g+4t"                   { value 33; }
            enum "cr2400g+4t"                   { value 34; }
        }
        description
            "Specifies an SROS Media Dependent Adapter (MDA)
             functional level";
    }

    typedef sros-mda-level-state {
        type enumeration {
            enum "unknown"                      { value 0; }
            enum "unrestricted"                 { value 1; }
            enum "he2400g"                      { value 2; }
            enum "he1600g"                      { value 3; }
            enum "he1200g"                      { value 4; }
            enum "er2400g"                      { value 5; }
            enum "er1600g"                      { value 6; }
            enum "er1200g"                      { value 7; }
            enum "cr2400g"                      { value 8; }
            enum "cr1600g"                      { value 9; }
            enum "cr1200g"                      { value 10; }
            enum "he2400g+"                     { value 11; }
            enum "er2400g+"                     { value 12; }
            enum "cr2400g+"                     { value 13; }
            enum "he3600g"                      { value 14; }
            enum "er3600g"                      { value 15; }
            enum "cr3600g"                      { value 16; }
            enum "he3600gdd"                    { value 17; }
            enum "er3600gdd"                    { value 18; }
            enum "cr3600gdd"                    { value 19; }
            enum "he4800g"                      { value 20; }
            enum "er4800g"                      { value 21; }
            enum "cr4800g"                      { value 22; }
            enum "he4800g+"                     { value 23; }
            enum "er4800g+"                     { value 24; }
            enum "cr4800g+"                     { value 25; }
            enum "he600g"                       { value 26; }
            enum "er600g"                       { value 27; }
            enum "cr600g"                       { value 28; }
            enum "he1200g+"                     { value 29; }
            enum "er1200g+"                     { value 30; }
            enum "cr1200g+"                     { value 31; }
            enum "he2400g+4t"                   { value 32; }
            enum "er2400g+4t"                   { value 33; }
            enum "cr2400g+4t"                   { value 34; }
        }
        description
            "Indicates an SROS Media Dependent Adapter (MDA)
             functional level";
    }

    typedef sros-mda-level-upgrade-path {
        type enumeration {
            enum "cr1200g-cr1600g"              { value 1; }
            enum "cr1600g-cr2400g"              { value 2; }
            enum "er1200g-er1600g"              { value 3; }
            enum "er1600g-er2400g"              { value 4; }
            enum "he1200g-he1600g"              { value 5; }
            enum "he1600g-he2400g"              { value 6; }
            enum "cr1200g-er1200g"              { value 7; }
            enum "er1200g-he1200g"              { value 8; }
            enum "cr1600g-er1600g"              { value 9; }
            enum "er1600g-he1600g"              { value 10; }
            enum "cr2400g-er2400g"              { value 11; }
            enum "er2400g-he2400g"              { value 12; }
            enum "any2400g-2400g+"              { value 13; }
            enum "cr3600g-cr4800g"              { value 14; }
            enum "er3600g-er4800g"              { value 15; }
            enum "he3600g-he4800g"              { value 16; }
            enum "cr3600g-er3600g"              { value 17; }
            enum "er3600g-he3600g"              { value 18; }
            enum "cr4800g-er4800g"              { value 19; }
            enum "er4800g-he4800g"              { value 20; }
            enum "any3600g-3600gdd"             { value 21; }
            enum "any4800g-4800g+"              { value 22; }
            enum "cr600g-cr1200g"               { value 23; }
            enum "er600g-er1200g"               { value 24; }
            enum "he600g-he1200g"               { value 25; }
            enum "cr600g-er600g"                { value 26; }
            enum "er600g-he600g"                { value 27; }
            enum "any1200g-1200g+"              { value 28; }
            enum "any2400g-2400g+4t"            { value 29; }
        }
        description "Specifies an SR OS series MDA functional level upgrade path.";
    }

    typedef sros-xiom-type {
        type enumeration {
            enum "iom-s-3.0t"                   { value 2; }
        }
        description "Specifies an SROS XIOM type.";
    }

    typedef sros-xiom-type-state {
        type enumeration {
            enum "unknown"                      { value 0; }
            enum "unassigned"                   { value 1; }
            enum "iom-s-3.0t"                   { value 2; }
        }
        description "Specifies an SROS XIOM type.";
    }

    typedef sros-xiom-level {
        type enumeration {
            enum "unrestricted"                 { value 1; }
            enum "he800g+"                      { value 2; }
            enum "er800g+"                      { value 3; }
            enum "cr800g+"                      { value 4; }
            enum "he1500g+"                     { value 5; }
            enum "er1500g+"                     { value 6; }
            enum "cr1500g+"                     { value 7; }
            enum "he1600g+"                     { value 8; }
            enum "er1600g+"                     { value 9; }
            enum "cr1600g+"                     { value 10; }
            enum "he2400g+"                     { value 11; }
            enum "er2400g+"                     { value 12; }
            enum "cr2400g+"                     { value 13; }
            enum "he3000g+"                     { value 14; }
            enum "er3000g+"                     { value 15; }
            enum "cr3000g+"                     { value 16; }
        }
        description "Specifies an SROS XIOM functional level";
    }

    typedef sros-xiom-level-state {
        type enumeration {
            enum "unknown"                      { value 0; }
            enum "unrestricted"                 { value 1; }
            enum "he800g+"                      { value 2; }
            enum "er800g+"                      { value 3; }
            enum "cr800g+"                      { value 4; }
            enum "he1500g+"                     { value 5; }
            enum "er1500g+"                     { value 6; }
            enum "cr1500g+"                     { value 7; }
            enum "he1600g+"                     { value 8; }
            enum "er1600g+"                     { value 9; }
            enum "cr1600g+"                     { value 10; }
            enum "he2400g+"                     { value 11; }
            enum "er2400g+"                     { value 12; }
            enum "cr2400g+"                     { value 13; }
            enum "he3000g+"                     { value 14; }
            enum "er3000g+"                     { value 15; }
            enum "cr3000g+"                     { value 16; }
        }
        description "Indicates an SROS XIOM functional-level.";
    }

    typedef sros-xiom-level-upgrade-path {
        type enumeration {
            enum "cr800g-cr1500g+"              { value 1; }
            enum "er800g-er1500g+"              { value 2; }
            enum "he800g-he1500g+"              { value 3; }
            enum "cr1600g-cr2400g+"             { value 4; }
            enum "er1600g-er2400g+"             { value 5; }
            enum "he1600g-he2400g+"             { value 6; }
            enum "cr2400g-cr3000g+"             { value 7; }
            enum "er2400g-er3000g+"             { value 8; }
            enum "he2400g-he3000g+"             { value 9; }
            enum "cr-er800g+"                   { value 10; }
            enum "er-he800g+"                   { value 11; }
            enum "cr-er1500g+"                  { value 12; }
            enum "er-he1500g+"                  { value 13; }
            enum "cr-er1600g+"                  { value 14; }
            enum "er-he1600g+"                  { value 15; }
            enum "cr-er2400g+"                  { value 16; }
            enum "er-he2400g+"                  { value 17; }
            enum "cr-er3000g+"                  { value 18; }
            enum "er-he3000g+"                  { value 19; }
        }
        description "Specifies an SROS series XIOM functional level upgrade path.";
    }

    typedef sros-xiom-mda-type {
        type enumeration {
            enum "ms6-200gb-cfp2-dco"           { value 51; }
            enum "ms18-100gb-qsfp28"            { value 209; }
            enum "ms4-400gb-qsfpdd+4-100gb-qsfp28" { value 212; }
            enum "ms24-10/100gb-sfpdd"          { value 213; }
            enum "ms4-400g-qsfpdd+4-100g-qsfp28" { status obsolete; }
        }
        description "Specifies an SROS XIOM Media Dependent Adapter (MDA) type";
    }

    typedef sros-xiom-mda-type-state {
        type enumeration {
            enum "unknown"                      { value 0; }
            enum "unassigned"                   { value 1; }
            enum "ms6-200gb-cfp2-dco"           { value 51; }
            enum "ms18-100gb-qsfp28"            { value 209; }
            enum "ms4-400gb-qsfpdd+4-100gb-qsfp28" { value 212; }
            enum "ms24-10/100gb-sfpdd"          { value 213; }
            enum "ms4-400g-qsfpdd+4-100g-qsfp28" { status obsolete; }
        }
        description "Specifies an SROS XIOM Media Dependent Adapter (MDA) type";
    }

    typedef mda-channel-type {
        type enumeration {
            enum "unknown"                      { value 0; }
            enum "sonet-sts-768"                { value 1; }
            enum "sonet-sts-192"                { value 2; }
            enum "sonet-sts-48"                 { value 3; }
            enum "sonet-sts-12"                 { value 4; }
            enum "sonet-sts-3"                  { value 5; }
            enum "sonet-sts-1"                  { value 6; }
            enum "sdh-tug-3"                    { value 7; }
            enum "sonet-vtg"                    { value 8; }
            enum "sonet-vt-15"                  { value 9; }
            enum "sonet-vt-2"                   { value 10; }
            enum "sonet-vt-3"                   { value 11; }
            enum "sonet-vt-6"                   { value 12; }
            enum "pdh-tu3"                      { value 13; }
            enum "pdh-ds3"                      { value 14; }
            enum "pdh-e3"                       { value 15; }
            enum "pdh-ds1"                      { value 16; }
            enum "pdh-e1"                       { value 17; }
            enum "pdh-ds0-group"                { value 18; }
        }
        description "Specifies the type of channel that can be created on an MDA";
    }

    typedef fp-generation {
        type enumeration {
            enum "not-applicable"               { value 0; }
            enum "fp2"                          { value 1; }
            enum "fp3"                          { value 2; }
            enum "fp4"                          { value 3; }
        }
        description "Specifies the forwarding plane (FP) network processor generation.";
    }

    typedef filter-profile {
        type enumeration {
            enum "none"                         { value 0; }
            enum "profile-a"                    { value 1; }
        }
        description
            "The filter-scale profile for the card. None specifies the default filter
             allocation for the chassis. Profile-a allows additional ingress IPv4 filter
             entries at the expense of egress IPv4 and IPv6 filter entries.";
    }

}
