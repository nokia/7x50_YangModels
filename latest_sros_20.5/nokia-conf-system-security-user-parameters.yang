submodule nokia-conf-system-security-user-parameters {

    yang-version "1.1";

    belongs-to nokia-conf { prefix "conf"; }

    import nokia-sros-yang-extensions     { prefix "sros-ext"; }
    import nokia-types-security           { prefix "types-security"; }
    import nokia-types-sros               { prefix "types-sros"; }
    import nokia-types-system             { prefix "types-system"; }

    include nokia-conf-groups;
    include nokia-conf-system;
    include nokia-conf-system-security;
    include nokia-conf-system-security-aaa;

    sros-ext:sros-major-release "rel20";

    organization "Nokia";

    contact
        "Nokia SR OS Support
         Web: <http://www.nokia.com>";

    description
        "Nokia YANG Data model to configure user and password parameters. on SR OS based routers.

         Copyright 2016 Nokia. All rights reserved. Reproduction of this document
         is authorized on the condition that the foregoing copyright notice is included.

         This nokia-conf-system-security-user-parameters YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";

    revision "2020-03-25";

    grouping conf-system-security-user-parameters-user-params {
        container user-params {
            description "Enter the user-params context";

            leaf-list apply-groups {
                type leafref {
                    path "../../../../groups/group/name";
                }
                max-elements 8;
                ordered-by user;
                description "Apply a configuration group at this level";
            }

            container attempts {
                description "Enter the attempts context";

                leaf count {
                    type uint32 {
                        range "1..64";
                    }
                    default "3";
                    description "Number of unsuccessful login attempts";
                }

                leaf time {
                    type uint32 {
                        range "0..60";
                    }
                    units "minutes";
                    default "5";
                    description "Time frame of unsuccessful login attempts";
                }

                leaf lockout {
                    type uint32 {
                        range "0..1440";
                    }
                    units "minutes";
                    default "10";
                    description "Lockout period after unsuccessful login attempts";
                }

            } // container attempts

            container authentication-order {
                description "Enter the authentication-order context";

                leaf-list order {
                    type types-security:password-authentication-order;
                    max-elements 4;
                    ordered-by user;
                    description "Sequence of password authentication, authorization, and accounting";
                }

                leaf exit-on-reject {
                    type boolean;
                    default "false";
                    description "Ignore subsequent AAA methods in authentication order when a reject is received";
                }

            } // container authentication-order

            container local-user {
                description "Enter the local-user context";

                container password {
                    description "Enter the password context";

                    leaf aging {
                        type uint32 {
                            range "1..500";
                        }
                        units "days";
                        description "Maximum time during which a user password is valid";
                    }

                    leaf history-size {
                        type uint32 {
                            range "0..20";
                        }
                        description "New password to match against previous ones";
                    }

                    leaf minimum-age {
                        type types-sros:time-duration {
                            range "0..86400";
                        }
                        units "seconds";
                        default "600";
                        description "Minimum age required for a password before changing it";
                    }

                    leaf minimum-change {
                        type uint32 {
                            range "1..20";
                        }
                        default "5";
                        description "Minimum distance required between the old and the new password";
                    }

                    leaf-list apply-groups {
                        type leafref {
                            path "../../../../../../groups/group/name";
                        }
                        max-elements 8;
                        ordered-by user;
                        description "Apply a configuration group at this level";
                    }

                    container complexity-rules {
                        description "Enter the complexity-rules context";

                        leaf allow-user-name {
                            type boolean;
                            default "false";
                            description "User name as part of the password";
                        }

                        leaf minimum-classes {
                            type uint32 {
                                range "2..4";
                            }
                            description "Force the use of different character classes for a minimum number";
                        }

                        leaf minimum-length {
                            type uint32 {
                                range "6..50";
                            }
                            default "6";
                            description "Minimum length required for local passwords";
                        }

                        leaf repeated-characters {
                            type uint32 {
                                range "2..8";
                            }
                            description "Number of times the same character appears consecutively";
                        }

                        choice complexity-rules-type {
                            case credits {

                                container credits {
                                    description "Enter the credits context";

                                    leaf lowercase {
                                        type uint32 {
                                            range "1..10";
                                        }
                                        description "Maximum credits given for the usage of lowercase letters";
                                    }

                                    leaf uppercase {
                                        type uint32 {
                                            range "1..10";
                                        }
                                        description "Maximum credits given for the usage of uppercase letters";
                                    }

                                    leaf numeric {
                                        type uint32 {
                                            range "1..10";
                                        }
                                        description "Maximum credits given for the usage of numeric characters";
                                    }

                                    leaf special-character {
                                        type uint32 {
                                            range "1..10";
                                        }
                                        description "Maximum credits given for the usage of special characters";
                                    }

                                } // container credits

                            }
                            case required {

                                container required {
                                    description "Enter the required context";

                                    leaf lowercase {
                                        type uint32 {
                                            range "1..10";
                                        }
                                        description "Number required for lowercase letters";
                                    }

                                    leaf uppercase {
                                        type uint32 {
                                            range "1..10";
                                        }
                                        description "Number required for uppercase letters";
                                    }

                                    leaf numeric {
                                        type uint32 {
                                            range "1..10";
                                        }
                                        description "Number required for numeric characters";
                                    }

                                    leaf special-character {
                                        type uint32 {
                                            range "1..10";
                                        }
                                        description "Number required for special characters";
                                    }

                                } // container required

                            }
                        }
                    } // container complexity-rules

                } // container password

                list user {
                    key "user-name";
                    description "Enter the user list instance";

                    leaf user-name {
                        type types-sros:named-item;
                        description "Local user name";
                    }

                    leaf home-directory {
                        type types-sros:local-url;
                        description "Home directory for the user";
                    }

                    leaf password {
                        type types-sros:hashed-leaf {
                            length "3..60";
                        }
                        mandatory true;
                        description "Password to authenticate the user for console and FTP access";
                    }

                    leaf restricted-to-home {
                        type boolean;
                        default "false";
                        description "Users prevented from navigating above their home directories to access file";
                    }

                    leaf-list cli-engine {
                        type types-system:cli-engine-type;
                        max-elements 2;
                        ordered-by user;
                        description "User level override for CLI engine access";
                    }

                    leaf-list apply-groups {
                        type leafref {
                            path "../../../../../../groups/group/name";
                        }
                        max-elements 8;
                        ordered-by user;
                        description "Apply a configuration group at this level";
                    }

                    container access {
                        description "Enter the access context";

                        leaf console {
                            type boolean;
                            default "false";
                            description "Allow console access (serial port or Telnet)";
                        }

                        leaf ftp {
                            type boolean;
                            default "false";
                            description "Allow FTP access";
                        }

                        leaf snmp {
                            type boolean;
                            default "false";
                            description "Allow SNMP access";
                        }

                        leaf netconf {
                            type boolean;
                            default "false";
                            description "Allow NETCONF session access";
                        }

                        leaf grpc {
                            type boolean;
                            default "false";
                            description "Allow gRPC access";
                        }

                        leaf li {
                            type boolean;
                            default "false";
                            description "Enable/disable access to LI.";
                        }

                    } // container access

                    container console {
                        description "Enter the console context";

                        leaf cannot-change-password {
                            type boolean;
                            default "false";
                            description "Change password privileges";
                        }

                        leaf login-exec {
                            type union {
                                type types-sros:sat-url;
                                type types-sros:cflash-url;
                                type types-sros:ftp-tftp-url {
                                    length "1..180";
                                }
                                type types-sros:filename;
                            }
                            description "File to execute when a user successfully logs in";
                        }

                        leaf new-password-at-login {
                            type boolean;
                            default "false";
                            description "Prompt a user to change password at next console login";
                        }

                        leaf-list member {
                            type leafref {
                                path "../../../../../aaa/local-profiles/profile/user-profile-name";
                            }
                            max-elements 8;
                            ordered-by user;
                            description "User profiles for this user";
                        }

                    } // container console

                    container public-keys {
                        description "Enter the public-keys context";

                        container ecdsa {
                            description "Enter the ecdsa context";

                            list ecdsa-key {
                                key "ecdsa-public-key-id";
                                description "Enter the ecdsa-key list instance";

                                leaf ecdsa-public-key-id {
                                    type uint32 {
                                        range "1..32";
                                    }
                                    description "Number of the Secure Shell version 2 (SSHv2) ECDSA public key that is associated with system user";
                                }

                                leaf description {
                                    type types-sros:description;
                                    description "Text description";
                                }

                                leaf key-value {
                                    type types-sros:string-not-all-spaces {
                                        length "1..255";
                                    }
                                    description "Number of the Secure Shell version 2 (SSHv2) ECDSA public key that is associated with system user";
                                }

                                leaf-list apply-groups {
                                    type leafref {
                                        path "../../../../../../../../../groups/group/name";
                                    }
                                    max-elements 8;
                                    ordered-by user;
                                    description "Apply a configuration group at this level";
                                }

                            } // list ecdsa-key

                        } // container ecdsa

                        container rsa {
                            description "Enter the rsa context";

                            list rsa-key {
                                key "rsa-public-key-id";
                                description "Enter the rsa-key list instance";

                                leaf rsa-public-key-id {
                                    type uint32 {
                                        range "1..32";
                                    }
                                    description "Number of the Secure Shell version 2 (SSHv2) RSA public key that is associated with system user";
                                }

                                leaf description {
                                    type types-sros:description;
                                    description "Text description";
                                }

                                leaf key-value {
                                    type types-sros:string-not-all-spaces {
                                        length "1..800";
                                    }
                                    description "Number of the Secure Shell version 2 (SSHv2) RSA public key that is associated with system user";
                                }

                                leaf-list apply-groups {
                                    type leafref {
                                        path "../../../../../../../../../groups/group/name";
                                    }
                                    max-elements 8;
                                    ordered-by user;
                                    description "Apply a configuration group at this level";
                                }

                            } // list rsa-key

                        } // container rsa

                    } // container public-keys

                    container snmp {
                        description "Enter the snmp context";

                        leaf group {
                            type types-sros:named-item;
                            description "User to associate with a group name";
                        }

                        leaf-list apply-groups {
                            type leafref {
                                path "../../../../../../../groups/group/name";
                            }
                            max-elements 8;
                            ordered-by user;
                            description "Apply a configuration group at this level";
                        }

                        container authentication {
                            presence "Authentication in the SNMP model.";
                            description "Enter the authentication context";

                            leaf authentication-protocol {
                                type enumeration {
                                    enum "md5"                          { value 2; }
                                    enum "sha"                          { value 3; }
                                }
                                description "Authentication protocol";
                            }

                            leaf authentication-key {
                                type types-sros:encrypted-leaf-hex-without-prefix {
                                    length "1..54";
                                }
                                description "Authentication key for authentication protocol";
                            }

                            container privacy {
                                presence "Privacy in the SNMP model.";
                                description "Enter the privacy context";

                                leaf privacy-protocol {
                                    type enumeration {
                                        enum "des"                          { value 2; }
                                        enum "aes-128-cfb"                  { value 4; }
                                    }
                                    mandatory true;
                                    description "Encryption protocol for authentication";
                                }

                                leaf privacy-key {
                                    type types-sros:encrypted-leaf-hex-without-prefix {
                                        length "1..51";
                                    }
                                    mandatory true;
                                    description "Localized privacy key for authentication";
                                }

                            } // container privacy

                        } // container authentication

                    } // container snmp

                } // list user

            } // container local-user

        } // container user-params

    } // grouping conf-system-security-user-parameters-user-params

}
