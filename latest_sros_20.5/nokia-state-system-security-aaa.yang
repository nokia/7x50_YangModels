submodule nokia-state-system-security-aaa {

    yang-version "1.1";

    belongs-to nokia-state { prefix "state"; }

    import ietf-yang-types                { prefix "yang"; }
    import nokia-sros-yang-extensions     { prefix "sros-ext"; }
    import nokia-types-sros               { prefix "types-sros"; }


    sros-ext:sros-major-release "rel20";

    organization "Nokia";

    contact
        "Nokia SR OS Support
         Web: <http://www.nokia.com>";

    description
        "Nokia YANG Data model with operational state for system security aaa parameters. on SR OS based routers.

         Copyright 2016 Nokia. All rights reserved. Reproduction of this document
         is authorized on the condition that the foregoing copyright notice is included.

         This nokia-state-system-security-aaa YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";

    revision "2020-05-11";

    grouping state-system-security-aaa {
        container aaa {
            description "Enter the aaa context";

            container remote-servers {
                description "Enter the remote-servers context";

                container radius {
                    description "Enter the radius context";

                    leaf oper-state {
                        type types-sros:up-down-status;
                        description "Current status of aaa server. Is it up if one server is up.";
                    }

                    list server {
                        key "index";
                        description "Enter the server list instance";

                        leaf index {
                            type uint32 {
                                range "1..5";
                            }
                            description "Unique number which identifies a specific RADIUS server.";
                        }

                        leaf oper-state {
                            type types-sros:up-down-status;
                            description "Current status of RADIUS server.";
                        }

                    } // list server

                } // container radius

                container ldap {
                    description "Enter the ldap context";

                    leaf oper-state {
                        type types-sros:up-down-status;
                        description "Current status of aaa server. Is it up if one server is up.";
                    }

                    list server {
                        key "index";
                        description "Enter the server list instance";

                        leaf index {
                            type uint32 {
                                range "1..5";
                            }
                            description "Unique value which identifies a specific LDAP server.";
                        }

                        leaf oper-state {
                            type types-sros:up-down-status;
                            description "Operational status of LDAP server.";
                        }

                    } // list server

                } // container ldap

                container tacplus {
                    description "Enter the tacplus context";

                    leaf oper-state {
                        type types-sros:up-down-status;
                        description "Current status of aaa server. Is it up if one server is up.";
                    }

                    list server {
                        key "index";
                        description "Enter the server list instance";

                        leaf index {
                            type uint32 {
                                range "1..5";
                            }
                            description "Identifies a specific TACACS+ server.";
                        }

                        leaf oper-state {
                            type types-sros:up-down-status;
                            description "Operational status of TACACS+ server.";
                        }

                    } // list server

                } // container tacplus

                container statistics {
                    description "Enter the statistics context";

                    container authentication {
                        description "Enter the authentication context";

                        container radius {
                            description "Enter the radius context";

                            list server {
                                key "index";
                                description "Enter the server list instance";

                                leaf index {
                                    type uint32 {
                                        range "1..5";
                                    }
                                    description "Unique number which identifies a specific RADIUS server.";
                                }

                                leaf connection-errors {
                                    type uint32;
                                    description "Indicates the number of connection errors.";
                                }

                                leaf accepted-logins {
                                    type uint32;
                                    description "Indicates the number of accepted logins.";
                                }

                                leaf rejected-logins {
                                    type uint32;
                                    description "Indicates the number of rejected logins.";
                                }

                            } // list server

                        } // container radius

                        container tacplus {
                            description "Enter the tacplus context";

                            list server {
                                key "index";
                                description "Enter the server list instance";

                                leaf index {
                                    type uint32 {
                                        range "1..5";
                                    }
                                    description "Identifies a specific TACACS+ server.";
                                }

                                leaf connection-errors {
                                    type uint32;
                                    description "Indicates the number of connection errors.";
                                }

                                leaf accepted-logins {
                                    type uint32;
                                    description "Indicates the number of accepted logins.";
                                }

                                leaf rejected-logins {
                                    type uint32;
                                    description "Indicates the number of rejected logins.";
                                }

                            } // list server

                        } // container tacplus

                        container ldap {
                            description "Enter the ldap context";

                            list server {
                                key "index";
                                description "Enter the server list instance";

                                leaf index {
                                    type uint32 {
                                        range "1..5";
                                    }
                                    description "Unique value which identifies a specific LDAP server.";
                                }

                                leaf connection-errors {
                                    type uint32;
                                    description "Indicates the number of connection errors.";
                                }

                                leaf accepted-logins {
                                    type uint32;
                                    description "Indicates the number of accepted logins.";
                                }

                                leaf rejected-logins {
                                    type uint32;
                                    description "Indicates the number of rejected logins.";
                                }

                            } // list server

                        } // container ldap

                        container local {
                            description "Enter the local context";

                            leaf accepted-logins {
                                type uint32;
                                description "Indicates the number of accepted logins.";
                            }

                            leaf rejected-logins {
                                type uint32;
                                description "Indicates the number of rejected logins.";
                            }

                        } // container local

                    } // container authentication

                    container authorization {
                        description "Enter the authorization context";

                        container tacplus {
                            description "Enter the tacplus context";

                            list server {
                                key "index";
                                description "Enter the server list instance";

                                leaf index {
                                    type uint32 {
                                        range "1..5";
                                    }
                                    description "Identifies a specific TACACS+ server.";
                                }

                                leaf connection-errors {
                                    type uint32;
                                    description "Indicates the number of connection errors.";
                                }

                                leaf sent-requests {
                                    type uint32;
                                    description "Indicates the number of sent requests.";
                                }

                                leaf rejected-requests {
                                    type uint32;
                                    description "Indicates the number of rejected requests.";
                                }

                            } // list server

                        } // container tacplus

                    } // container authorization

                    container accounting {
                        description "Enter the accounting context";

                        container tacplus {
                            description "Enter the tacplus context";

                            list server {
                                key "index";
                                description "Enter the server list instance";

                                leaf index {
                                    type uint32 {
                                        range "1..5";
                                    }
                                    description "Identifies a specific TACACS+ server.";
                                }

                                leaf connection-errors {
                                    type uint32;
                                    description "Indicates the number of connection errors.";
                                }

                                leaf sent-messages {
                                    type uint32;
                                    description "Indicates the number of sent messages.";
                                }

                                leaf rejected-messages {
                                    type uint32;
                                    description "Indicates the number of rejected messages.";
                                }

                            } // list server

                        } // container tacplus

                        container radius {
                            description "Enter the radius context";

                            list server {
                                key "index";
                                description "Enter the server list instance";

                                leaf index {
                                    type uint32 {
                                        range "1..5";
                                    }
                                    description "Unique number which identifies a specific RADIUS server.";
                                }

                                leaf connection-errors {
                                    type uint32;
                                    description "Indicates the number of connection errors.";
                                }

                                leaf sent-messages {
                                    type uint32;
                                    description "Indicates the number of sent messages.";
                                }

                                leaf rejected-messages {
                                    type uint32;
                                    description "Indicates the number of rejected messages.";
                                }

                            } // list server

                        } // container radius

                    } // container accounting

                } // container statistics

                list router-statistics {
                    key "router-instance";
                    description "Enter the router-statistics list instance";

                    leaf router-instance {
                        type types-sros:router-instance;
                        description "Routing context of AAA servers.";
                    }

                    container authentication {
                        description "Enter the authentication context";

                        container radius {
                            description "Enter the radius context";

                            list server {
                                key "index";
                                description "Enter the server list instance";

                                leaf index {
                                    type uint32 {
                                        range "1..5";
                                    }
                                    description "Unique number which identifies a specific RADIUS server.";
                                }

                                leaf connection-errors {
                                    type uint32;
                                    description "Indicates the number of connection errors.";
                                }

                                leaf accepted-logins {
                                    type uint32;
                                    description "Indicates the number of accepted logins.";
                                }

                                leaf rejected-logins {
                                    type uint32;
                                    description "Indicates the number of rejected logins.";
                                }

                            } // list server

                        } // container radius

                        container tacplus {
                            description "Enter the tacplus context";

                            list server {
                                key "index";
                                description "Enter the server list instance";

                                leaf index {
                                    type uint32 {
                                        range "1..5";
                                    }
                                    description "Identifies a specific TACACS+ server.";
                                }

                                leaf connection-errors {
                                    type uint32;
                                    description "Indicates the number of connection errors.";
                                }

                                leaf accepted-logins {
                                    type uint32;
                                    description "Indicates the number of accepted logins.";
                                }

                                leaf rejected-logins {
                                    type uint32;
                                    description "Indicates the number of rejected logins.";
                                }

                            } // list server

                        } // container tacplus

                    } // container authentication

                    container authorization {
                        description "Enter the authorization context";

                        container tacplus {
                            description "Enter the tacplus context";

                            list server {
                                key "index";
                                description "Enter the server list instance";

                                leaf index {
                                    type uint32 {
                                        range "1..5";
                                    }
                                    description "Identifies a specific TACACS+ server.";
                                }

                                leaf connection-errors {
                                    type uint32;
                                    description "Indicates the number of connection errors.";
                                }

                                leaf sent-requests {
                                    type uint32;
                                    description "Indicates the number of sent requests.";
                                }

                                leaf rejected-requests {
                                    type uint32;
                                    description "Indicates the number of rejected requests.";
                                }

                            } // list server

                        } // container tacplus

                    } // container authorization

                    container accounting {
                        description "Enter the accounting context";

                        container tacplus {
                            description "Enter the tacplus context";

                            list server {
                                key "index";
                                description "Enter the server list instance";

                                leaf index {
                                    type uint32 {
                                        range "1..5";
                                    }
                                    description "Identifies a specific TACACS+ server.";
                                }

                                leaf connection-errors {
                                    type uint32;
                                    description "Indicates the number of connection errors.";
                                }

                                leaf sent-messages {
                                    type uint32;
                                    description "Indicates the number of sent messages.";
                                }

                                leaf rejected-messages {
                                    type uint32;
                                    description "Indicates the number of rejected messages.";
                                }

                            } // list server

                        } // container tacplus

                        container radius {
                            description "Enter the radius context";

                            list server {
                                key "index";
                                description "Enter the server list instance";

                                leaf index {
                                    type uint32 {
                                        range "1..5";
                                    }
                                    description "Unique number which identifies a specific RADIUS server.";
                                }

                                leaf connection-errors {
                                    type uint32;
                                    description "Indicates the number of connection errors.";
                                }

                                leaf sent-messages {
                                    type uint32;
                                    description "Indicates the number of sent messages.";
                                }

                                leaf rejected-messages {
                                    type uint32;
                                    description "Indicates the number of rejected messages.";
                                }

                            } // list server

                        } // container radius

                    } // container accounting

                } // list router-statistics

            } // container remote-servers

            list cli-session-group {
                key "cli-session-group-name";
                description "Enter the cli-session-group list instance";

                leaf cli-session-group-name {
                    type types-sros:named-item;
                    description "The name of the cli session group.";
                }

                leaf ref-count {
                    type yang:counter32;
                    description "Number of referencing user profiles";
                }

                list ref-user-profiles {
                    key "user-profile-name";
                    description "Enter the ref-user-profiles list instance";

                    leaf user-profile-name {
                        type types-sros:named-item;
                        description "The name of the referencing user profile";
                    }

                } // list ref-user-profiles

            } // list cli-session-group

        } // container aaa

    } // grouping state-system-security-aaa

}
