submodule nokia-state-system-security-pki {

    yang-version "1.1";

    belongs-to nokia-state { prefix "state"; }

    import ietf-yang-types                { prefix "yang"; }
    import nokia-sros-yang-extensions     { prefix "sros-ext"; }
    import nokia-types-security           { prefix "types-security"; }
    import nokia-types-sros               { prefix "types-sros"; }


    sros-ext:sros-major-release "rel20";

    organization "Nokia";

    contact
        "Nokia SR OS Support
         Web: <http://www.nokia.com>";

    description
        "Nokia YANG Data model with operational state for system security pki parameters. on SR OS based routers.

         Copyright 2016 Nokia. All rights reserved. Reproduction of this document
         is authorized on the condition that the foregoing copyright notice is included.

         This nokia-state-system-security-pki YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";

    revision "2020-06-03";

    grouping state-system-security-pki {
        container pki {
            description "Enter the pki context";

            container statistics {
                description "Enter the statistics context";

                container authentication {
                    description "Enter the authentication context";

                    leaf failed {
                        type yang:counter32;
                        description "The number of authentication failures using the certificates.";
                    }

                    leaf passed {
                        type yang:counter32;
                        description "The number of authentication checks passed using the certificates.";
                    }

                    leaf attempted {
                        type yang:counter32;
                        description "The number of authentication attempts using the certificates.";
                    }

                } // container authentication

            } // container statistics

            list ca-profile {
                key "ca-profile-name";
                description "Enter the ca-profile list instance";

                leaf ca-profile-name {
                    type types-sros:named-item;
                    description "Certificate Authority (CA) profile name";
                }

                leaf oper-state {
                    type types-sros:oper-state;
                    description "Operational state of the CA profile.";
                }

                leaf oper-flags {
                    type bits {
                        bit adminDown                      { position 0; }
                        bit invalid-crl                    { position 1; }
                        bit invalid-cert                   { position 2; }
                        bit invalid-cmpv2-signing-cert     { position 3; }
                        bit expired-crl                    { position 4; }
                        bit expired-cert                   { position 5; }
                        bit expired-cmpv2-signing-cert     { position 6; }
                        bit not-yet-valid-crl              { position 7; }
                        bit not-yet-valid-cert             { position 8; }
                        bit not-yet-valid-cmpv2-signing-cert { position 9; }
                        bit loading-crl                    { position 10; }
                        bit loading-cert                   { position 11; }
                        bit loading-cmpv2-signing-cert     { position 12; }
                    }
                    description "Reason why the CA profile is not in service.";
                }

                container auto-crl-update {
                    description "Enter the auto-crl-update context";

                    leaf last-success-auto-crl-update-url-id {
                        type union {
                            type uint32 {
                                range "1..8";
                            }
                            type enumeration {
                                enum "not-applicable"               { value 0; }
                            }
                        }
                        description "URL entry ID of the last successful automated CRL update.";
                    }

                    leaf last-success-auto-crl-update-time-start {
                        type uint32;
                        units "seconds";
                        description
                            "Time at which the last successful automated CRL update
                             was initiated. It is measured from 1-Jan-1970 00:00:00 UTC.";
                    }

                    leaf last-success-auto-crl-update-time-end {
                        type uint32;
                        units "seconds";
                        description
                            "Time at which the last successful automated CRL update
                             was finished. It is measured from 1-Jan-1970 00:00:00 UTC.";
                    }

                    leaf next-scheduled-auto-crl-update-time {
                        type uint32;
                        units "seconds";
                        description
                            "Start time of the next scheduled update. It is measured
                             from 1-Jan-1970 00:00:00 UTC.";
                    }

                    container current-crl-update {
                        description "Enter the current-crl-update context";

                        leaf status {
                            type types-security:crl-update-status;
                            description "The CRL update status.";
                        }

                        leaf entry-id {
                            type uint32 {
                                range "1..8";
                            }
                            description "The url-entry which is being used in the current update for a CRL file.";
                        }

                        leaf start-time {
                            type yang:date-and-time;
                            description "The time at which the current automated CRL update was initiated.";
                        }

                        container last-failed-update {
                            description "Enter the last-failed-update context";

                            leaf start-time {
                                type yang:date-and-time;
                                description "The time at which the last failed automated CRL update was initiated.";
                            }

                            leaf end-time {
                                type yang:date-and-time;
                                description "The time at which the last failed automated CRL update was finished.";
                            }

                            leaf entry-id {
                                type uint32 {
                                    range "1..8";
                                }
                                description "The url-entry of the last failed automated CRL update.";
                            }

                            leaf cause {
                                type enumeration {
                                    enum "no-failure"                   { value 0; }
                                    enum "download-failed"              { value 1; }
                                    enum "invalid-crl"                  { value 2; }
                                }
                                description
                                    "The reason of the recent failed automated CRL update.

                                     noFailure      (0) -- The system never fails to update the CRL file
                                     downloadFailed (1) -- The system failed to download the CRL file
                                     invalidCRL     (2) -- The verification of the downloaded CRL file failed.";
                            }

                        } // container last-failed-update

                    } // container current-crl-update

                } // container auto-crl-update

            } // list ca-profile

        } // container pki

    } // grouping state-system-security-pki

}
