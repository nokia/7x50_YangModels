module nokia-li-notifications {

    yang-version "1.1";

    namespace "urn:nokia.com:sros:ns:yang:sr:li-notifications";

    prefix "notif";

    import nokia-sros-yang-extensions   { prefix "sros-ext"; }
    import nokia-types-log              { prefix "types-log"; }
    import nokia-types-sros             { prefix "types-sros"; }
    import ietf-netconf                 { prefix "nc"; }
    import ietf-netconf-notifications   { prefix "ietf-ncn"; }

    description "Description of the li notifications which are available in the 
                 system and can be sent out by the logger.";

    sros-ext:sros-major-release "rel20";

    organization "Nokia";

    contact
        "Nokia SR OS Support
         Web: <http://www.nokia.com>";


    revision "2020-01-03";

//  -------------------- AUGMENT STANDARD NOTIFICATIONS --------------------

    augment "/ietf-ncn:netconf-config-change/ietf-ncn:edit" {
        leaf value {
            description
                "The new value of the target.";
            type string;
        }
    }

//  -------------------------- SROS LI NOTIFICATIONS -----------------------

    notification sros-li-config-change-event {
        description
            "Generated when the li configuration of the system gets created, 
             modified or deleted.";

        uses basic-event-params;
        uses nokia-event-data;
    }

    notification sros-li-state-change-event {
        description
            "Generated on li state changes in the system.";

        uses basic-event-params;
        uses nokia-event-data;
    }

    notification sros-li-command-accounting-event {
        description
            "Generated when a user executes a li command on a management interface.";

        uses basic-event-params;
        uses nokia-event-data;
    }

    notification sros-li-md-rpc-accounting-event {
        description
            "Generated when a user executes a li RPC on a management interface.";

        uses basic-event-params;
        uses nokia-event-data;
    }

    notification sros-li-log-generic-event {
        description
            "Generated on any event that is generated in the system
             that is not modeled by a more specific event.";

        uses basic-event-params;
        uses nokia-event-data;
    }

    notification netconf-li-config-change {
        description
            "Generated when the NETCONF server detects that the
             <running> or <startup> configuration datastore
             has been changed for LI by a management session.
             The notification summarizes the edits that
             have been detected.

             The server MAY choose to also generate this
             notification while loading a datastore during the
             boot process for the device.";

        uses ietf-ncn:changed-by-parms;

        leaf datastore {
            type enumeration {
                enum running {
                    description "The <running> datastore has changed.";
                }
                enum startup {
                    description "The <startup> datastore has changed";
                }
            }
            default "running";
            description
                "Indicates which configuration datastore has changed.";
        }

        list edit {
            description
                "An edit record SHOULD be present for each distinct
                edit operation that the server has detected on
                the target datastore.  This list MAY be omitted
                if the detailed edit operations are not known.
                The server MAY report entries in this list for
                changes not made by a NETCONF session (e.g., CLI).";

            leaf target {
                type instance-identifier;
                    description
                        "Topmost node associated with the configuration change.
                        A server SHOULD set this object to the node within
                        the datastore that is being altered.  A server MAY
                        set this object to one of the ancestors of the actual
                        node that was changed, or omit this object, if the
                        exact node is not known.";
            }

            leaf operation {
                type nc:edit-operation-type;
                description
                    "Type of edit operation performed.
                    A server MUST set this object to the NETCONF edit
                    operation performed on the target datastore.";
            }
        } // list edit
    } // notification netconf-config-change

//  -------------------------- GROUPINGS --------------------------

    grouping basic-event-params {
        leaf sequence-number {
            description
                "A sequence number to indicate the ordering of log events in the log-id.
                 If the event is replayed, the sequence number is replayed as well.";
            type uint64;
        }

        leaf severity {
            description
                "The severity level of the log event.";
            type types-log:severity-level;
        }

        leaf application {
            description
                "The name of the application that reports the log event.";
            type types-log:application;
        }

        leaf event-id {
            description
                "The id the event that was generated.
                 Each log event type has a unique identifying number.  This number is
                 unique within a particular software application, such as IP, MPLS,
                 OSPF, etc.; but it is not necessarily unique across different software
                 applications.  That is MPLS event #1001 may be different from OSPF
                 event #1001.";
            type uint32 {
                range 1..max;
            }
        }

        leaf event-name {
            description
                "The name of the log event that was generated.";
            type types-sros:named-item;
        }

        leaf router-name {
            description
                "The router context name that generated the log event.";
            type types-sros:named-item-or-empty;
        }

        leaf subject {
            description
                "The router context name that generated the log event.
                 The subject is the entity that originated the event, such as the Port ID.";
            type types-sros:named-item;
        }

        leaf message {
            description
                "The log event message.";
            type string {
                length 1..4100;
            }
        }
    }

    grouping nokia-event-data {
        anyxml event-params {
            description
                "The event specific data splitted in parameters.";
        }
    }   
}
