submodule nokia-conf-system-security-aaa {

    yang-version "1.1";

    belongs-to nokia-conf { prefix "conf"; }

    import nokia-sros-yang-extensions     { prefix "sros-ext"; }
    import nokia-types-qos                { prefix "types-qos"; }
    import nokia-types-sros               { prefix "types-sros"; }
    import nokia-types-system             { prefix "types-system"; }

    include nokia-conf-groups;
    include nokia-conf-system;
    include nokia-conf-system-security;
    include nokia-conf-system-security-tls;

    sros-ext:sros-major-release "rel20";

    organization "Nokia";

    contact
        "Nokia SR OS Support
         Web: <http://www.nokia.com>";

    description
        "Nokia YANG Data model to configure system security aaa parameters. on SR OS based routers.

         Copyright 2016 Nokia. All rights reserved. Reproduction of this document
         is authorized on the condition that the foregoing copyright notice is included.

         This nokia-conf-system-security-aaa YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";

    revision "2020-06-01";

    grouping conf-system-security-aaa {
        container aaa {
            description "Enter the aaa context";

            leaf health-check {
                type union {
                    type int32 {
                        range "6..1500";
                    }
                    type enumeration {
                        enum "none"                         { value 0; }
                    }
                }
                units "seconds";
                default "30";
                description "Polling interval of RADIUS, TACACS+, and LDAP servers";
            }

            leaf-list apply-groups {
                type leafref {
                    path "../../../../groups/group/name";
                }
                max-elements 8;
                ordered-by user;
                description "Apply a configuration group at this level";
            }

            container remote-servers {
                description "Enter the remote-servers context";

                leaf-list apply-groups {
                    type leafref {
                        path "../../../../../groups/group/name";
                    }
                    max-elements 8;
                    ordered-by user;
                    description "Apply a configuration group at this level";
                }

                container radius {
                    description "Enter the radius context";

                    leaf admin-state {
                        type types-sros:admin-state;
                        default "enable";
                        description "Administrative state of RADIUS authentication";
                    }

                    leaf accounting {
                        type boolean;
                        default "false";
                        description "Enable/disable RADIUS command accounting.";
                    }

                    leaf accounting-port {
                        type uint32 {
                            range "1..65535";
                        }
                        default "1813";
                        description "Port number on which to contact RADIUS server for accounting requests.";
                    }

                    leaf authorization {
                        type boolean;
                        default "false";
                        description "Enable/disable RADIUS command authorization.";
                    }

                    leaf interactive-authentication {
                        type boolean;
                        default "false";
                        description "Enable/disable RADIUS interactive authentication.";
                    }

                    leaf server-retry {
                        type uint32 {
                            range "1..10";
                        }
                        default "3";
                        description "Number of attempts to retry contacting RADIUS.";
                    }

                    leaf server-timeout {
                        type uint32 {
                            range "1..90";
                        }
                        units "seconds";
                        default "3";
                        description "Timeout for a response from RADIUS server.";
                    }

                    leaf port {
                        type uint32 {
                            range "1..65535";
                        }
                        default "1812";
                        description "Port number on which to contact RADIUS server.";
                    }

                    leaf use-default-template {
                        type boolean;
                        default "false";
                        description "Enable/disable RADIUS default template.";
                    }

                    leaf access-algorithm {
                        type enumeration {
                            enum "direct"                       { value 1; }
                            enum "round-robin"                  { value 2; }
                        }
                        default "direct";
                        description "Configure the algorithm used to access the set of RADIUS servers.";
                    }

                    leaf-list apply-groups {
                        type leafref {
                            path "../../../../../../groups/group/name";
                        }
                        max-elements 8;
                        ordered-by user;
                        description "Apply a configuration group at this level";
                    }

                    list server {
                        key "index";
                        max-elements 5;
                        description "Enter the server list instance";

                        leaf index {
                            type uint32 {
                                range "1..5";
                            }
                            description "Unique number which identifies a specific RADIUS server.";
                        }

                        leaf address {
                            type types-sros:ip-unicast-address;
                            mandatory true;
                            description "IP address of Radius server.";
                        }

                        leaf secret {
                            type types-sros:encrypted-leaf {
                                length "1..115";
                            }
                            mandatory true;
                            description "The secret key associated with RADIUS server. The value of secret cannot be set to an empty string.";
                        }

                        leaf-list apply-groups {
                            type leafref {
                                path "../../../../../../../groups/group/name";
                            }
                            max-elements 8;
                            ordered-by user;
                            description "Apply a configuration group at this level";
                        }

                    } // list server

                } // container radius

                container ldap {
                    description "Enter the ldap context";

                    leaf admin-state {
                        type types-sros:admin-state;
                        default "enable";
                        description "Administrative state of the LDAP protocol";
                    }

                    leaf public-key-authentication {
                        type boolean;
                        default "false";
                        description "Allow SSH public key authentication from LDAP server";
                    }

                    leaf server-retry {
                        type uint32 {
                            range "1..10";
                        }
                        default "3";
                        description "Number of attempts to retry contacting an LDAP server";
                    }

                    leaf server-timeout {
                        type types-sros:time-duration {
                            range "1..90";
                        }
                        units "seconds";
                        default "3";
                        description "Timeout for a response from an LDAP server";
                    }

                    leaf use-default-template {
                        type boolean;
                        default "true";
                        description "Use LDAP default template";
                    }

                    leaf-list apply-groups {
                        type leafref {
                            path "../../../../../../groups/group/name";
                        }
                        max-elements 8;
                        ordered-by user;
                        description "Apply a configuration group at this level";
                    }

                    list server {
                        key "index";
                        max-elements 5;
                        description "Enter the server list instance";

                        leaf index {
                            type uint32 {
                                range "1..5";
                            }
                            description "Unique value which identifies a specific LDAP server.";
                        }

                        leaf admin-state {
                            type types-sros:admin-state;
                            default "disable";
                            description "Administrative state of this LDAP server";
                        }

                        leaf server-name {
                            type types-sros:named-item;
                            description "LDAP server name";
                        }

                        leaf tls-profile {
                            type leafref {
                                path "../../../../../tls/client-tls-profile/client-profile-name";
                            }
                            description "TLS client transport profile";
                        }

                        leaf-list apply-groups {
                            type leafref {
                                path "../../../../../../../groups/group/name";
                            }
                            max-elements 8;
                            ordered-by user;
                            description "Apply a configuration group at this level";
                        }

                        list address {
                            key "ip-address";
                            max-elements 1;
                            sros-ext:auto-restart-to-modify;
                            description "Enter the address list instance";

                            leaf ip-address {
                                type types-sros:ip-unicast-address;
                                description "LDAP server address";
                            }

                            leaf port {
                                type int32 {
                                    range "1..65535";
                                }
                                default "389";
                                description "Port number on which to contact the LDAP server.";
                            }

                            leaf-list apply-groups {
                                type leafref {
                                    path "../../../../../../../../groups/group/name";
                                }
                                max-elements 8;
                                ordered-by user;
                                description "Apply a configuration group at this level";
                            }

                        } // list address

                        container bind-authentication {
                            description "Enter the bind-authentication context";

                            leaf root-dn {
                                type types-sros:string-not-all-spaces {
                                    length "1..512";
                                }
                                description "Root domain used for authentication with the LDAP server.";
                            }

                            leaf password {
                                type types-sros:encrypted-leaf {
                                    length "1..199";
                                }
                                description "Password used for authentication with the LDAP server.";
                            }

                        } // container bind-authentication

                        container search {
                            description "Enter the search context";

                            leaf base-dn {
                                type types-sros:string-not-all-spaces {
                                    length "1..512";
                                }
                                description "LDAP server search domain";
                            }

                        } // container search

                    } // list server

                } // container ldap

                container tacplus {
                    description "Enter the tacplus context";

                    leaf interactive-authentication {
                        type boolean;
                        default "false";
                        description "Enable/disable TACACS+ interactive authentication.";
                    }

                    leaf admin-state {
                        type types-sros:admin-state;
                        default "enable";
                        description "Administrative state of the TACACS+ protocol operation";
                    }

                    leaf server-timeout {
                        type types-sros:time-duration {
                            range "1..90";
                        }
                        units "seconds";
                        default "3";
                        description "Timeout for a response from an TACACS+ server.";
                    }

                    leaf use-default-template {
                        type boolean;
                        default "true";
                        description "Enable/disable TACACS+ default template.";
                    }

                    leaf-list apply-groups {
                        type leafref {
                            path "../../../../../../groups/group/name";
                        }
                        max-elements 8;
                        ordered-by user;
                        description "Apply a configuration group at this level";
                    }

                    container accounting {
                        presence "Enable/disable TACACS+ command accounting.";
                        description "Enter the accounting context";

                        leaf record-type {
                            type enumeration {
                                enum "start-stop"                   { value 1; }
                                enum "stop-only"                    { value 2; }
                            }
                            default "stop-only";
                            description "Configure the type of accounting record packet that is to be sent to the TACACS+ server.";
                        }

                    } // container accounting

                    container authorization {
                        presence "Enable/disable TACACS+ command authorization.";
                        description "Enter the authorization context";

                        leaf use-priv-lvl {
                            type boolean;
                            default "false";
                            description "Enable/disable the privilege level mapping.";
                        }

                    } // container authorization

                    container admin-control {
                        description "Enter the admin-control context";

                        leaf tacplus-map-to-priv-lvl {
                            type int32 {
                                range "0..15";
                            }
                            description "Interactive authentication exchange from the node to the TACACS+ server";
                        }

                    } // container admin-control

                    container priv-lvl-map {
                        description "Enter the priv-lvl-map context";

                        leaf-list apply-groups {
                            type leafref {
                                path "../../../../../../../groups/group/name";
                            }
                            max-elements 8;
                            ordered-by user;
                            description "Apply a configuration group at this level";
                        }

                        list priv-lvl {
                            key "level";
                            description "Enter the priv-lvl list instance";

                            leaf level {
                                type uint32 {
                                    range "0..15";
                                }
                                description "Specifies the privilege level for this mapping.";
                            }

                            leaf user-profile-name {
                                type leafref {
                                    path "../../../../../local-profiles/profile/user-profile-name";
                                }
                                mandatory true;
                                description "Specifies the user profile for this mapping.";
                            }

                            leaf-list apply-groups {
                                type leafref {
                                    path "../../../../../../../../groups/group/name";
                                }
                                max-elements 8;
                                ordered-by user;
                                description "Apply a configuration group at this level";
                            }

                        } // list priv-lvl

                    } // container priv-lvl-map

                    list server {
                        key "index";
                        max-elements 5;
                        description "Enter the server list instance";

                        leaf index {
                            type uint32 {
                                range "1..5";
                            }
                            description "Identifies a specific TACACS+ server.";
                        }

                        leaf address {
                            type types-sros:ip-unicast-address;
                            mandatory true;
                            description "IP address of TACACS+ server.";
                        }

                        leaf port {
                            type types-qos:tcp-udp-match-port;
                            default "49";
                            description "TCP port number on which to contact TACACS+ server.";
                        }

                        leaf secret {
                            type types-sros:encrypted-leaf {
                                length "1..199";
                            }
                            mandatory true;
                            description "The secret key associated with the TACACS+ server. The value of secret cannot be set to an empty string.";
                        }

                        leaf-list apply-groups {
                            type leafref {
                                path "../../../../../../../groups/group/name";
                            }
                            max-elements 8;
                            ordered-by user;
                            description "Apply a configuration group at this level";
                        }

                    } // list server

                } // container tacplus

            } // container remote-servers

            container local-profiles {
                description "Enter the local-profiles context";

                leaf-list apply-groups {
                    type leafref {
                        path "../../../../../groups/group/name";
                    }
                    max-elements 8;
                    ordered-by user;
                    description "Apply a configuration group at this level";
                }

                list profile {
                    key "user-profile-name";
                    max-elements 128;
                    description "Enter the profile list instance";

                    leaf user-profile-name {
                        type types-sros:named-item {
                            pattern "[^ ]*" {
                                error-message "The name cannot contain spaces.";
                            }
                        }
                        description "Profile name";
                    }

                    leaf cli-session-group {
                        type leafref {
                            path "../../../cli-session-group/cli-session-group-name";
                        }
                        description "CLI session group to which the profile belongs";
                    }

                    leaf default-action {
                        type enumeration {
                            enum "deny-all"                     { value 1; }
                            enum "permit-all"                   { value 2; }
                            enum "none"                         { value 3; }
                            enum "read-only-all"                { value 4; }
                        }
                        default "none";
                        description "Action for non-matching entry";
                    }

                    leaf combined-max-sessions {
                        type types-system:session-limit;
                        description "Maximum number of concurrent SSH and Telnet sessions";
                    }

                    leaf ssh-max-sessions {
                        type types-system:session-limit;
                        description "Maximum number of concurrent SSH sessions";
                    }

                    leaf telnet-max-sessions {
                        type types-system:session-limit;
                        description "Maximum number of concurrent TELNET sessions";
                    }

                    leaf li {
                        type boolean;
                        default "false";
                        description "Lawful Intercept profile identifier.";
                    }

                    leaf-list apply-groups {
                        type leafref {
                            path "../../../../../../groups/group/name";
                        }
                        max-elements 8;
                        ordered-by user;
                        description "Apply a configuration group at this level";
                    }

                    container grpc {
                        description "Enter the grpc context";

                        container rpc-authorization {
                            description "Enter the rpc-authorization context";

                            leaf gnmi-capabilities {
                                type types-system:permit-deny;
                                description "Capability RPC use";
                            }

                            leaf gnmi-get {
                                type types-system:permit-deny;
                                description "Service gNMI Get RPC";
                            }

                            leaf gnmi-set {
                                type types-system:permit-deny;
                                description "Service gNMI Get RPC";
                            }

                            leaf gnmi-subscribe {
                                type types-system:permit-deny;
                                description "Service gNMI Subscribe RPC";
                            }

                            leaf gnoi-cert-mgmt-rotate {
                                type types-system:permit-deny;
                                default "deny";
                                description "Rotate RPC usage";
                            }

                            leaf gnoi-cert-mgmt-install {
                                type types-system:permit-deny;
                                default "deny";
                                description "Install RPC usage";
                            }

                            leaf gnoi-cert-mgmt-getcert {
                                type types-system:permit-deny;
                                default "deny";
                                description "GetCertificates RPC usage";
                            }

                            leaf gnoi-cert-mgmt-revoke {
                                type types-system:permit-deny;
                                default "deny";
                                description "RevokeCertificates RPC usage";
                            }

                            leaf gnoi-cert-mgmt-cangenerate {
                                type types-system:permit-deny;
                                default "deny";
                                description "CanGenerateCSR RPC usage";
                            }

                            leaf gnoi-system-setpackage {
                                type types-system:permit-deny;
                                default "deny";
                                description "SetPackage RPC usage";
                            }

                            leaf gnoi-system-switchcontrolprocessor {
                                type types-system:permit-deny;
                                default "deny";
                                description "SwitchControlProcessor RPC usage";
                            }

                            leaf gnoi-system-reboot {
                                type types-system:permit-deny;
                                default "deny";
                                description "Allow gNOI System Reboot RPC.";
                            }

                            leaf gnoi-system-rebootstatus {
                                type types-system:permit-deny;
                                default "deny";
                                description "Allow gNOI System RebootStatus RPC.";
                            }

                            leaf gnoi-system-cancelreboot {
                                type types-system:permit-deny;
                                default "deny";
                                description "CancelReboot RPC usage";
                            }

                            leaf md-cli-session {
                                type types-system:permit-deny;
                                description "Allow gNOI MdCli Session RPC.";
                            }

                            leaf rib-api-getversion {
                                type types-system:permit-deny;
                                description "Allow RibApi GetVersion RPC.";
                            }

                            leaf rib-api-modify {
                                type types-system:permit-deny;
                                description "Allow RibApi Modify RPC.";
                            }

                        } // container rpc-authorization

                    } // container grpc

                    container netconf {
                        description "Enter the netconf context";

                        container base-op-authorization {
                            description "Enter the base-op-authorization context";

                            leaf kill-session {
                                type boolean;
                                default "false";
                                description "Send a kill session NETCONF operation";
                            }

                            leaf lock {
                                type boolean;
                                default "false";
                                description "Send a lock session NETCONF operation";
                            }

                        } // container base-op-authorization

                    } // container netconf

                    list entry {
                        key "entry-id";
                        description "Enter the entry list instance";

                        leaf entry-id {
                            type uint32 {
                                range "1..9999";
                            }
                            description "User profile entry identifier";
                        }

                        leaf action {
                            type enumeration {
                                enum "deny"                         { value 1; }
                                enum "permit"                       { value 2; }
                                enum "none"                         { value 3; }
                                enum "read-only"                    { value 4; }
                            }
                            default "none";
                            description "Action when a user command matches this entry";
                        }

                        leaf description {
                            type types-sros:description;
                            description "Text description";
                        }

                        leaf match {
                            type types-sros:display-string;
                            description "Command to match this entry";
                        }

                        leaf-list apply-groups {
                            type leafref {
                                path "../../../../../../../groups/group/name";
                            }
                            max-elements 8;
                            ordered-by user;
                            description "Apply a configuration group at this level";
                        }

                    } // list entry

                } // list profile

            } // container local-profiles

            list user-template {
                key "user-template-name";
                description "Enter the user-template list instance";

                leaf user-template-name {
                    type enumeration {
                        enum "ldap-default"                 { value 0; }
                        enum "radius-default"               { value 1; }
                        enum "tacplus-default"              { value 2; }
                    }
                    description "Template value to derive a system user";
                }

                leaf home-directory {
                    type types-sros:local-url;
                    description "Home directory for the user based on this template";
                }

                leaf profile {
                    type types-sros:named-item {
                        pattern "[^ ]*" {
                            error-message "The profile name cannot contain spaces.";
                        }
                    }
                    description "User profile based on this template";
                }

                leaf restricted-to-home {
                    type boolean;
                    default "false";
                    description "Users to prevent from navigating above their home directories to access file";
                }

                leaf-list apply-groups {
                    type leafref {
                        path "../../../../../groups/group/name";
                    }
                    max-elements 8;
                    ordered-by user;
                    description "Apply a configuration group at this level";
                }

                container access {
                    description "Enter the access context";

                    leaf ftp {
                        type boolean;
                        default "false";
                        description "Allow FTP access";
                    }

                    leaf console {
                        type boolean;
                        default "true";
                        description "Allow console access (serial port or Telnet)";
                    }

                    leaf grpc {
                        type boolean;
                        default "false";
                        description "Allow gRPC access";
                    }

                    leaf netconf {
                        type boolean;
                        default "false";
                        description "Allow NETCONF session access";
                    }

                    leaf li {
                        type boolean;
                        default "false";
                        description "Enable/disable access to LI.";
                    }

                } // container access

                container console {
                    description "Enter the console context";

                    leaf login-exec {
                        type types-sros:string-not-all-spaces {
                            length "1..200";
                        }
                        description "File to execute when a user, who derived from the template, logs in successfully";
                    }

                } // container console

            } // list user-template

            list cli-session-group {
                key "cli-session-group-name";
                max-elements 16;
                description "Enter the cli-session-group list instance";

                leaf cli-session-group-name {
                    type types-sros:named-item {
                        pattern "[^ ]*" {
                            error-message "The name cannot contain spaces.";
                        }
                    }
                    description "The name of the cli session group.";
                }

                leaf description {
                    type types-sros:description;
                    description "Text description";
                }

                leaf combined-max-sessions {
                    type types-system:session-limit;
                    description "Maximum number of concurrent SSH and Telnet sessions";
                }

                leaf ssh-max-sessions {
                    type types-system:session-limit;
                    description "Maximum number of concurrent SSH sessions";
                }

                leaf telnet-max-sessions {
                    type types-system:session-limit;
                    description "Maximum number of concurrent TELNET sessions";
                }

                leaf-list apply-groups {
                    type leafref {
                        path "../../../../../groups/group/name";
                    }
                    max-elements 8;
                    ordered-by user;
                    description "Apply a configuration group at this level";
                }

            } // list cli-session-group

        } // container aaa

    } // grouping conf-system-security-aaa

}
